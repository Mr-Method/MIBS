-- File Name : ZTE-DSL-SYSCTRL-MIB.mib
-- Date      : Mon Oct 17 14:13:24 GMT+08:00 2005
-- Author    : ZTE Nms dept.

--
-- Zte Dsl SYS-CTRL Mib 
-- 
-- 

ZTE-DSL-SYSCTRL-MIB DEFINITIONS ::= BEGIN
    IMPORTS     
            zxDsl
            FROM ZTE-DSL-MIB
        RowStatus, DisplayString, TruthValue, MacAddress
            FROM SNMPv2-TC
        DisplayString, ifIndex,ifAdminStatus, ifOperStatus, ifType
            FROM RFC1213-MIB
        MODULE-IDENTITY, OBJECT-TYPE, NOTIFICATION-TYPE, IpAddress, TimeTicks, Counter32, Gauge32, Integer32, Unsigned32
            FROM SNMPv2-SMI
        SnmpAdminString
            FROM SNMP-FRAMEWORK-MIB             
        InetAddress, InetAddressType, InetAddressPrefixLength, InetAutonomousSystemNumber           
            FROM INET-ADDRESS-MIB;

    zxDslSysctrlMib MODULE-IDENTITY
        LAST-UPDATED    "200404151500Z"
        ORGANIZATION    "ZTE Corporation"
        CONTACT-INFO    "ma ke
                  Mail: zte@zte.com.cn
                  Tel : 021-68896477"
        DESCRIPTION     "This MIB defines zte dsl managed objects."
        ::=  {  zxDsl  3  } 
        
    -- TEXTUAL-CONVENTIONS --
    PortList ::= TEXTUAL-CONVENTION 
        DISPLAY-HINT    ""
        STATUS          current
        DESCRIPTION
            "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
        SYNTAX          OCTET STRING
        

    zxDslSysctrlObjects OBJECT IDENTIFIER
        ::=  {  zxDslSysctrlMib  1  }

    zxDslSysctrlTrapObjects OBJECT IDENTIFIER
        ::=  {  zxDslSysctrlMib  2  }
        
    zxDslSysCompatibility OBJECT IDENTIFIER
        ::=  {  zxDslSysctrlMib  3  }     
        
------------------------------------------------------------------------------------                
    zxDslPhysical   OBJECT IDENTIFIER
        ::=  {  zxDslSysctrlObjects  1  }   

    zxDslRackTable  OBJECT-TYPE
        SYNTAX      SEQUENCE  OF  ZxDslRackEntry
        MAX-ACCESS  not-accessible
        STATUS      current
        DESCRIPTION "This table includes common attributes describing
           both ends of the line.  It is required for all ADSL
           physical interfaces.  ADSL physical interfaces are
           those ifEntries where ifType is equal to adsl(94)."
        ::=  { zxDslPhysical  1 }

    zxDslRackEntry  OBJECT-TYPE
        SYNTAX      ZxDslRackEntry
        MAX-ACCESS  not-accessible
        STATUS      current
        DESCRIPTION "An entry in zxDslRackTable."
        INDEX       {  zxDslRackNo  }
        ::=  { zxDslRackTable 1 }

    ZxDslRackEntry  ::=  SEQUENCE {
        zxDslRackNo  Integer32,
        zxDslRackType  Integer32,
        zxDslRackMaxShelfNum  Integer32,
        zxDslRackRowStatus  RowStatus
        }


    zxDslRackNo OBJECT-TYPE 
        SYNTAX          Integer32
        MAX-ACCESS      not-accessible
        STATUS          current
        DESCRIPTION     ":i"
        ::=  {  zxDslRackEntry  1  }


    zxDslRackType   OBJECT-TYPE 
        SYNTAX          Integer32
        MAX-ACCESS      read-create
        STATUS          current
        DESCRIPTION     ":z"
        ::=  {  zxDslRackEntry  2  }


    zxDslRackMaxShelfNum    OBJECT-TYPE 
        SYNTAX          Integer32
        MAX-ACCESS      read-only
        STATUS          current
        DESCRIPTION     ",:? 'O:Fp"
        ::=  {  zxDslRackEntry  3  }


    zxDslRackRowStatus  OBJECT-TYPE 
        SYNTAX          RowStatus
        MAX-ACCESS      read-create
        STATUS          current
        DESCRIPTION     "insert,delete"
        ::=  {  zxDslRackEntry  4  }

    zxDslShelfTable OBJECT-TYPE
        SYNTAX      SEQUENCE  OF  ZxDslShelfEntry
        MAX-ACCESS  not-accessible
        STATUS      current
        DESCRIPTION "This table includes common attributes describing
           both ends of the line.  It is required for all ADSL
           physical interfaces.  ADSL physical interfaces are
           those ifEntries where ifType is equal to adsl(94)."
        ::=  { zxDslPhysical  2 }

    zxDslShelfEntry OBJECT-TYPE
        SYNTAX      ZxDslShelfEntry
        MAX-ACCESS  not-accessible
        STATUS      current
        DESCRIPTION "An entry in zxDslShelfTable."
        INDEX       {  zxDslShelfRackNo, zxDslShelfNo  }
        ::=  { zxDslShelfTable 1 }

    ZxDslShelfEntry  ::=  SEQUENCE {
        zxDslShelfRackNo    Integer32,
        zxDslShelfNo        Integer32,
        zxDslShelfType      Integer32,
        zxDslShelfMaxSlotNum  Integer32,
        zxDslShelfInvSn      DisplayString,
        zxDslShelfCleiCode   DisplayString,
        zxDslShelfRowStatus  RowStatus
        }


    zxDslShelfRackNo    OBJECT-TYPE 
        SYNTAX          Integer32
        MAX-ACCESS      not-accessible
        STATUS          current
        DESCRIPTION "Rack no."
        DEFVAL {1}
        ::=  {  zxDslShelfEntry  1  }


    zxDslShelfNo    OBJECT-TYPE 
        SYNTAX          Integer32
        MAX-ACCESS      not-accessible
        STATUS          current
        DESCRIPTION "Shelf no."
        DEFVAL {1}
        ::=  {  zxDslShelfEntry  2  }


    zxDslShelfType  OBJECT-TYPE 
        SYNTAX          Integer32
        MAX-ACCESS      read-create
        STATUS          current
        DESCRIPTION ""
        ::=  {  zxDslShelfEntry  3  }


    zxDslShelfMaxSlotNum    OBJECT-TYPE 
        SYNTAX          Integer32
        MAX-ACCESS      read-only
        STATUS          current
        DESCRIPTION "Max Slot Number in a shelf."
        ::=  {  zxDslShelfEntry  4  }


    zxDslShelfInvSn     OBJECT-TYPE 
        SYNTAX          DisplayString  ( SIZE ( 0 .. 64  ) )
        MAX-ACCESS      read-create
        STATUS          current
        DESCRIPTION     "This MIB is defined for serial number of this shelf.
              it is used by inventroy management."
        ::=  {  zxDslShelfEntry  5  }
        
        
    zxDslShelfCleiCode     OBJECT-TYPE 
        SYNTAX          DisplayString  ( SIZE ( 0 .. 64  ) )
        MAX-ACCESS      read-only
        STATUS          current
        DESCRIPTION     "This MIB is defined for CLEI code of this card.
              it is used by inventroy management.Pls reference 
              http://www.commonlanguage.com to get knowledge about CLEI code. 
              "
        REFERENCE "http://www.commonlanguage.com"              
        ::=  {  zxDslShelfEntry  6  }



    zxDslShelfRowStatus OBJECT-TYPE 
        SYNTAX          RowStatus
        MAX-ACCESS      read-create
        STATUS          current
        DESCRIPTION     "insert,delete"
        ::=  {  zxDslShelfEntry  15  }












    zxDslBoardConfigTable   OBJECT-TYPE
        SYNTAX      SEQUENCE  OF  ZxDslBoardConfigEntry
        MAX-ACCESS  not-accessible
        STATUS      current
        DESCRIPTION "This table includes common attributes describing
           both ends of the line.  It is required for all ADSL
           physical interfaces.  ADSL physical interfaces are
           those ifEntries where ifType is equal to adsl(94)."
        ::=  { zxDslPhysical  3 }

    zxDslBoardConfigEntry   OBJECT-TYPE
        SYNTAX      ZxDslBoardConfigEntry
        MAX-ACCESS  not-accessible
        STATUS      current
        DESCRIPTION "An entry in zxDslBoardConfigTable."
        INDEX       {  zxDslBoardConfigRackNo, zxDslBoardConfigShelfNo, zxDslBoardConfigSlotNo  }
        ::=  { zxDslBoardConfigTable 1 }

    ZxDslBoardConfigEntry  ::=  SEQUENCE {
        zxDslBoardConfigRackNo  Integer32,
        zxDslBoardConfigShelfNo  Integer32,
        zxDslBoardConfigSlotNo  Integer32,
        zxDslBoardConfigSubType  Integer32,
        zxDslBoardConfigBaseType  Integer32,
        zxDslBoardConfigHardVerType  Integer32,
        zxDslBoardConfigRowStatus  RowStatus
        }


    zxDslBoardConfigRackNo  OBJECT-TYPE 
        SYNTAX          Integer32
        MAX-ACCESS      not-accessible
        STATUS          current
        DESCRIPTION     ""
        ::=  {  zxDslBoardConfigEntry  1  }


    zxDslBoardConfigShelfNo OBJECT-TYPE 
        SYNTAX          Integer32
        MAX-ACCESS      not-accessible
        STATUS          current
        DESCRIPTION     ""
        ::=  {  zxDslBoardConfigEntry  2  }


    zxDslBoardConfigSlotNo  OBJECT-TYPE 
        SYNTAX          Integer32
        MAX-ACCESS      not-accessible
        STATUS          current
        DESCRIPTION     ""
        ::=  {  zxDslBoardConfigEntry  3  }


    zxDslBoardConfigSubType OBJECT-TYPE 
        SYNTAX          Integer32
        MAX-ACCESS      read-create
        STATUS          current
        DESCRIPTION     ""
        ::=  {  zxDslBoardConfigEntry  4  }


    zxDslBoardConfigBaseType    OBJECT-TYPE 
        SYNTAX          Integer32
        MAX-ACCESS      read-create
        STATUS          current
        DESCRIPTION     ""
        ::=  {  zxDslBoardConfigEntry  5  }
    
    zxDslBoardConfigHardVerType OBJECT-TYPE 
        SYNTAX          Integer32
        MAX-ACCESS      read-create
        STATUS          current
        DESCRIPTION     "This is used to configure linecard supporting 8220V1.X version or 8220V2.X
                                 version and ADSL1 or ADSL2"
        ::=  {  zxDslBoardConfigEntry  6  }


    zxDslBoardConfigRowStatus   OBJECT-TYPE 
        SYNTAX          RowStatus
        MAX-ACCESS      read-create
        STATUS          current
        DESCRIPTION     "insert,delete"
        ::=  {  zxDslBoardConfigEntry  7  }

    zxDslSplitBoardTable    OBJECT-TYPE
        SYNTAX      SEQUENCE  OF  ZxDslSplitBoardEntry
        MAX-ACCESS  not-accessible
        STATUS      current
        DESCRIPTION "This table includes common attributes describing
           both ends of the line.  It is required for all ADSL
           physical interfaces.  ADSL physical interfaces are
           those ifEntries where ifType is equal to adsl(94)."
        ::=  { zxDslPhysical  4 }

    zxDslSplitBoardEntry    OBJECT-TYPE
        SYNTAX      ZxDslSplitBoardEntry
        MAX-ACCESS  not-accessible
        STATUS      current
        DESCRIPTION "An entry in zxDslSplitBoardTable."
        INDEX       {  zxDslSplitBoardRackNo, zxDslSplitBoardShelfNo, zxDslSplitBoardSlotNo  }
        ::=  { zxDslSplitBoardTable 1 }

    ZxDslSplitBoardEntry  ::=  SEQUENCE {
        zxDslSplitBoardRackNo  Integer32,
        zxDslSplitBoardShelfNo  Integer32,
        zxDslSplitBoardSlotNo  Integer32,
        zxDslSplitBoardPos  Integer32,
        zxDslSplitBoardStatus  Integer32
        }


    zxDslSplitBoardRackNo   OBJECT-TYPE 
        SYNTAX          Integer32
        MAX-ACCESS      not-accessible
        STATUS          current
        DESCRIPTION     "rack number"
        ::=  {  zxDslSplitBoardEntry  1  }


    zxDslSplitBoardShelfNo  OBJECT-TYPE 
        SYNTAX          Integer32
        MAX-ACCESS      not-accessible
        STATUS          current
        DESCRIPTION     "shelf number"
        ::=  {  zxDslSplitBoardEntry  2  }


    zxDslSplitBoardSlotNo   OBJECT-TYPE 
        SYNTAX          Integer32
        MAX-ACCESS      not-accessible
        STATUS          current
        DESCRIPTION     "slot number"
        ::=  {  zxDslSplitBoardEntry  3  }


    zxDslSplitBoardPos  OBJECT-TYPE 
        SYNTAX          Integer32
        MAX-ACCESS      read-write
        STATUS          current
        DESCRIPTION     "splitter board position 1 == SelfRack, 2 == SplitterRack 0 == NULL"
        ::=  {  zxDslSplitBoardEntry  4  }


    zxDslSplitBoardStatus   OBJECT-TYPE 
        SYNTAX          Integer32
        MAX-ACCESS      read-write
        STATUS          current
        DESCRIPTION     "splitter board status"
        ::=  {  zxDslSplitBoardEntry  5  }

    zxDslSubBoardTable  OBJECT-TYPE
        SYNTAX      SEQUENCE  OF  ZxDslSubBoardEntry
        MAX-ACCESS  not-accessible
        STATUS      current
        DESCRIPTION "This table includes common attributes describing
           both ends of the line.  It is required for all ADSL
           physical interfaces.  ADSL physical interfaces are
           those ifEntries where ifType is equal to adsl(94)."
        ::=  { zxDslPhysical  5 }

    zxDslSubBoardEntry  OBJECT-TYPE
        SYNTAX      ZxDslSubBoardEntry
        MAX-ACCESS  not-accessible
        STATUS      current
        DESCRIPTION "An entry in zxDslSubBoardTable."
        INDEX       {  zxDslSubBoardRackNo, zxDslSubBoardShelfNo, zxDslSubBoardSlotNo, zxDslSubBoardSubCardNo  }
        ::=  { zxDslSubBoardTable 1 }

    ZxDslSubBoardEntry  ::=  SEQUENCE {
        zxDslSubBoardRackNo      Integer32,
        zxDslSubBoardShelfNo     Integer32,
        zxDslSubBoardSlotNo      Integer32,
        zxDslSubBoardSubCardNo   Integer32,
        zxDslSubBoardType        Integer32,
        zxDslSubBoardDescr       OCTET STRING,      
        zxDslSubBoardStatus      INTEGER,
        zxDslSubBoardReset       Integer32,
        zxDslSubBoardRowStatus   Integer32,        
        zxDslSubBoardHardVersion  OCTET STRING,
        zxDslSubBoardSoftVersion  OCTET STRING,
        zxDslSubBoardPortNum      Integer32
        }


    zxDslSubBoardRackNo OBJECT-TYPE 
        SYNTAX          Integer32
        MAX-ACCESS      not-accessible
        STATUS          current
        DESCRIPTION     "rack number"
        ::=  {  zxDslSubBoardEntry  1  }


    zxDslSubBoardShelfNo    OBJECT-TYPE 
        SYNTAX          Integer32
        MAX-ACCESS      not-accessible
        STATUS          current
        DESCRIPTION     "shelf number"
        ::=  {  zxDslSubBoardEntry  2  }


    zxDslSubBoardSlotNo OBJECT-TYPE 
        SYNTAX          Integer32
        MAX-ACCESS      not-accessible
        STATUS          current
        DESCRIPTION     "slot number"
        ::=  {  zxDslSubBoardEntry  3  }


    zxDslSubBoardSubCardNo  OBJECT-TYPE 
        SYNTAX          Integer32
        MAX-ACCESS      not-accessible
        STATUS          current
        DESCRIPTION     "subcard number"
        ::=  {  zxDslSubBoardEntry  4  }


    zxDslSubBoardType   OBJECT-TYPE 
        SYNTAX          Integer32
        MAX-ACCESS      read-write
        STATUS          current
        DESCRIPTION     "subBoard type"
        ::=  {  zxDslSubBoardEntry  5  }

    zxDslSubBoardDescr  OBJECT-TYPE
        SYNTAX          OCTET STRING  ( SIZE ( 1 .. 255  ) ) 
        MAX-ACCESS      read-only
        STATUS          current
        DESCRIPTION     "sub-board information."
        ::=  {  zxDslSubBoardEntry  6  }
    
    zxDslSubBoardStatus OBJECT-TYPE 
        SYNTAX          INTEGER
            {
             inService   (1),
             notInService(2),
             hwOnline(3),
             hwOffline(4),
             configuring(5),
             configFailed(6),
             typeMismatch(7),
             deactived(8),
             faulty(9),
             invalid(10)             
            }
        MAX-ACCESS      read-only
        STATUS          current
        DESCRIPTION     "This MIB is defined for the sub card status on the card.
          inService(1)   --  card pluged in,running normally and service is being
                             provided normally.
          notInService(2)--  card pluged in,running normally but service is stopped.
          hwOnline(3)    --  card pluged in AND card communication is ok,but software 
                             isn't running now.
          hwOffline(4)   --  card not pluged in,but added to agent's database only
          configuring(5) --  card pluged in,but it is configuring
          configFailed(6)--  card pluged in,but configuration failed
          typeMismatch(7)--  card pluged in,but it's type is mismatch
          deactived(8)   --  card pluged in,but it is deactivated by a manager
          faulty(9)      --  fault occurs when card is running normally
          invalid(10)    --  invalid card instance,such as adding card failed.    
        "
        ::=  {  zxDslSubBoardEntry  7  }

    zxDslSubBoardReset  OBJECT-TYPE 
        SYNTAX          Integer32
        MAX-ACCESS      read-write
        STATUS          current
        DESCRIPTION     ""
        ::=  {  zxDslSubBoardEntry  8  }

    zxDslSubBoardRowStatus  OBJECT-TYPE 
        SYNTAX          Integer32
        MAX-ACCESS      read-write
        STATUS          current
        DESCRIPTION     ""
        ::=  {  zxDslSubBoardEntry  9  }

    zxDslSubBoardHardVersion   OBJECT-TYPE 
        SYNTAX          OCTET STRING( SIZE ( 1 .. 32  ) )
        MAX-ACCESS      read-only
        STATUS          current
        DESCRIPTION     "sub board hard version, default is UNKNOWN"
        ::=  {  zxDslSubBoardEntry  10  }

    zxDslSubBoardSoftVersion   OBJECT-TYPE 
        SYNTAX          OCTET STRING ( SIZE ( 1 .. 32  ) )
        MAX-ACCESS      read-only
        STATUS          current
        DESCRIPTION     "sub board software version, default is UNKNOWN"
        ::=  {  zxDslSubBoardEntry  11  }

    zxDslSubBoardPortNum   OBJECT-TYPE 
        SYNTAX          Integer32
        MAX-ACCESS      read-only
        STATUS          current
        DESCRIPTION     "sub board port number"
        ::=  {  zxDslSubBoardEntry  12  }       




    zxDslBoardTable OBJECT-TYPE
        SYNTAX      SEQUENCE  OF  ZxDslBoardEntry
        MAX-ACCESS  not-accessible
        STATUS      current
        DESCRIPTION "This table includes common attributes describing
           both ends of the line.  It is required for all ADSL
           physical interfaces.  ADSL physical interfaces are
           those ifEntries where ifType is equal to adsl(94)."
        ::=  { zxDslPhysical  6 }

    zxDslBoardEntry OBJECT-TYPE
        SYNTAX      ZxDslBoardEntry
        MAX-ACCESS  not-accessible
        STATUS      current
        DESCRIPTION "An entry in zxDslBoardTable."
        INDEX       {  zxDslBoardRackNo, zxDslBoardShelfNo, zxDslBoardSlotNo  }
        ::=  { zxDslBoardTable 1 }

    ZxDslBoardEntry  ::=  SEQUENCE {
        zxDslBoardRackNo  Integer32,
        zxDslBoardShelfNo  Integer32,
        zxDslBoardSlotNo  Integer32,
        zxDslBoardType  Integer32,
        zxDslBoardDescr  OCTET STRING,
        zxDslBoardPortNum  Integer32,
        zxDslBoardPortType  Integer32,
        zxDslBoardAdminStatus    INTEGER,
        zxDslBoardOperStatus  INTEGER,
        zxDslBoardHardVersion  OCTET STRING,
        zxDslBoardSoftVersion  OCTET STRING,
        zxDslBoardSoftLastChange  TimeTicks,        
        zxDslBoardReset    Integer32,
        zxDslBoardCpuLoad  Integer32,
        zxDslBoardCpuLoadThreshhold  Integer32,
        zxDslBoardMemUsage    Integer32,
        zxDslBoardMemUsageThreshhold    Integer32,
        zxDslBoardActPortNum    Integer32,
        zxDslBoardHardVerStatus    Integer32,
        zxDslBoardSoftVerCfg    Integer32,
        zxDslBoardStandByStatus   INTEGER,
        zxDslBoardMemTotalSize  Integer32
        }


    zxDslBoardRackNo    OBJECT-TYPE 
        SYNTAX          Integer32
        MAX-ACCESS      not-accessible
        STATUS          current
        DESCRIPTION     "rack number"
        ::=  {  zxDslBoardEntry  1  }


    zxDslBoardShelfNo   OBJECT-TYPE 
        SYNTAX          Integer32
        MAX-ACCESS      not-accessible
        STATUS          current
        DESCRIPTION     "shelf number"
        ::=  {  zxDslBoardEntry  2  }


    zxDslBoardSlotNo    OBJECT-TYPE 
        SYNTAX          Integer32
        MAX-ACCESS      not-accessible
        STATUS          current
        DESCRIPTION     "slot number"
        ::=  {  zxDslBoardEntry  3  }


    zxDslBoardType  OBJECT-TYPE 
        SYNTAX          Integer32
        MAX-ACCESS      read-only
        STATUS          current
        DESCRIPTION     "board type"
        ::=  {  zxDslBoardEntry  4  }


    zxDslBoardDescr OBJECT-TYPE 
        SYNTAX          OCTET STRING ( SIZE ( 1 .. 32  ) )
        MAX-ACCESS      read-only
        STATUS          current
        DESCRIPTION     "board descript"
        ::=  {  zxDslBoardEntry  5  }


    zxDslBoardPortNum   OBJECT-TYPE 
        SYNTAX          Integer32
        MAX-ACCESS      read-only
        STATUS          current
        DESCRIPTION     "board portnum"
        ::=  {  zxDslBoardEntry  6  }


    zxDslBoardPortType  OBJECT-TYPE 
        SYNTAX          Integer32
        MAX-ACCESS      read-only
        STATUS          current
        DESCRIPTION     "board port type"
        ::=  {  zxDslBoardEntry  7  }
    
    zxDslBoardAdminStatus   OBJECT-TYPE 
        SYNTAX          INTEGER
        {
            unlock(3),
            lock(4)
        }
        MAX-ACCESS      read-write
        STATUS          current
        DESCRIPTION     "board administrative status."
        DEFVAL { unlock }
        ::=  {  zxDslBoardEntry  8  }

    zxDslBoardOperStatus    OBJECT-TYPE 
        SYNTAX          INTEGER
                        {
                            unknown(1),      --  card pluged in but can't get right state.
                            offline(2),      --  card not pluged in,but added to agent's database only
                            online(3),       --  card pluged in.hardware online or resetting
                            inService(4),    --  card pluged in and running normally
                            standby(5),      --  card pluged in,it is runing as a slave card.
                            configuring(6)   --  card pluged in,but it is configuring data.
                        }    
        MAX-ACCESS      read-only
        STATUS          current
        DESCRIPTION     "board operational status"
        ::=  {  zxDslBoardEntry  9  }


    zxDslBoardHardVersion   OBJECT-TYPE 
        SYNTAX          OCTET STRING( SIZE ( 1 .. 32  ) )
        MAX-ACCESS      read-only
        STATUS          current
        DESCRIPTION     "board hard version"
        ::=  {  zxDslBoardEntry  10  }


    zxDslBoardSoftVersion   OBJECT-TYPE 
        SYNTAX          OCTET STRING ( SIZE ( 1 .. 32  ) )
        MAX-ACCESS      read-only
        STATUS          current
        DESCRIPTION     "board software version"
        ::=  {  zxDslBoardEntry  11  }


    zxDslBoardSoftLastChange    OBJECT-TYPE 
        SYNTAX          TimeTicks
        MAX-ACCESS      read-only
        STATUS          current
        DESCRIPTION     "soft last change"
        ::=  {  zxDslBoardEntry  12  }
        
    zxDslBoardReset OBJECT-TYPE 
        SYNTAX          Integer32
        MAX-ACCESS      read-write
        STATUS          current
        DESCRIPTION     "Server as reset card"
        ::=  {  zxDslBoardEntry  13  }
    
    zxDslBoardCpuLoad   OBJECT-TYPE 
        SYNTAX          Integer32
        MAX-ACCESS      read-only
        STATUS          current
        DESCRIPTION     "Server as cup load of card"
        ::=  {  zxDslBoardEntry  14  }
    
    zxDslBoardCpuLoadThreshhold OBJECT-TYPE 
        SYNTAX          Integer32
        MAX-ACCESS      read-write
        STATUS          current
        DESCRIPTION     "Server as cup load of card"
        ::=  {  zxDslBoardEntry  15  }
        
    zxDslBoardMemUsage  OBJECT-TYPE 
        SYNTAX          Integer32
        MAX-ACCESS      read-only
        STATUS          current
        DESCRIPTION     "Server as memory usage rate of card"
        ::=  {  zxDslBoardEntry  16  }
    
    zxDslBoardMemUsageThreshhold    OBJECT-TYPE 
        SYNTAX          Integer32
        MAX-ACCESS      read-write
        STATUS          current
        DESCRIPTION     "Server as memory usage rate of card"
        ::=  {  zxDslBoardEntry  17  }
    
    zxDslBoardActPortNum    OBJECT-TYPE 
        SYNTAX          Integer32
        MAX-ACCESS      read-only
        STATUS          current
        DESCRIPTION     "Server as active port numbers of card"
        ::=  {  zxDslBoardEntry  18  }
    
    zxDslBoardHardVerStatus OBJECT-TYPE 
        SYNTAX          Integer32
        MAX-ACCESS      read-only
        STATUS          current
        DESCRIPTION     "Server as v1 or v2 line card of 8000, g1 or g2 line type of 8000"
        ::=  {  zxDslBoardEntry  19  }
    
    zxDslBoardSoftVerCfg    OBJECT-TYPE 
        SYNTAX          Integer32 
        MAX-ACCESS      read-write
        STATUS          current
        DESCRIPTION     "Server as configuring the running software type on atugb"
        ::=  {  zxDslBoardEntry  20  }        
    
    zxDslBoardStandByStatus OBJECT-TYPE 
        SYNTAX          INTEGER{master(1), slave(2), single(3)}
        MAX-ACCESS      read-write
        STATUS          current
        DESCRIPTION     "Board standBy status.
                NOTE: Not available now. "
        ::=  {  zxDslBoardEntry  21  }        
        
    zxDslBoardMemTotalSize    OBJECT-TYPE 
        SYNTAX          Integer32 
        UNITS              "KB"
        MAX-ACCESS      read-only
        STATUS          current
        DESCRIPTION     "Total memory size of board"
        ::=  {  zxDslBoardEntry  22  }        



--  Card Inventory Mgmt table
  
    zxDslCardInvMgmtTable       OBJECT-TYPE
        SYNTAX SEQUENCE OF ZxDslCardInvMgmtEntry
        MAX-ACCESS not-accessible
        STATUS current
        DESCRIPTION
            "A list of card entries."
        ::= { zxDslPhysical 7 }

    zxDslCardInvMgmtEntry OBJECT-TYPE
        SYNTAX ZxDslCardInvMgmtEntry 
        MAX-ACCESS not-accessible
        STATUS current
        DESCRIPTION
            "An card entry containing objects 
            describing the card in some slot."
        INDEX { zxDslCardInvRack, zxDslCardInvShelf, 
                zxDslCardInvSlot, zxDslCardInvSubSlot }
        ::= { zxDslCardInvMgmtTable 1 }

    ZxDslCardInvMgmtEntry ::= SEQUENCE {
            zxDslCardInvRack          Integer32, 
            zxDslCardInvShelf         Integer32,
            zxDslCardInvSlot          INTEGER,
            zxDslCardInvSubSlot       INTEGER,
            zxDslCardInvSn            DisplayString,
            zxDslCardInvCleiCode      DisplayString
            }

    zxDslCardInvRack    OBJECT-TYPE
        SYNTAX      Integer32
        MAX-ACCESS  not-accessible
        STATUS      current
        DESCRIPTION
            "The rack number of the card"
        ::= { zxDslCardInvMgmtEntry 1 }
        
     zxDslCardInvShelf  OBJECT-TYPE
        SYNTAX      Integer32
        MAX-ACCESS  not-accessible
        STATUS      current
        DESCRIPTION
            "The shelf number of the card"
        ::= { zxDslCardInvMgmtEntry 2 }
        
     zxDslCardInvSlot   OBJECT-TYPE
        SYNTAX      INTEGER(1..18)
        MAX-ACCESS  not-accessible
        STATUS      current
        DESCRIPTION
            "The slot number of the card"
        ::= { zxDslCardInvMgmtEntry 3 }


     zxDslCardInvSubSlot    OBJECT-TYPE
        SYNTAX      INTEGER(0..4)
        MAX-ACCESS  not-accessible
        STATUS      current
        DESCRIPTION
            "The sub slot number of the card.If there is no sublot,then this value
            is 0. "
        ::= { zxDslCardInvMgmtEntry 4 }

     zxDslCardInvSn     OBJECT-TYPE
        SYNTAX      DisplayString
        MAX-ACCESS  read-write
        STATUS      current
        DESCRIPTION
            "The series number of the card."
        ::= { zxDslCardInvMgmtEntry 5 }


     zxDslCardInvCleiCode   OBJECT-TYPE
        SYNTAX      DisplayString
        MAX-ACCESS  read-only
        STATUS      current
        DESCRIPTION
            "The CLEI code of the card.It is a present of a cardtype."
        ::= { zxDslCardInvMgmtEntry 6 }

        
--------------------------------------------------------------------------------
-- Dsl enviroment monitoring mgmt,such as chassis temperature and fans.

   zxDslEnvMon      OBJECT IDENTIFIER ::= {zxDslSysctrlObjects 2}

   zxDslEnvChassisTemperature OBJECT-TYPE
       SYNTAX       Integer32 
       UNITS        "centigrade"
       MAX-ACCESS   read-only
       STATUS       current
       DESCRIPTION
            "The current temperature of the chassis."
       ::= { zxDslEnvMon 1 }


   zxDslEnvTemperatureThreshold OBJECT-TYPE
       SYNTAX       Integer32 
       UNITS        "centigrade"
       MAX-ACCESS   read-write
       STATUS       current
       DESCRIPTION
            "The threshold of the chassis temperature,zxDslEnvTempExceeded trap 
        should be generated when zxDslEnvChassisTemperature is lareger than it.
       Otherwise,zxDslEnvTempNormal trap should be generated when 
        zxDslEnvChassisTemperature is less than it."
       DEFVAL { 75 }
       ::= { zxDslEnvMon 2 }

    zxDslEnvTemperatureTrapEnable OBJECT-TYPE
        SYNTAX     INTEGER{
            enable(1),
            disable(2)
        }
        MAX-ACCESS  read-write
        STATUS current
        DESCRIPTION
            "The adminstrative status of temperature alarm trap."
        DEFVAL { enable }
        ::= { zxDslEnvMon 3 } 
        
-- Fans mgmt   ----------------

   zxDslEnvFanMgmtCap OBJECT-TYPE
        SYNTAX     BITS
                {
                    unused(0),
                    speed_control(1),
                    alarm_send(2),
                    shutdown_control(3)
                }
        MAX-ACCESS  read-only
        STATUS current
        DESCRIPTION
            "The capbilities to be controlled.
               speed_control(1) -- The speed of fun can be controlled
               alarm_send(2)    -- Alarm of fans can be generated and send to manager.
               shutdown_control(3) -- Which fan is running can be controlled.
            "
        ::= { zxDslEnvMon 4 }  
          
          
   zxDslEnvFanSpeedCtrlType OBJECT-TYPE
        SYNTAX     INTEGER
                {
                    auto_SpeedControl(1),
                    fix_Speed(2),
                    noSpeedControl(3)
                }
        MAX-ACCESS  read-write
        STATUS current
        DESCRIPTION
            "The control type of fan speed.
            If fix_Speed(2) is selected,zxDslEnvFanSpeed in zxDslEnvFanTable
            should be configured.
            "
        ::= { zxDslEnvMon 5 }  
          
       
   zxDslEnvFanTrapEnable OBJECT-TYPE
        SYNTAX     INTEGER{
            enable(1),
            disable(2)
        }
        MAX-ACCESS  read-write
        STATUS current
        DESCRIPTION
            "The adminstrative status of fun's alarm trap."
        DEFVAL { enable }
        ::= { zxDslEnvMon 6 } 

       
   zxDslEnvFanTrayAlarmBeep OBJECT-TYPE
        SYNTAX     INTEGER{
            enable(1),
            disable(2)
        }
        MAX-ACCESS  read-write
        STATUS current
        DESCRIPTION
            "Enable or disable the alarm beep for fun tray."
        DEFVAL { enable }
        ::= { zxDslEnvMon 7 } 

       
   zxDslEnvEpmRelaySwitchEnable OBJECT-TYPE
        SYNTAX     INTEGER{
            enable(1),
            disable(2)
        }
        MAX-ACCESS  read-write
        STATUS current
        DESCRIPTION
            "Enable or disable the EPM relay switch.
            if it's disabled, there will be four environment switch,
            and if it's enabled, there will be only two environment switch.
            Other two environment switch and the EMP serial port are alternative."
        DEFVAL { enable }
        ::= { zxDslEnvMon 8 } 
        
        
   zxDslEnvLossOfPowerTrapEnable OBJECT-TYPE
        SYNTAX     INTEGER{
            enable(1),
            disable(2)
        }
        MAX-ACCESS  read-write
        STATUS current
        DESCRIPTION
            "Enable or disable the dying gasp event when the device is 
             power off or power failure."
        DEFVAL { enable }
        ::= { zxDslEnvMon 9 }         
            
        
-- fans table ----------------
    
   zxDslEnvFanTable OBJECT-TYPE
        SYNTAX SEQUENCE OF ZxDslEnvFanEntry 
        MAX-ACCESS not-accessible
        STATUS     current
        DESCRIPTION
            "The table of fan's managed objects.Each row instance represents 
            a controllable fan unit,may be a controlled fan or a controlled fan tray.
            
            When zxDslEnvFanOperstatus and zxDslEnvFanAdminstatus are mismatched,
            zxDslEnvFanFailed trap should be sent to manager.If this error state
            doesn't exist,zxDslEnvFanRecovered trap should be sent.
            "
        ::= { zxDslEnvMon 10 }

   zxDslEnvFanEntry  OBJECT-TYPE
        SYNTAX     ZxDslEnvFanEntry 
        MAX-ACCESS not-accessible
        STATUS     current
        DESCRIPTION
            "a entry of this table."
        INDEX      { zxDslEnvFanIndex }
        ::= { zxDslEnvFanTable 1 }

    ZxDslEnvFanEntry ::= SEQUENCE {
        zxDslEnvFanIndex               Integer32,
        zxDslEnvFanSpeed               INTEGER,
        zxDslEnvFanAdminstatus         INTEGER, 
        zxDslEnvFanOperstatus          INTEGER
    }
        
    zxDslEnvFanIndex OBJECT-TYPE
        SYNTAX     Integer32 
        MAX-ACCESS not-accessible
        STATUS     current
        DESCRIPTION
            "The index of this fan or fan tray referred to in this table entry."
        ::= { zxDslEnvFanEntry 1 }   
       
    zxDslEnvFanSpeed    OBJECT-TYPE 
        SYNTAX          INTEGER
                {
                    auto_speed(0),-- read only
                    low_speed(1),
                    middle_speed(2),
                    normal_speed(3),
                    high_speed(4)
                }
        MAX-ACCESS      read-create
        STATUS          current
        DESCRIPTION     "The speed of fan.
                If it is to be set, zxDslEnvFanSpeedCtrlType must be fix_Speed(2).
        "
       DEFVAL { normal_speed }
        ::=  {  zxDslEnvFanEntry  2  }
    
    zxDslEnvFanAdminstatus  OBJECT-TYPE 
        SYNTAX          INTEGER 
        {
            up(1),
            down(2)
        }
        MAX-ACCESS      read-create
        STATUS          current
        DESCRIPTION     "The adminstrative status of fan"
        DEFVAL { up }
        ::=  {  zxDslEnvFanEntry  3  }  


    zxDslEnvFanOperstatus   OBJECT-TYPE 
        SYNTAX          INTEGER 
        {
            up(1),
            down(2)
        }
        MAX-ACCESS      read-only
        STATUS          current
        DESCRIPTION     "The operational status of a fan."
        ::=  {  zxDslEnvFanEntry  4  }  
            
-- switch table ----------------

   zxDslEnvDeviceTable OBJECT-TYPE
       SYNTAX      SEQUENCE OF ZxDslEnvDeviceEntry 
       MAX-ACCESS  not-accessible
       STATUS      current
       DESCRIPTION
           "The table of environment monitor Device."
       ::= { zxDslEnvMon 11 }

   zxDslEnvDeviceEntry  OBJECT-TYPE
       SYNTAX      ZxDslEnvDeviceEntry 
       MAX-ACCESS  not-accessible
       STATUS      current
       DESCRIPTION
           "a entry of this table."
       INDEX       { zxDslEnvEnvDeviceIndex }
       ::= { zxDslEnvDeviceTable 1 }

    ZxDslEnvDeviceEntry ::= SEQUENCE {
        zxDslEnvEnvDeviceIndex               Integer32,
        zxDslEnvEnvDeviceName                DisplayString,
        zxDslEnvDeviceRowStatus              RowStatus
    }
        
    zxDslEnvEnvDeviceIndex OBJECT-TYPE
        SYNTAX     Integer32 
        MAX-ACCESS not-accessible
        STATUS     current
        DESCRIPTION
            "The index of this environment monitor Device.
            "
        ::= { zxDslEnvDeviceEntry 1 }   
       
    zxDslEnvEnvDeviceName OBJECT-TYPE 
        SYNTAX      DisplayString  (SIZE(0..32))                 
        MAX-ACCESS  read-create
        STATUS      current
        DESCRIPTION     
            "the name of environment monitor Device.
            zxDslEnvEnvDeviceIndex 1-50 is default value,can't delete or modify.
            "        
        ::= { zxDslEnvDeviceEntry 2 }

    zxDslEnvDeviceRowStatus OBJECT-TYPE 
        SYNTAX      RowStatus
        MAX-ACCESS  read-create
        STATUS      current
        DESCRIPTION   "The status of this table."
        ::=  { zxDslEnvDeviceEntry 3 }
    
   zxDslEnvSwitchTable OBJECT-TYPE
        SYNTAX SEQUENCE OF ZxDslEnvSwitchEntry 
        MAX-ACCESS not-accessible
        STATUS     current
        DESCRIPTION
            "The table of switch's managed objects.Each row instance represents 
            a device connected with this switch.
            "
        ::= { zxDslEnvMon 12 }

   zxDslEnvSwitchEntry  OBJECT-TYPE
        SYNTAX     ZxDslEnvSwitchEntry 
        MAX-ACCESS not-accessible
        STATUS     current
        DESCRIPTION
            "a entry of this table."
        INDEX      { zxDslEnvSwitchIndex }
        ::= { zxDslEnvSwitchTable 1 }

    ZxDslEnvSwitchEntry ::= SEQUENCE {
        zxDslEnvSwitchIndex               Integer32,
        zxDslEnvDeviceId                  Integer32,
        zxDslEnvSwitchNormalStatus        INTEGER,
        zxDslEnvSwitchEnable              INTEGER,
        zxDslEnvSwitchCurrentStatus       INTEGER
    }
        
    zxDslEnvSwitchIndex OBJECT-TYPE
        SYNTAX     Integer32 
        MAX-ACCESS not-accessible
        STATUS     current
        DESCRIPTION
            "The index of this Switch."
        ::= { zxDslEnvSwitchEntry 1 }   
       
    zxDslEnvDeviceId    OBJECT-TYPE 
        SYNTAX          Integer32
        MAX-ACCESS      read-write
        STATUS          current
        DESCRIPTION     
            "The device id.If this switch can't connect with any device,
            zxDslEnvDeviceId set to 0."
        DEFVAL { 0 }
        ::= { zxDslEnvSwitchEntry 2 }             
        
    zxDslEnvSwitchNormalStatus  OBJECT-TYPE 
        SYNTAX      INTEGER  
        { 
            low(0),
            high(1)
        } 
        MAX-ACCESS  read-write
        STATUS      current
        DESCRIPTION   
            "The Threshold of this environment monitor Device."
        ::= { zxDslEnvSwitchEntry 3 }
   
    zxDslEnvSwitchEnable  OBJECT-TYPE 
        SYNTAX      INTEGER  
        { 
            enable(1),
            disable(2)
        } 
        MAX-ACCESS  read-write
        STATUS      current
        DESCRIPTION   
            "Enables and disables Trap of this environment monitor Device."
        ::= { zxDslEnvSwitchEntry 4 }        
     
    zxDslEnvSwitchCurrentStatus  OBJECT-TYPE 
        SYNTAX      INTEGER  
        { 
            low(0),
            high(1)
        } 
        MAX-ACCESS  read-only
        STATUS      current
        DESCRIPTION   
            "The current status of this environment monitor Device."
        ::= { zxDslEnvSwitchEntry 5 }     
        
    zxDslEnvExteriorPower     OBJECT IDENTIFIER ::= {zxDslEnvMon 13}        
  
    zxDslEnvExteriorPowerEnable  OBJECT-TYPE 
        SYNTAX      INTEGER  
        { 
            enable(1),
            disable(2)
        } 
        MAX-ACCESS  read-write
        STATUS      current
        DESCRIPTION   
            "Enables and disables Trap of Exterior Power."
        ::= { zxDslEnvExteriorPower 1 }        
          
    zxDslEnvBatteriesVoltage  OBJECT IDENTIFIER ::= {zxDslEnvMon 14}  

    zxDslEnvBatteriesVoltageEnable  OBJECT-TYPE 
        SYNTAX      INTEGER  
        { 
            enable(1),
            disable(2)
        } 
        MAX-ACCESS  read-write
        STATUS      current
        DESCRIPTION   
            "Enables and disables Trap of Batteries Voltage."
        ::= { zxDslEnvBatteriesVoltage 1 }        
           
    zxDslEnvPowerFailure      OBJECT IDENTIFIER ::= {zxDslEnvMon 15}           

    zxDslEnvPowerFailureEnable  OBJECT-TYPE 
        SYNTAX      INTEGER  
        { 
            enable(1),
            disable(2)
        } 
        MAX-ACCESS  read-write
        STATUS      current
        DESCRIPTION   
            "Enables and disables Trap of Power Failure."
        ::= { zxDslEnvPowerFailure 1 }        
         
      
    zxDslEnvCtrlObjects      OBJECT IDENTIFIER ::= {zxDslEnvMon 16}          
       
    zxDslEnvMonitorInterfaceUsage OBJECT-TYPE
        SYNTAX     INTEGER
        {
            epm(1),
            battery(2),
            noUse(3),
            noSupport(4),
            electricLock(5)
        }
        MAX-ACCESS  read-write
        STATUS      current
        DESCRIPTION
           "The equipment type connected to the enviroment monitor interface.
            The possible values are:
              epm(1) - connect to EPM device
              battery(2) - direct connect to battery
              noUse(3) - support enviroment monitor interface, but not use.  
              noSupport(4) - doesn't support enviroment monitor interface.
              electricLock(5) - connect to electric lock."
        DEFVAL { storageBattery }        
        ::= { zxDslEnvCtrlObjects 1 }  
        
    zxDslEnvMonitorInterfaceTrapEnable OBJECT-TYPE
        SYNTAX     INTEGER
        {
            enable(1),
            disable(2)
        }
        MAX-ACCESS  read-write
        STATUS      current
        DESCRIPTION
           "Indicates whether linkUp/linkDown traps should be
            generated for MonitorInterface."
        DEFVAL { enable }        
        ::= { zxDslEnvCtrlObjects 2 }                                                         
                           
    zxDslEnvFanAutoCtrlEnable OBJECT-TYPE
        SYNTAX     INTEGER
        {
            enable(1),
            disable(2)
        }
        MAX-ACCESS  read-write
        STATUS      current
        DESCRIPTION
           "Enable or disble the autocontrol of fan by temperature."
        DEFVAL { disable }        
        ::= { zxDslEnvCtrlObjects 3 }      
    
    zxDslEnvFanCtrlTemperatureThresh OBJECT-TYPE
        SYNTAX     Integer32
        MAX-ACCESS  read-write
        STATUS      current
        DESCRIPTION
           "The temperature threshold of fan for start-up or shut down,
            in Celsiur scale."
        ::= { zxDslEnvCtrlObjects 4 }          
        
   zxDslEnvTemperatureLowerThreshold OBJECT-TYPE
       SYNTAX       Integer32(-60..0) 
       UNITS        "centigrade"
       MAX-ACCESS   read-write
       STATUS       current
       DESCRIPTION
            "The lower threshold of the chassis temperature,the
             zxDslTempUnderThreshTrap trap should be generated when 
             zxDslEnvChassisTemperature is lower than it. 
             Otherwise,zxDslTempUnderThreshTrapCleared trap should be generated
             when zxDslEnvChassisTemperature 2 degrees higher than it."
       DEFVAL { -30 }
       ::= { zxDslEnvCtrlObjects 5 }              
     
    zxDslEnvBatteryEnergySavingEnable OBJECT-TYPE
        SYNTAX      INTEGER { enable(1), disable(2) }
        MAX-ACCESS  read-write
        STATUS      current
         DESCRIPTION
           "enable or disable energy saving for battery.
           
            if enabled, device will switch to energy saving mode when the 
            exterior power lose and battery as power supply. 
           "                           
       DEFVAL      { disable }
       ::= { zxDslEnvCtrlObjects 6 }              
    
    zxDslEnvFanFaultInfo OBJECT-TYPE
        SYNTAX      DisplayString
        MAX-ACCESS  read-only
        STATUS      current
         DESCRIPTION
           "This object indicates the failed fan list. 
            e.g., 1,3-5 means Fan 1,Fan 3,Fan 4 and Fan 5 are in failure.
           "
       ::= { zxDslEnvCtrlObjects 7 }              
       
    zxDslEnvFanTotalNumber OBJECT-TYPE
        SYNTAX      Integer32
        MAX-ACCESS  read-only
        STATUS      current
         DESCRIPTION
           "The total Number of Fans."
       ::= { zxDslEnvCtrlObjects 8 }              
       
   zxDslEnvMonitorElecLock   OBJECT IDENTIFIER ::= {zxDslEnvMon 17}  

   zxDslEnvMonitorElecLockServerTable OBJECT-TYPE
        SYNTAX SEQUENCE OF ZxDslEnvMonitorElecLockServerEntry
        MAX-ACCESS not-accessible
        STATUS     current
        DESCRIPTION
            "electric lock server table. "
        ::= { zxDslEnvMonitorElecLock 1 }

   zxDslEnvMonitorElecLockServerEntry  OBJECT-TYPE
        SYNTAX     ZxDslEnvMonitorElecLockServerEntry 
        MAX-ACCESS not-accessible
        STATUS     current
        DESCRIPTION
            "electric lock server entry"
        INDEX      { zxDslEnvMonitorElecLockServerAddress }
        ::= { zxDslEnvMonitorElecLockServerTable 1 }

    ZxDslEnvMonitorElecLockServerEntry ::= SEQUENCE {
        zxDslEnvMonitorElecLockServerAddress   InetAddress,
        zxDslEnvMonitorElecLockServerRowStatus RowStatus
    }
        
    zxDslEnvMonitorElecLockServerAddress OBJECT-TYPE
        SYNTAX     InetAddress 
        MAX-ACCESS not-accessible
        STATUS     current
        DESCRIPTION
            "The server address for electric lock monitor."
        ::= { zxDslEnvMonitorElecLockServerEntry 1 }   
    
    zxDslEnvMonitorElecLockServerRowStatus OBJECT-TYPE
        SYNTAX          RowStatus
        MAX-ACCESS      read-create
        STATUS          current
        DESCRIPTION     "rowstatus"
        ::=  {  zxDslEnvMonitorElecLockServerEntry 2 }
       
                   
--------------------------------------------------------------------------------
    zxDslVersion       OBJECT IDENTIFIER ::= {zxDslSysctrlObjects 3}
    
    zxDslVerCfgTable    OBJECT-TYPE
        SYNTAX      SEQUENCE  OF  ZxDslVerCfgEntry
        MAX-ACCESS  not-accessible
        STATUS      current
        DESCRIPTION "A table entry containing AdslVersion information  for each
        port. These variables are not in RFC2495 configuration table."
        ::=  { zxDslVersion  1 }
    
    zxDslVerCfgEntry    OBJECT-TYPE
        SYNTAX      ZxDslVerCfgEntry
        MAX-ACCESS  not-accessible
        STATUS      current
        DESCRIPTION "AdslVersion information entry"
        INDEX       {  zxDslVerTypeName  }
        ::=  { zxDslVerCfgTable 1 }
        
    ZxDslVerCfgEntry  ::=  SEQUENCE {
        zxDslVerTypeName   SnmpAdminString,
        zxDslEraseFileName         SnmpAdminString,
        zxDslActiveFileName         SnmpAdminString,
        zxDslEraseVerType   Unsigned32
        }
        
    zxDslVerTypeName      OBJECT-TYPE   
        SYNTAX          SnmpAdminString( SIZE ( 0 .. 32  ) )
        MAX-ACCESS      not-accessible
        STATUS          current
        DESCRIPTION     "
             "
        ::=  {  zxDslVerCfgEntry  1  }

    zxDslEraseFileName  OBJECT-TYPE 
        SYNTAX          SnmpAdminString( SIZE ( 0 .. 32  ) )
        MAX-ACCESS      read-write
        STATUS          current
        DESCRIPTION     "
             "
        ::=  {  zxDslVerCfgEntry  2  }
    
    zxDslActiveFileName OBJECT-TYPE 
        SYNTAX          SnmpAdminString( SIZE ( 0 .. 32  ) )
        MAX-ACCESS      read-write
        STATUS          current
        DESCRIPTION     "
             "
        ::=  {  zxDslVerCfgEntry  3  }
    
    zxDslEraseVerType   OBJECT-TYPE 
        SYNTAX          Unsigned32
        MAX-ACCESS      read-write
        STATUS          current
        DESCRIPTION     "
             "
        ::=  {  zxDslVerCfgEntry  4  }
        
        
        zxDslVersionTable   OBJECT-TYPE
        SYNTAX      SEQUENCE  OF  ZxDslVersionEntry
        MAX-ACCESS  not-accessible
        STATUS      current
        DESCRIPTION "A table entry containing AdslVersion information  for each
        port. These variables are not in RFC2495 configuration table."
        ::=  { zxDslVersion  2 }

    zxDslVersionEntry   OBJECT-TYPE
        SYNTAX      ZxDslVersionEntry
        MAX-ACCESS  not-accessible
        STATUS      current
        DESCRIPTION "AdslVersion information entry"
        INDEX       {  zxDslVerTypeName, zxDslVerFileName  }
        ::=  { zxDslVersionTable 1 }

    ZxDslVersionEntry  ::=  SEQUENCE {      
        zxDslVerFileName  OCTET STRING,
        zxDslVersionNo  OCTET STRING,
        zxDslVerType  OCTET STRING,
        zxDslVerCreateTime  OCTET STRING,
        zxDslVerDownLoadTime  OCTET STRING,
        zxDslVersionStatus  OCTET STRING,               
        zxDslVerLen  Unsigned32,               
        zxDslVersionState  OCTET STRING          
        }

    zxDslVerFileName    OBJECT-TYPE 
        SYNTAX          OCTET STRING ( SIZE ( 0 .. 64  ) )
        MAX-ACCESS      not-accessible
        STATUS          current
        DESCRIPTION     "the file name of the version "
        ::=  {  zxDslVersionEntry  1  }


    zxDslVersionNo  OBJECT-TYPE 
        SYNTAX          OCTET STRING ( SIZE ( 0 .. 16  ) )
        MAX-ACCESS      read-only
        STATUS          current
        DESCRIPTION     "the  version id"
        ::=  {  zxDslVersionEntry  2  }


    zxDslVerType    OBJECT-TYPE 
        SYNTAX          OCTET STRING ( SIZE ( 0 .. 16  ) )
        MAX-ACCESS      read-only
        STATUS          current
        DESCRIPTION     "the  version type"
        ::=  {  zxDslVersionEntry  3  }


    zxDslVerCreateTime  OBJECT-TYPE 
        SYNTAX          OCTET STRING ( SIZE ( 0 .. 16  ) )
        MAX-ACCESS      read-only
        STATUS          current
        DESCRIPTION     "the  version Create Time"
        ::=  {  zxDslVersionEntry  4  }


    zxDslVerDownLoadTime    OBJECT-TYPE 
        SYNTAX          OCTET STRING ( SIZE ( 0 .. 16  ) )
        MAX-ACCESS      read-only
        STATUS          current
        DESCRIPTION     "the  version DownLoad Time"
        ::=  {  zxDslVersionEntry  5  }


    zxDslVersionStatus  OBJECT-TYPE 
        SYNTAX          OCTET STRING
        MAX-ACCESS      read-only
        STATUS          current
        DESCRIPTION     "the  version Status"
        ::=  {  zxDslVersionEntry  6  }


    zxDslVerLen OBJECT-TYPE 
        SYNTAX          Unsigned32
        MAX-ACCESS      read-only
        STATUS          current
        DESCRIPTION     "the  version length"
        ::=  {  zxDslVersionEntry  7  }
        

    zxDslVersionState  OBJECT-TYPE 
        SYNTAX          OCTET STRING
        MAX-ACCESS      read-only
        STATUS          current
        DESCRIPTION     "the  version active state"
        ::=  {  zxDslVersionEntry  8  }
        
        
        
    zxDslPatchTable   OBJECT-TYPE
        SYNTAX      SEQUENCE  OF  ZxDslPatchEntry
        MAX-ACCESS  not-accessible
        STATUS      current
        DESCRIPTION "A table entry containing patch information."
        ::=  { zxDslVersion  3 }

    zxDslPatchEntry   OBJECT-TYPE
        SYNTAX      ZxDslPatchEntry
        MAX-ACCESS  not-accessible
        STATUS      current
        DESCRIPTION "patch information entry"
        INDEX       {  zxDslPatchName  }
        ::=  { zxDslPatchTable 1 }

    ZxDslPatchEntry  ::=  SEQUENCE {   
        zxDslPatchName           OCTET STRING,
        zxDslPatchSystemVersion  OCTET STRING,  
        zxDslPatchVersionNo      OCTET STRING,        
        zxDslPatchSize           Unsigned32,    
        zxDslPatchStatus         OCTET STRING,     
        zxDslPatchCreateTime     OCTET STRING,
        zxDslPatchActiveTime    OCTET STRING,
        zxDslPatchRunningTime        OCTET STRING,          
        zxDslPatchDesc           OCTET STRING,
        zxDslPatchAdminStatus    INTEGER                   
        }

    zxDslPatchName      OBJECT-TYPE 
        SYNTAX          OCTET STRING ( SIZE ( 0 .. 64  ) )
        MAX-ACCESS      not-accessible
        STATUS          current
        DESCRIPTION     "the file name of the patch "
        ::=  {  zxDslPatchEntry  1  }

    zxDslPatchSystemVersion  OBJECT-TYPE 
        SYNTAX          OCTET STRING ( SIZE ( 0 .. 32  ) )
        MAX-ACCESS      read-only
        STATUS          current
        DESCRIPTION     "the system version of the patch"
        ::=  {  zxDslPatchEntry  2  }
        
    zxDslPatchVersionNo  OBJECT-TYPE 
        SYNTAX          OCTET STRING ( SIZE ( 0 .. 32  ) )
        MAX-ACCESS      read-only
        STATUS          current
        DESCRIPTION     "the version no of the patch"
        ::=  {  zxDslPatchEntry  3  }

    zxDslPatchSize OBJECT-TYPE 
        SYNTAX          Unsigned32
        MAX-ACCESS      read-only
        STATUS          current
        DESCRIPTION     "the  version length of the patch"
        ::=  {  zxDslPatchEntry  4  }
        
    zxDslPatchStatus  OBJECT-TYPE 
        SYNTAX          OCTET STRING ( SIZE ( 0 .. 32  ) )
        MAX-ACCESS      read-only
        STATUS          current
        DESCRIPTION     "the status of the patch, such as activated, deactivated and autorun"
        ::=  {  zxDslPatchEntry  5  }
        
    zxDslPatchCreateTime  OBJECT-TYPE 
        SYNTAX          OCTET STRING ( SIZE ( 0 .. 16  ) )
        MAX-ACCESS      read-only
        STATUS          current
        DESCRIPTION     "the patch create time"
        ::=  {  zxDslPatchEntry  6  }
        
    zxDslPatchActiveTime  OBJECT-TYPE 
        SYNTAX          OCTET STRING ( SIZE ( 0 .. 16  ) )
        MAX-ACCESS      read-only
        STATUS          current
        DESCRIPTION     "the patch active time"        
        ::=  {  zxDslPatchEntry  7  }
        
    zxDslPatchRunningTime  OBJECT-TYPE 
        SYNTAX          OCTET STRING ( SIZE ( 0 .. 16  ) )
        MAX-ACCESS      read-only
        STATUS          current
        DESCRIPTION     "the running time of the patch"
        ::=  {  zxDslPatchEntry  8  }
    
    zxDslPatchDesc  OBJECT-TYPE 
        SYNTAX          OCTET STRING ( SIZE ( 0 .. 64  ) )
        MAX-ACCESS      read-only
        STATUS          current
        DESCRIPTION     "the patch description"
        ::=  {  zxDslPatchEntry  9  }
        
    zxDslPatchAdminStatus  OBJECT-TYPE 
        SYNTAX          INTEGER  { active ( 1 ) , save ( 2 ), deactive ( 3 ),  delete( 4 ) } 
        MAX-ACCESS      read-write
        STATUS          current
        DESCRIPTION     "config the status of patch"
        ::=  {  zxDslPatchEntry  10  }
        
--------------------------------------------------------------------------------        
    zxDslCommon       OBJECT IDENTIFIER ::= {zxDslSysctrlObjects 4}
        
        zxDslCliPrompt      OBJECT-TYPE 
        SYNTAX          OCTET STRING  ( SIZE ( 0 .. 16  ) ) 
        MAX-ACCESS      read-write
        STATUS          current
        DESCRIPTION     "prompt name of the zxDsl. (ex. fasp#)"
        ::=  {  zxDslCommon  1  }
    
    zxDslLineTestRootMode   OBJECT-TYPE 
        SYNTAX          INTEGER  { rootMode ( 1 ) , notRootMode ( 2 ) } 
        MAX-ACCESS      read-write
        STATUS          current
        DESCRIPTION     "A flag is to indicate whether the MasterToSLave transfering is going on."
        ::=  {  zxDslCommon  2  }   

    zxDslEPMConfType    OBJECT-TYPE 
        SYNTAX          INTEGER  { csv ( 0 ) , epm ( 1 ) } 
        MAX-ACCESS      read-write
        STATUS          current
        DESCRIPTION     "the EPM config type."
        ::=  {  zxDslCommon  3  }
    
    zxDslSaveToNvm  OBJECT-TYPE 
        SYNTAX          Integer32
        MAX-ACCESS      read-write
        STATUS          current
        DESCRIPTION     ""
        REFERENCE       ""
        DEFVAL          { 0 }
        ::=  {  zxDslCommon  4  }
    
    zxDslEraseNvm   OBJECT-TYPE 
        SYNTAX          Integer32  ( -2147483648 .. 2147483647  ) 
        MAX-ACCESS      read-write
        STATUS          current
        DEFVAL          { 0 }
        ::=  {  zxDslCommon  5  }

    zxDslSwapCore   OBJECT-TYPE 
        SYNTAX          INTEGER  { switch ( 1 ) } 
        MAX-ACCESS      read-write
        STATUS          current
        DESCRIPTION     "The flag that master to slave."
        ::=  {  zxDslCommon  6  }       
    
    zxDslBorrowBoardSet OBJECT-TYPE 
        SYNTAX          INTEGER  { default ( 1 ) , slot10 ( 10 ) , slot12 ( 12 ) } 
        MAX-ACCESS      read-write
        STATUS          current
        DESCRIPTION     "The borrow board type."
        ::=  {  zxDslCommon  7  }

    zxDslBorrowBoardGet OBJECT-TYPE 
        SYNTAX          INTEGER  { default ( 1 ) , slot10 ( 10 ) , slot12 ( 12 ) } 
        MAX-ACCESS      read-only
        STATUS          current
        DESCRIPTION     "The actual borrow board type"
        ::=  {  zxDslCommon  8  }

    zxDslSysDateTime    OBJECT-TYPE 
        SYNTAX          OCTET STRING  ( SIZE ( 0 .. 20  ) ) 
        MAX-ACCESS      read-write
        STATUS          current
        DESCRIPTION     "yyyy-mm-dd HH:MM:SS.For example(2001-01-01 02:22:33)."
        ::=  {  zxDslCommon  9  }


    zxDslTimeZoneOffset       OBJECT-TYPE 
        SYNTAX          Integer32(-12..12)
        MAX-ACCESS      read-write
        STATUS          current
        DESCRIPTION     "Time zone offset.
           The zone offset can be 0 for GMT or it can be a value '+' or '-' 
        from GMT. 
        "
        ::=  {  zxDslCommon  10  }


    zxDslIsHalfTimeZone  OBJECT-TYPE 
        SYNTAX          TruthValue
        MAX-ACCESS      read-write
        STATUS          current
        DESCRIPTION     "Whether it is a half zone.If it is true(1),the local 
            time should be plused 0.5 hours."
        ::=  {  zxDslCommon  11  }
   
   
   
    zxDslSystemReboot   OBJECT-TYPE 
        SYNTAX          Integer32
        MAX-ACCESS      read-write
        STATUS          current
        DESCRIPTION     "Server as reboot system."
        ::=  {  zxDslCommon  12  }
        
    zxDslSystemPortList OBJECT-TYPE 
        SYNTAX          PortList
        MAX-ACCESS      read-write
        STATUS          current
        DESCRIPTION     "Server as port batch configuring."
        ::=  {  zxDslCommon  13  }

    zxDslAutoSaveToNvmInterval  OBJECT-TYPE 
        SYNTAX          Integer32(0..168)
        UNITS           "hours" 
        MAX-ACCESS      read-write
        STATUS          deprecated
        DESCRIPTION     "The interval to save running configuration of agent to 
                    flash media automatically.
                         The value 0 means disable the auto save flash operation."
        DEFVAL          { 0 }
        ::=  {  zxDslCommon  14  }        

    zxDslTimingSaveModifiedToNvmInterval  OBJECT-TYPE
        SYNTAX          Integer32(0..1440)
        UNITS           "minutes" 
        MAX-ACCESS      read-write
        STATUS          current
        DESCRIPTION     "The interval to save flash if running configuration of 
                         agent modified, value 0 means disable the auto save flash
                         operation."
        DEFVAL          { 0 }
        ::=  {  zxDslCommon  15  }
        
    zxDslTimingSaveToNvmInterval  OBJECT-TYPE 
        SYNTAX          Integer32(0..8760)
        UNITS           "hours" 
        MAX-ACCESS      read-write
        STATUS          current
        DESCRIPTION     "The interval to force saving flash , value 0 means disable 
                         the force save saving operation."
        DEFVAL          { 0 }
        ::=  {  zxDslCommon  16  }
        
    zxDslUserSideMtu  OBJECT-TYPE 
        SYNTAX          Integer32(64..2047)
        UNITS           "byte" 
        MAX-ACCESS      read-write
        STATUS          current
        DESCRIPTION     "The user side maximum transmission unit, 
                         the packge from user side will be discard 
                         while it exceed this limit."
        DEFVAL          { 1700 }
        ::=  {  zxDslCommon  17  }
        
    zxDslSysMaxPortNumPerSlot  OBJECT-TYPE 
        SYNTAX          Integer32
        MAX-ACCESS      read-only
        STATUS          current
        DESCRIPTION     "The max port number per slot of the device.
                         This number is used to compute the ifIndex."
        ::=  {  zxDslCommon  18  }
        
    zxDslSysOutbandPortUsage OBJECT-TYPE 
        SYNTAX         INTEGER
            {
                outbandPort(1),
                cascadePort(2)
            }
        MAX-ACCESS     read-write
        STATUS         current
        DESCRIPTION     
            "The usage of outband port.
             outbandPort(1) - Switch the port usage to outband port.
             cascadePort(2) - Switch the port usage to cascade port.
            "
        DEFVAL {  outbandPort  }
        ::=  {  zxDslCommon  19  }
    
    zxDslPerfStatTable  OBJECT-TYPE
        SYNTAX      SEQUENCE  OF  ZxDslPerfStatEntry
        MAX-ACCESS  not-accessible
        STATUS      current
        DESCRIPTION "This table provides one row for each adsl interface.
          Each row contains the perf statistic parameters for this adsl line"
        ::=  { zxDslCommon  30 }

    zxDslPerfStatEntry  OBJECT-TYPE
        SYNTAX      ZxDslPerfStatEntry
        MAX-ACCESS  not-accessible
        STATUS      current
        DESCRIPTION "An entry containing additional performance management information
               applicable to a adsl line interface."
        INDEX       {  ifIndex  }
        ::=  { zxDslPerfStatTable 1 }

    ZxDslPerfStatEntry  ::=  SEQUENCE {
        zxDslPerfStatType       INTEGER,
        zxDslPerfStatTableList  BITS,
        zxDslPerfStatAction     INTEGER       
        }
    
    zxDslPerfStatType   OBJECT-TYPE 
        SYNTAX          INTEGER  
                        { 
                            adsl (1),
                            shdsl(2),
                            vdsl (3),
                            etherlike(4)
                        } 
        MAX-ACCESS      read-write
        STATUS          current
        DESCRIPTION     
                "The type of performance metrics to be updated."
        ::=  {  zxDslPerfStatEntry  1  }


    zxDslPerfStatTableList  OBJECT-TYPE 
        SYNTAX          BITS 
        MAX-ACCESS      read-write
        STATUS          current
        DESCRIPTION     "bitmap for perf statistic object table"
        ::=  {  zxDslPerfStatEntry  2  }


    zxDslPerfStatAction OBJECT-TYPE 
        SYNTAX          INTEGER  { actOnPort ( 1 ) , noop ( 2 ) , actOnBoard ( 3 ) } 
        MAX-ACCESS      read-write
        STATUS          current
        DESCRIPTION     "bitmap for perf statistic object table"
        ::=  {  zxDslPerfStatEntry  3  }


    zxDslUserTable  OBJECT-TYPE
        SYNTAX      SEQUENCE  OF  ZxDslUserEntry
        MAX-ACCESS  not-accessible
        STATUS      current
        DESCRIPTION "A table contain user information for web and console and telnet.."
        ::=  { zxDslCommon  31 }

    zxDslUserEntry  OBJECT-TYPE
        SYNTAX      ZxDslUserEntry
        MAX-ACCESS  not-accessible
        STATUS      current
        DESCRIPTION "A list of user information."
        INDEX       {  zxDslUserIndex  }
        ::=  { zxDslUserTable 1 }

    ZxDslUserEntry  ::=  SEQUENCE {
        zxDslUserIndex      Integer32,
        zxDslUserName       DisplayString,
        zxDslUserPwd        DisplayString,
        zxDslUserAccess     Integer32,
        zxDslUserRowStatus  INTEGER
        }


    zxDslUserIndex  OBJECT-TYPE 
        SYNTAX          Integer32  ( 1 .. 8  ) 
        MAX-ACCESS      not-accessible
        STATUS          current
        DESCRIPTION     "A simple index into 'TmsCommonMiscUserTable'."
        ::=  {  zxDslUserEntry  1  }


    zxDslUserName   OBJECT-TYPE 
        SYNTAX          DisplayString  ( SIZE ( 0 .. 15  ) ) 
        MAX-ACCESS      read-write
        STATUS          current
        DESCRIPTION     "A simple index into 'TmsCommonMiscUserTable'."
        ::=  {  zxDslUserEntry  2  }


    zxDslUserPwd    OBJECT-TYPE 
        SYNTAX          DisplayString  ( SIZE ( 0 .. 32  ) ) 
        MAX-ACCESS      read-write
        STATUS          current
        DESCRIPTION     "A simple index into 'TmsCommonMiscUserTable'."
        ::=  {  zxDslUserEntry  3  }


    zxDslUserAccess OBJECT-TYPE 
        SYNTAX          Integer32  ( 1 .. 10  ) 
        MAX-ACCESS      read-write
        STATUS          current
        DESCRIPTION     "the user access in this row."
        ::=  {  zxDslUserEntry  4  }


    zxDslUserRowStatus  OBJECT-TYPE 
        SYNTAX          INTEGER  { valid ( 1 ) , invalid ( 2 ) } 
        MAX-ACCESS      read-write
        STATUS          current
        DESCRIPTION     "the user state in this row."
        ::=  {  zxDslUserEntry  5  }
        
    
    zxDslTrapHostTable  OBJECT-TYPE
        SYNTAX      SEQUENCE  OF  ZxDslTrapHostEntry
        MAX-ACCESS  not-accessible
        STATUS      current
        DESCRIPTION "This table, which provides Trap target."
        ::=  { zxDslCommon  33 }

    zxDslTrapHostEntry  OBJECT-TYPE
        SYNTAX      ZxDslTrapHostEntry
        MAX-ACCESS  not-accessible
        STATUS      current
        DESCRIPTION ""
        INDEX       {  zxDslTrapHostIpAddr  }
        ::=  { zxDslTrapHostTable 1 }

    ZxDslTrapHostEntry  ::=  SEQUENCE {
        zxDslTrapHostIpAddr  IpAddress,
        zxDslTrapHostSnmpVer  Integer32,
        zxDslTrapHostCommunity  DisplayString,
        zxDslTrapHostIsZteNmsSever  TruthValue,
        zxDslTrapHostRowStatus  RowStatus,
        
        zxDslTrapHostEventType      BITS,
        zxDslTrapHostMinEventLevel  INTEGER
        }


    zxDslTrapHostIpAddr OBJECT-TYPE 
        SYNTAX          IpAddress
        MAX-ACCESS      not-accessible
        STATUS          current
        DESCRIPTION     ""
        ::=  {  zxDslTrapHostEntry  1  }


    zxDslTrapHostSnmpVer    OBJECT-TYPE 
        SYNTAX          Integer32  ( 0 .. 1  ) 
        MAX-ACCESS      read-create
        STATUS          current
        DESCRIPTION     ""
        ::=  {  zxDslTrapHostEntry  2  }

    zxDslTrapHostCommunity  OBJECT-TYPE 
        SYNTAX          DisplayString  ( SIZE ( 0 .. 64  ) ) 
        MAX-ACCESS      read-create
        STATUS          current
        DESCRIPTION     ""
        ::=  {  zxDslTrapHostEntry  3  }


    zxDslTrapHostIsZteNmsSever  OBJECT-TYPE
        SYNTAX  TruthValue 
        MAX-ACCESS read-create
        STATUS current
        DESCRIPTION
            "If or not it is a zte's nms.
            true(1): it is a zte's nms;
            false(2): it is not a zte's nms.
            "
        ::= { zxDslTrapHostEntry 4  }

    zxDslTrapHostRowStatus  OBJECT-TYPE 
        SYNTAX          RowStatus
        MAX-ACCESS      read-create
        STATUS          current
        DESCRIPTION     ""
        ::=  {  zxDslTrapHostEntry  5  }        
        
        
    zxDslTrapHostEventType  OBJECT-TYPE
        SYNTAX BITS {
                     equipmentEvent(0),
                     qualityOfServiceEvent(1),
                     communicationsEvent(2),
                     environmentEvent(3),
                     processingErrorEvent(4)
                    }
        MAX-ACCESS read-create
        STATUS current
        DESCRIPTION
            "The event type that a receiver expects.
             
            The event type are defined in ITU-T X.733.
            
            -  equipment event type: 
                An event of this type is principally 
            associated with an equipment fault;
             
            -  quality of service event type: 
                An event of this type is
             principally associated with a degradation in the quality of a 
             service;
             
            -  communications event type: 
                An event of this type is principally
             associated with the procedures and/or processes required to convey 
             information from one point to another;
            
            -  environmental event type:
                An event of this type is principally 
            associated with a condition relating to an enclosure in which the 
            equipment resides.

            -  processing error event type: 
                An event of this type is 
            principally associated with a software or processing fault;
            "
        DEFVAL { { equipmentEvent,qualityOfServiceEvent,communicationsEvent,
                environmentEvent,processingErrorEvent  } }
        ::= { zxDslTrapHostEntry 6 }

    zxDslTrapHostMinEventLevel  OBJECT-TYPE
        SYNTAX INTEGER {
                     cleared(0),
                     critical(1),
                     major(2),
                     minor(3),
                     warning(4),
                     notification(5)
                    }
        MAX-ACCESS read-create
        STATUS current
        DESCRIPTION
            "The min event level that a receiver expects.If the actual event 
            level is more serious than this value,the event will be sent to 
            Event Receiver. For example,if this value is warning(4),all the 
            events that the level in cleared(0),critical(1),major(2),minor(3),
            warning(4) will be sent,but notification(5) will not be sent.
            
            The event levels are defined in ITU-T X.733.            
            
           -   cleared: The Cleared severity level indicates the clearing of 
            one or more previously reported alarms. This alarm clears all 
            alarms for this managed object that have the same Alarm type,
            Probable cause and Specific problems (if given).  
            Multiple associated notifications may be cleared by using 
            the Correlated notifications parameter (defined below).
            This Recommendation | International Standard does not require that
            the clearing of previously reported alarms be reported.  
            Therefore, a managing system cannot assume that the absence of
            an alarm with the Cleared severity level means that the condition
            that caused the generation of previous alarms is still present.  
               Managed object definers shall state if, and under which 
            conditions, the Cleared severity level is used.
            
           -  critical: The Critical severity level indicates that a service 
             affecting condition has occurred and an immediate corrective action
             is required.  Such a severity can be reported, for example, when 
             a managed object becomes totally out of service and its capability 
             must be restored. 
             
           -   major: The Major severity level indicates that a service 
            affecting condition has developed and an urgent corrective action 
            is required.  Such a severity can be reported, for example, when 
            there is a severe degradation in the capability of the managed 
            object and its full capability must be restored. 
            
           -   minor: The Minor severity level indicates the existence of 
            a non-service affecting fault condition and that corrective action 
            should be taken in order to prevent a more serious (for example, 
            service affecting) fault. Such a severity can be reported, 
            for example, when the detected alarm condition is not currently 
            degrading the capacity of the managed object. 
                        
           -   warning: The Warning severity level indicates the detection of 
            a potential or impending service affecting fault, before any 
            significant effects have been felt. Action should be taken to 
            further diagnose (if necessary) and correct the problem in order 
            to prevent it from becoming a more serious service affecting fault.               

            -  notification: The notification severity level indicates that 
            only a infomation to be report and it is either a fault or 
            a potential fault. 

            "
        DEFVAL { notification }
        ::= { zxDslTrapHostEntry 7 }
            
        

----
        zxDslSysIfCtrlTable OBJECT-TYPE
        SYNTAX      SEQUENCE  OF  ZxDslSysIfCtrlEntry
        MAX-ACCESS  not-accessible
        STATUS      current
        DESCRIPTION "An (conceptual) table listing  of zxDsl system interface extend attribute."
        ::=  { zxDslCommon  34 }

    zxDslSysIfCtrlEntry OBJECT-TYPE
        SYNTAX      ZxDslSysIfCtrlEntry
        MAX-ACCESS  not-accessible
        STATUS      current
        DESCRIPTION "An entry (conceptual) table listing  of zxDsl system interface extend attribute."
        INDEX       {  ifIndex  }
        ::=  { zxDslSysIfCtrlTable 1 }

    ZxDslSysIfCtrlEntry  ::=  SEQUENCE {
        zxDslSysIfTrapCtrl  PortList,
        zxDslSysIfType      Integer32
        }
    
    
    zxDslSysIfTrapCtrl  OBJECT-TYPE 
        SYNTAX          PortList
        MAX-ACCESS      read-write
        STATUS          current
        DESCRIPTION     "port trap control."
        ::=  {  zxDslSysIfCtrlEntry  1  }
    
    zxDslSysIfType  OBJECT-TYPE 
        SYNTAX          Integer32
        MAX-ACCESS      read-write
        STATUS          current
        DESCRIPTION     "If type ."
        ::=  {  zxDslSysIfCtrlEntry  2  }
        
--------------------------------------------------------------------------------
        
        zxDslCluster    OBJECT IDENTIFIER
        ::=  {  zxDslSysctrlObjects  5  }
        zxDslStackModuleId  OBJECT-TYPE 
        SYNTAX          Integer32  ( 1 .. 24  ) 
        MAX-ACCESS      read-write
        STATUS          current
        DESCRIPTION     "moduleId of this ZXDSL in this stack system."
        ::=  {  zxDslCluster  1  }

    zxDslStackModuleNum OBJECT-TYPE 
        SYNTAX          Integer32  ( 1 .. 24  ) 
        MAX-ACCESS      read-write
        STATUS          current
        DESCRIPTION     "moduleNum of this ZXDSL in this stack system."
        ::=  {  zxDslCluster  2  }

    zxDslStackModuleRole    OBJECT-TYPE 
        SYNTAX          INTEGER  { master ( 1 ) , slave ( 2 ) } 
        MAX-ACCESS      read-write
        STATUS          current
        DESCRIPTION     "role of this ZXDSL in this stack system."
        ::=  {  zxDslCluster  3  }

    zxDslStackTable OBJECT-TYPE
        SYNTAX      SEQUENCE  OF  ZxDslStackEntry
        MAX-ACCESS  not-accessible
        STATUS      current
        DESCRIPTION "The (conceptual) table listing  of zxDsl system stack."
        ::=  { zxDslCluster  4 }

    zxDslStackEntry OBJECT-TYPE
        SYNTAX      ZxDslStackEntry
        MAX-ACCESS  not-accessible
        STATUS      current
        DESCRIPTION "An entry (conceptual) table listing  of zxDsl system stack."
        INDEX       {  zxDslStackIndex  }
        ::=  { zxDslStackTable 1 }

    ZxDslStackEntry  ::=  SEQUENCE {
        zxDslStackIndex  Integer32,
        zxDslStackIpAddr  IpAddress,
        zxDslStackRowStatus  RowStatus
        }


    zxDslStackIndex OBJECT-TYPE 
        SYNTAX          Integer32  ( 1 .. 24  ) 
        MAX-ACCESS      not-accessible
        STATUS          current
        DESCRIPTION     "stackid of zxDsl system."
        ::=  {  zxDslStackEntry  1  }


    zxDslStackIpAddr    OBJECT-TYPE 
        SYNTAX          IpAddress
        MAX-ACCESS      read-create
        STATUS          current
        DESCRIPTION     "stack ip address of zxDsl system."
        ::=  {  zxDslStackEntry  2  }


    zxDslStackRowStatus OBJECT-TYPE 
        SYNTAX          RowStatus  { active ( 1 ) , notInService ( 2 ) , 
        notReady ( 3 ) , createAndGo ( 4 ) , createAndWait ( 5 ) , 
        destroy ( 6 ) } 
        MAX-ACCESS      read-create
        STATUS          current
        DESCRIPTION     "This object indicates the status of this entry."
        ::=  {  zxDslStackEntry  3  }

    

--------------------------------------------------------------------------------
        
        zxDslFtp    OBJECT IDENTIFIER   
        ::=  {  zxDslSysctrlObjects  7  }
        
    zxDslFtpManagedObjectType   OBJECT-TYPE 
        SYNTAX          DisplayString  ( SIZE ( 1 .. 16  ) )
        MAX-ACCESS      read-write
        STATUS          current
        DESCRIPTION     "
             Operation type, related with following operations.
             port config file:PORT_INFO,DSL_PORT_INFO
             startup config file:STARTUP_CONFIG
             running config file:RUNNING_CONFIG
             version download:COREI, COREF, PCSA, COREF2, WANB1, WANB, WANAB, 
                              STUCA, LTC, ATUGA, IMAA, ATUGI, IMAB, ATUGB, 
                              VTUCA, STUDB, gplus, gdmt, g2p512k, g2p1M, 
                              ISUGB4, APPARM, SCCE, SCCH
             patch download:PATCH
             Localization file download(console and telnet): LOCAL_FILE             
             module config file:MODULE_FILE
             "
        ::=  {  zxDslFtp  1  }

    zxDslFtpAddress OBJECT-TYPE 
        SYNTAX          IpAddress
        MAX-ACCESS      read-write
        STATUS          current
        DESCRIPTION     "
             The IP Address for the FTP server used for downloading
             and/or uploading files."
        ::=  {  zxDslFtp  2  }

    zxDslFtpUserName    OBJECT-TYPE 
        SYNTAX          DisplayString  ( SIZE ( 1 .. 64  ) ) 
        MAX-ACCESS      read-write
        STATUS          current
        DESCRIPTION     "The FTP username."
        ::=  {  zxDslFtp  3  }

    zxDslFtpUserPwd OBJECT-TYPE 
        SYNTAX          DisplayString  ( SIZE ( 1 .. 64  ) ) 
        MAX-ACCESS      read-write
        STATUS          current
        DESCRIPTION     "
             The FTP User Password."
        ::=  {  zxDslFtp  4  }

    zxDslFtpFilePath    OBJECT-TYPE 
        SYNTAX          DisplayString  ( SIZE ( 1 .. 64  ) ) 
        MAX-ACCESS      read-write
        STATUS          current
        DESCRIPTION     "
             The FTP File Path, start from the root directory."
        ::=  {  zxDslFtp  5  }

    zxDslFtpFileName    OBJECT-TYPE 
        SYNTAX          DisplayString  ( SIZE ( 1 .. 64  ) ) 
        MAX-ACCESS      read-write
        STATUS          current
        DESCRIPTION     "
             The FTP file path and name."
        ::=  {  zxDslFtp  6  }

    zxDslFtpLoadType    OBJECT-TYPE 
        SYNTAX          INTEGER  { upload ( 1 ) , download ( 2 ) ,
        versionDownloadAndOverwriteExisting ( 3 ) } 
        MAX-ACCESS      read-write
        STATUS          current
        DESCRIPTION     " Ftp load type."
        ::=  {  zxDslFtp  7  }

    zxDslDownloadStatus OBJECT-TYPE 
        SYNTAX          INTEGER  { notstarted ( 1 ) , inprogress ( 2 ) , success ( 3 ) , masterfailed ( 4 ) , slavefailed ( 5 ) , allfailed ( 6 ) } 
        MAX-ACCESS      read-only
        STATUS          current
        DESCRIPTION     " Ftp operation status."
        ::=  {  zxDslFtp  8  }
        
    zxDslFtpAddressType OBJECT-TYPE
        SYNTAX      InetAddressType
        MAX-ACCESS  read-write
        STATUS      current
        DESCRIPTION
            "The type of IP Address for FTP server."
        DEFVAL { 1 } 
        ::= {   zxDslFtp  9   } 
        
    zxDslFtpIpv6Address OBJECT-TYPE
        SYNTAX      InetAddress
        MAX-ACCESS  read-write
        STATUS      current
        DESCRIPTION
            "The IPv6 Ip Address for FTP server."
        ::= {   zxDslFtp  10   }

    zxDslFtpProtocolType  OBJECT-TYPE     
        SYNTAX     INTEGER 
        {
            ftp(1),
            sftp(2)
        } 
        MAX-ACCESS read-write
        STATUS     current
        DESCRIPTION     
            "zxDslFtpProtocolType is used to indicate the ftp protocol.
             It includes two protocols: one is ftp and the other is sftp."
        DEFVAL { ftp }
        ::= {   zxDslFtp  11   }    

--------------------------------------------------------------------------------
        zxDslAddress    OBJECT IDENTIFIER   
        ::=  {  zxDslSysctrlObjects  8  }   

    zxDslOutBandIpAddress   OBJECT-TYPE 
        SYNTAX          IpAddress
        MAX-ACCESS      read-write
        STATUS          current
        DESCRIPTION     "
             "
        ::=  {  zxDslAddress  1  }

    zxDslOutBandIpMask  OBJECT-TYPE 
        SYNTAX          IpAddress
        MAX-ACCESS      read-write
        STATUS          current
        DESCRIPTION     "
             "
        ::=  {  zxDslAddress  2  }

    zxDslOutBandMACAddress  OBJECT-TYPE 
        SYNTAX          MacAddress
        MAX-ACCESS      read-write
        STATUS          current
        DESCRIPTION     "
             "
        ::=  {  zxDslAddress  3  }

    zxDslInBandMACAddress   OBJECT-TYPE 
        SYNTAX          MacAddress
        MAX-ACCESS      read-write
        STATUS          current
        DESCRIPTION     "
             "
        ::=  {  zxDslAddress  4  }

    zxDslInBandTable    OBJECT-TYPE
        SYNTAX      SEQUENCE  OF  ZxDslInBandEntry
        MAX-ACCESS  not-accessible
        STATUS      current
        DESCRIPTION "A table of subnet parameters.  There is one entry
             available for each of the 'tmsL3InBandMaxRows'
             supported IP subnets."
        ::=  { zxDslAddress  5 }

    zxDslInBandEntry    OBJECT-TYPE
        SYNTAX      ZxDslInBandEntry
        MAX-ACCESS  not-accessible
        STATUS      current
        DESCRIPTION "A list of subnet parameters."
        INDEX       {  zxDslInBandIpAddr  }
        ::=  { zxDslInBandTable 1 }

    ZxDslInBandEntry  ::=  SEQUENCE {
        zxDslInBandIpAddr  IpAddress,
        zxDslInBandIpMask  IpAddress,
        zxDslInBandIpVid  Integer32,
        zxDslInBandIpName  DisplayString,
        zxDslInBandIpUseType  INTEGER,
        zxDslInBandIpRowStatus  RowStatus
        }


    zxDslInBandIpAddr   OBJECT-TYPE 
        SYNTAX          IpAddress
        MAX-ACCESS      not-accessible
        STATUS          current
        DESCRIPTION     "DURABLE:
             The network management station uses this IP Address to talk
             with the Agent on this subnet.  This IP address logically
             AND'ed with 'tmsL3InBandMask' yields the actual subnet
             value for this subnet."
        ::=  {  zxDslInBandEntry  1  }


    zxDslInBandIpMask   OBJECT-TYPE 
        SYNTAX          IpAddress
        MAX-ACCESS      read-create
        STATUS          current
        DESCRIPTION     "DURABLE:
             The subnet mask for this subnet.  It contains 1's in the
             bit positions for the net and subnet IDs and 0's in the
             bit positions for host ID.  The 1's must be contiguous,
             starting with the left most bit."
        ::=  {  zxDslInBandEntry  2  }


    zxDslInBandIpVid    OBJECT-TYPE 
        SYNTAX          Integer32  ( 0 .. 4094  ) 
        MAX-ACCESS      read-create
        STATUS          current
        DESCRIPTION     "DURABLE: { default=0:all }
             For a L2/L3 hybrid switch, this object contains the actual
             VLAN ID (VID) from 1 to 4094 or 0 if the VID is unassigned.
             For a L3 only switch, this object contains the actual switch
             interface from 1 to 4094 or 0 if unassigned.
             
             Changing this object for this row causes all rows with the same
             'tmsL3InBandIfIndex' as this row to be changed to this new
             'tmsL3InBandVidIface' value."
        ::=  {  zxDslInBandEntry  3  }


    zxDslInBandIpName   OBJECT-TYPE 
        SYNTAX          DisplayString  ( SIZE ( 0 .. 16  ) ) 
        MAX-ACCESS      read-create
        STATUS          current
        DESCRIPTION     "DURABLE:  { '':all )
             A user reference name for this subnet."
        ::=  {  zxDslInBandEntry  4  }
    
    zxDslInBandIpUseType    OBJECT-TYPE 
        SYNTAX         INTEGER  
            {
                normal(1),
                modem(2),
                voip(3),
                media(4),
                normalSecondary(5),
                layer3(6),
                ieee1588(7),
                serialPort(8)
            } 
        MAX-ACCESS      read-create
        STATUS          current
        DESCRIPTION     
            "Inband IP address type.
             normal         (1) - Inband IP address;
             modem          (2) - Modem management;
             voip           (3) - VoIP subnet IP address;
             media          (4) - VoIP media subnet IP address;
             normalSecondary(5) - Secondary inband IP address;
             layer3         (6) - Layer3 interface IP address;
             ieee1588       (7) - IEEE 1588 IP address, just used by F829;
             serialPort     (8) - Serial port IP address, just used by F809;
            "
        ::=  {  zxDslInBandEntry  5  }


    zxDslInBandIpRowStatus  OBJECT-TYPE 
        SYNTAX          RowStatus
        MAX-ACCESS      read-create
        STATUS          current
        DESCRIPTION     "DURABLE:
             This object indicates the status of this entry.  A row in this
             table must be created using the createAndWait(5) action state
             (i.e., createAndGo(4) is not supported).  This object can only
             be set to active(1) after all objects for this row are valid.
             The 'tmsL3InBandName' is optional.
             
             Note that the notInService(2) state is not supported.  Objects
             in this table row can be changed when this object is notReady(3)
             or active(1)."
        ::=  {  zxDslInBandEntry  6  }
        
            
        
--------------------------------------------------------------------------------
        zxDslIpv6Objects    OBJECT IDENTIFIER   
        ::=  {  zxDslSysctrlObjects  14  }       

    zxDslIpv6InBandTable    OBJECT-TYPE
        SYNTAX      SEQUENCE  OF  ZxDslIpv6InBandEntry
        MAX-ACCESS  not-accessible
        STATUS      current
        DESCRIPTION "A table of subnet parameters.  There is one entry
             available for each of the 'tmsL3InBandMaxRows'
             supported IP subnets."
        ::=  { zxDslIpv6Objects  1 }

    zxDslIpv6InBandEntry    OBJECT-TYPE
        SYNTAX      ZxDslIpv6InBandEntry
        MAX-ACCESS  not-accessible
        STATUS      current
        DESCRIPTION "A list of subnet parameters."
        INDEX       {  zxDslIpv6InBandInetAddress  }
        ::=  { zxDslIpv6InBandTable 1 }

    ZxDslIpv6InBandEntry  ::=  SEQUENCE {
        zxDslIpv6InBandInetAddress              InetAddress,
        zxDslIpv6InBandInetAddressPrefixLength  InetAddressPrefixLength,
        zxDslIpv6InBandIpVid                    Integer32,
        zxDslIpv6InBandIpName                   DisplayString,
        zxDslIpv6InBandIpUseType                INTEGER,
        zxDslIpv6InBandIpRowStatus              RowStatus
        }


    zxDslIpv6InBandInetAddress   OBJECT-TYPE 
        SYNTAX          InetAddress
        MAX-ACCESS      not-accessible
        STATUS          current
        DESCRIPTION     "DURABLE:
             The network management station uses this IP Address to talk
             with the Agent on this subnet.  This IP address logically
             AND'ed with 'tmsL3InBandMask' yields the actual subnet
             value for this subnet."
        ::=  {  zxDslIpv6InBandEntry  1  }


    zxDslIpv6InBandInetAddressPrefixLength   OBJECT-TYPE 
        SYNTAX          InetAddressPrefixLength
        MAX-ACCESS      read-create
        STATUS          current
        DESCRIPTION     "the prefix length of inband inet address."
        ::=  {  zxDslIpv6InBandEntry  2  }


    zxDslIpv6InBandIpVid    OBJECT-TYPE 
        SYNTAX          Integer32  ( 0 .. 4094  ) 
        MAX-ACCESS      read-create
        STATUS          current
        DESCRIPTION     "DURABLE: { default=0:all }
             For a L2/L3 hybrid switch, this object contains the actual
             VLAN ID (VID) from 1 to 4094 or 0 if the VID is unassigned.
             For a L3 only switch, this object contains the actual switch
             interface from 1 to 4094 or 0 if unassigned.
             
             Changing this object for this row causes all rows with the same
             'tmsL3InBandIfIndex' as this row to be changed to this new
             'tmsL3InBandVidIface' value."
        ::=  {  zxDslIpv6InBandEntry  3  }


    zxDslIpv6InBandIpName   OBJECT-TYPE 
        SYNTAX          DisplayString  ( SIZE ( 0 .. 16  ) ) 
        MAX-ACCESS      read-create
        STATUS          current
        DESCRIPTION     "DURABLE:  { '':all )
             A user reference name for this subnet."
        ::=  {  zxDslIpv6InBandEntry  4  }
    
    zxDslIpv6InBandIpUseType    OBJECT-TYPE 
        SYNTAX          INTEGER
            { 
                normal(1),
                modem(2),
                voip(3),
                media(4),
                normalSecondary(5),
                layer3(6),
                ieee1588(7),
                serialPort(8)
            } 
        MAX-ACCESS      read-create
        STATUS          current
        DESCRIPTION     
            "IPv6 Inband IP address type.
             normal         (1) - Inband IP address;
             Modem          (2) - Modem management;
             voip           (3) - VoIP subnet IP address;
             media          (4) - VoIP media subnet IP address;
             normalSecondary(5) - Secondary inband IP address;
             layer3         (6) - Layer3 interface IP address;
             ieee1588       (7) - IEEE 1588 IP address, just used by F829;
             serialPort     (8) - Serial port IP address, just used by F809;
            "
        ::=  {  zxDslIpv6InBandEntry  5  }


    zxDslIpv6InBandIpRowStatus  OBJECT-TYPE 
        SYNTAX          RowStatus
        MAX-ACCESS      read-create
        STATUS          current
        DESCRIPTION     "DURABLE:
             This object indicates the status of this entry.  A row in this
             table must be created using the createAndWait(5) action state
             (i.e., createAndGo(4) is not supported).  This object can only
             be set to active(1) after all objects for this row are valid.
             The 'tmsL3InBandName' is optional.
             
             Note that the notInService(2) state is not supported.  Objects
             in this table row can be changed when this object is notReady(3)
             or active(1)."
        ::=  {  zxDslIpv6InBandEntry  6  }
        
                
    zxDslIpv6TrapHostTable  OBJECT-TYPE
        SYNTAX      SEQUENCE  OF  ZxDslIpv6TrapHostEntry
        MAX-ACCESS  not-accessible
        STATUS      current
        DESCRIPTION "This table, which provides Trap target."
        ::=  { zxDslIpv6Objects  2 }

    zxDslIpv6TrapHostEntry  OBJECT-TYPE
        SYNTAX      ZxDslIpv6TrapHostEntry
        MAX-ACCESS  not-accessible
        STATUS      current
        DESCRIPTION ""
        INDEX       {  zxDslIpv6TrapHostIpAddr  }
        ::=  { zxDslIpv6TrapHostTable 1 }

    ZxDslIpv6TrapHostEntry  ::=  SEQUENCE {
        zxDslIpv6TrapHostIpAddr         InetAddress,
        zxDslIpv6TrapHostSnmpVer        Integer32,
        zxDslIpv6TrapHostCommunity      DisplayString,
        zxDslIpv6TrapHostIsZteNmsSever  TruthValue,        
        zxDslIpv6TrapHostEventType      BITS,
        zxDslIpv6TrapHostMinEventLevel  INTEGER,
        zxDslIpv6TrapHostRowStatus      RowStatus
        }


    zxDslIpv6TrapHostIpAddr OBJECT-TYPE 
        SYNTAX          InetAddress
        MAX-ACCESS      not-accessible
        STATUS          current
        DESCRIPTION     ""
        ::=  {  zxDslIpv6TrapHostEntry  1  }


    zxDslIpv6TrapHostSnmpVer    OBJECT-TYPE 
        SYNTAX          Integer32  ( 0 .. 1  ) 
        MAX-ACCESS      read-create
        STATUS          current
        DESCRIPTION     ""
        ::=  {  zxDslIpv6TrapHostEntry  2  }

    zxDslIpv6TrapHostCommunity  OBJECT-TYPE 
        SYNTAX          DisplayString  ( SIZE ( 0 .. 64  ) ) 
        MAX-ACCESS      read-create
        STATUS          current
        DESCRIPTION     ""
        ::=  {  zxDslIpv6TrapHostEntry  3  }


    zxDslIpv6TrapHostIsZteNmsSever  OBJECT-TYPE
        SYNTAX  TruthValue 
        MAX-ACCESS read-create
        STATUS current
        DESCRIPTION
            "If or not it is a zte's nms.
            true(1): it is a zte's nms;
            false(2): it is not a zte's nms.
            "
        ::= { zxDslIpv6TrapHostEntry 4  }       
        
    zxDslIpv6TrapHostEventType  OBJECT-TYPE
        SYNTAX BITS {
                     equipmentEvent(0),
                     qualityOfServiceEvent(1),
                     communicationsEvent(2),
                     environmentEvent(3),
                     processingErrorEvent(4)
                    }
        MAX-ACCESS read-create
        STATUS current
        DESCRIPTION
            "The event type that a reciever expects.
             
            The event type are defined in ITU-T X.733.
            
            -  equipment event type: 
                An event of this type is principally 
            associated with an equipment fault;
             
            -  quality of service event type: 
                An event of this type is
             principally associated with a degradation in the quality of a service;
             
            -  communications event type: 
                An event of this type is principally
             associated with the procedures and/or processes required to convey 
             information from one point to another;
            
            -  environmental event type:
                An event of this type is principally 
            associated with a condition relating to an enclosure in which the 
            equipment resides.

            -  processing error event type: 
                An event of this type is 
            principally associated with a software or processing fault;
            "
        DEFVAL { { equipmentEvent,qualityOfServiceEvent,communicationsEvent,
                environmentEvent,processingErrorEvent  } }
        ::= { zxDslIpv6TrapHostEntry 5 }

    zxDslIpv6TrapHostMinEventLevel  OBJECT-TYPE
        SYNTAX INTEGER {
                     cleared(0),
                     critical(1),
                     major(2),
                     minor(3),
                     warning(4),
                     notification(5)
                    }
        MAX-ACCESS read-create
        STATUS current
        DESCRIPTION
            "The min event level that a reciever expects.If the actual event 
            level is more serious then this value,the event will be sent to 
            Event Reciever. For example,if this value is warning(4),all the 
            events that the level in cleared(0),critical(1),major(2),minor(3),
            warning(4) will be sent,but notification(5) will not be sent.
            
            The event levels are defined in ITU-T X.733.            
            
           -   cleared: The Cleared severity level indicates the clearing of 
            one or more previously reported alarms. This alarm clears all 
            alarms for this managed object that have the same Alarm type,
            Probable cause and Specific problems (if given).  
            Multiple associated notifications may be cleared by using 
            the Correlated notifications parameter (defined below).
            This Recommendation | International Standard does not require that
            the clearing of previously reported alarms be reported.  
            Therefore, a managing system cannot assume that the absence of
            an alarm with the Cleared severity level means that the condition
            that caused the generation of previous alarms is still present.  
               Managed object definers shall state if, and under which 
            conditions, the Cleared severity level is used.
            
           -  critical: The Critical severity level indicates that a service 
             affecting condition has occurred and an immediate corrective action
             is required.  Such a severity can be reported, for example, when 
             a managed object becomes totally out of service and its capability 
             must be restored. 
             
           -   major: The Major severity level indicates that a service 
            affecting condition has developed and an urgent corrective action 
            is required.  Such a severity can be reported, for example, when 
            there is a severe degradation in the capability of the managed 
            object and its full capability must be restored. 
            
           -   minor: The Minor severity level indicates the existence of 
            a non-service affecting fault condition and that corrective action 
            should be taken in order to prevent a more serious (for example, 
            service affecting) fault. Such a severity can be reported, 
            for example, when the detected alarm condition is not currently 
            degrading the capacity of the managed object. 
                        
           -   warning: The Warning severity level indicates the detection of 
            a potential or impending service affecting fault, before any 
            significant effects have been felt. Action should be taken to 
            further diagnose (if necessary) and correct the problem in order 
            to prevent it from becoming a more serious service affecting fault.               

            -  notification: The notification severity level indicates that 
            only a infomation to be report and it is either a fault or 
            a potential fault. 

            "
        DEFVAL { notification }
        ::= { zxDslIpv6TrapHostEntry 6 }          
        

    zxDslIpv6TrapHostRowStatus  OBJECT-TYPE 
        SYNTAX          RowStatus
        MAX-ACCESS      read-create
        STATUS          current
        DESCRIPTION     ""
        ::=  {  zxDslIpv6TrapHostEntry  30  }    
        
    zxDslIpv6GlobalObjects   OBJECT IDENTIFIER ::= { zxDslIpv6Objects 3 }
    
    zxDslIpv6Enable  OBJECT-TYPE 
        SYNTAX      INTEGER
        {
            enable(1), 
            disable(2)
        }
        MAX-ACCESS  read-write
        STATUS      current
        DESCRIPTION
            "Enable/Disable IPv6."
        DEFVAL { disable }
        ::= { zxDslIpv6GlobalObjects 1}

    zxDslIpv6OutbandAddress   OBJECT IDENTIFIER ::=  {  zxDslIpv6Objects  4  } 
    
    zxDslIpv6OutBandInetAddr   OBJECT-TYPE 
        SYNTAX          InetAddress
        MAX-ACCESS      read-write
        STATUS          current
        DESCRIPTION     
            "Outband inet address."
        ::=  {  zxDslIpv6OutbandAddress  1  }

    zxDslIpv6OutBandInetAddrPfxLen  OBJECT-TYPE 
        SYNTAX          InetAddressPrefixLength
        MAX-ACCESS      read-write
        STATUS          current
        DESCRIPTION     
            "Outband inet address prefix length."
        ::=  {  zxDslIpv6OutbandAddress  2  }

--------------------------------------------------------------------------------
    zxDslLocalizationObjects    OBJECT IDENTIFIER   
        ::=  {  zxDslSysctrlObjects  15  }           
        
    zxDslLocalizationGlobalObjects   OBJECT IDENTIFIER 
        ::=  { zxDslLocalizationObjects 1 }
        
    zxDslLanguage OBJECT-TYPE 
        SYNTAX            INTEGER
        {
            english(1),
            chinese(2)            
        }
        MAX-ACCESS        read-write
        STATUS            current
        DESCRIPTION       
            "The language for console and telnet."         
        DEFVAL { english }
        ::=  {  zxDslLocalizationGlobalObjects 1 }    
                   
    zxDslLocalizationFileTable   OBJECT-TYPE
        SYNTAX      SEQUENCE  OF  ZxDslLocalizationFileEntry
        MAX-ACCESS  not-accessible
        STATUS      current
        DESCRIPTION 
            "This table includes the localization file information
             for console and telnet."
        ::=  { zxDslLocalizationObjects 2 }

    zxDslLocalizationFileEntry   OBJECT-TYPE
        SYNTAX      ZxDslLocalizationFileEntry
        MAX-ACCESS  not-accessible
        STATUS      current
        DESCRIPTION 
            "An entry in zxDslLocalizationFileTable."
        INDEX   {zxDslLocalizationFileType}
        ::=  { zxDslLocalizationFileTable 1 }

    ZxDslLocalizationFileEntry  ::=  SEQUENCE {
        zxDslLocalizationFileType         INTEGER, 
        zxDslLocalizationFileVersion      DisplayString,
        zxDslLocalizationFileSize         Unsigned32,
        zxDslLocalizationFileCreateTime   DisplayString,                 
        zxDslLocalizationFileAdminStatus  INTEGER
        }         
        
    zxDslLocalizationFileType OBJECT-TYPE 
        SYNTAX            INTEGER
        {
            english(1),
            chinese(2)            
        }
        MAX-ACCESS        not-accessible
        STATUS            current
        DESCRIPTION       
            "Localization file type."
        ::=  {  zxDslLocalizationFileEntry  1  }            
        
    zxDslLocalizationFileVersion  OBJECT-TYPE 
        SYNTAX          DisplayString (SIZE( 0..32))
        MAX-ACCESS      read-only
        STATUS          current
        DESCRIPTION     
            "The version number of the localization file."
        ::=  {  zxDslLocalizationFileEntry  2  }

    zxDslLocalizationFileSize OBJECT-TYPE 
        SYNTAX          Unsigned32
        UNITS           "byte"         
        MAX-ACCESS      read-only
        STATUS          current
        DESCRIPTION     
            "The version length of the localization file."
        ::=  {  zxDslLocalizationFileEntry  3  }    
        
    zxDslLocalizationFileCreateTime  OBJECT-TYPE 
        SYNTAX          DisplayString(SIZE( 0..16))
        MAX-ACCESS      read-only
        STATUS          current
        DESCRIPTION     
            "Create time of the localization file.The format is 
             yyyymmdd HHMMSS.For example,20100707 131527"
        ::=  {  zxDslLocalizationFileEntry  4  } 
                              
    zxDslLocalizationFileAdminStatus  OBJECT-TYPE 
        SYNTAX          INTEGER  
        { 
            delete(1) 
        } 
        MAX-ACCESS      read-write
        STATUS          current
        DESCRIPTION     
            "Delete localization file."
        ::=  {  zxDslLocalizationFileEntry  10  }    

--------------------------------------------------------------------------------

    zxDslModuleFileObjects    OBJECT IDENTIFIER
        ::=  {  zxDslSysctrlObjects  16  }
        
    zxDslModuleFileGlobalObjects   OBJECT IDENTIFIER 
        ::=  { zxDslModuleFileObjects 1 }
        
    zxDslModuleFileStatus OBJECT-TYPE 
        SYNTAX       INTEGER
        {
            notExist(1),
            loadSucceeded(2),
            loadFailed(3)
        }
        MAX-ACCESS   read-only
        STATUS       current
        DESCRIPTION       
            "The status of the module file: 
             notExist(1)       - Module file does not exist.
             loadSucceeded(2)  - Load module file succeeded.
             loadFailed(3)     - Load module file failed.
            "
        DEFVAL { notExist }
        ::=  {  zxDslModuleFileGlobalObjects 1 }
        
    zxDslModuleFileInfo OBJECT-TYPE 
        SYNTAX       DisplayString(1..128)
        MAX-ACCESS   read-only
        STATUS       current
        DESCRIPTION       
            "The information of the module file which includes NE version name,
             NE version No., module file version No. and module file build time.
            "
        ::=  {  zxDslModuleFileGlobalObjects 2 }
        
    zxDslEraseModuleFile OBJECT-TYPE 
        SYNTAX       Integer32
        MAX-ACCESS   read-write
        STATUS       current
        DESCRIPTION       
            "Value 1 means to erase the module file."
        ::=  {  zxDslModuleFileGlobalObjects 3 }
    
--------------------------------------------------------------------------------

   zxDslNmsAccessCtrl   OBJECT IDENTIFIER   ::= {  zxDslSysctrlObjects  9  }

    zxDslCommunityConfTable OBJECT-TYPE
        SYNTAX SEQUENCE OF ZxDslCommunityConfEntry
        MAX-ACCESS not-accessible
        STATUS current
        DESCRIPTION
            "A table of SNMPv1/v2c community string configuration."
        ::= { zxDslNmsAccessCtrl 1 }

    zxDslCommunityConfEntry OBJECT-TYPE
        SYNTAX ZxDslCommunityConfEntry
        MAX-ACCESS not-accessible
        STATUS current
        DESCRIPTION
            "A list of community strings."
        INDEX { zxDslCommunityConfCommunity }
        ::= { zxDslCommunityConfTable 1 }

    ZxDslCommunityConfEntry ::= SEQUENCE {
        zxDslCommunityConfCommunity     DisplayString,
        zxDslCommunityConfPermission    INTEGER,
        zxDslCommunityConfViewName      DisplayString,
        zxDslCommunityConfRowStatus     RowStatus
    }

    zxDslCommunityConfCommunity  OBJECT-TYPE
        SYNTAX DisplayString (SIZE(1..20))
        MAX-ACCESS not-accessible
        STATUS current
        DESCRIPTION
            "DURABLE: { 'public','':all }
             The SNMPv1/v2c community name string.  
             Name must begin with alphabetic character or '_' and '@' shouldn't 
             be used in community string.
             Duplicate community names are not allowed in this table. 
             Note that a null string is not a valid community name 
             (i.e., a null string forces 'zxDslCommunityConfRowStatus' 
             to 'notReady(3)')."
        ::= { zxDslCommunityConfEntry 1 }


    zxDslCommunityConfPermission OBJECT-TYPE
        SYNTAX INTEGER {
               readOnly(1),
               readWrite(2)
        }
        MAX-ACCESS read-create
        STATUS current
        DESCRIPTION
            "DURABLE: { readWrite:all }
             This object specifies the type of access allowed. 'readOnly(1)'
             allows GET operations (i.e., GET, GET-NEXT, GET-BULK) and
             'readWrite(2)' allows both GET and SET operations."
        ::= { zxDslCommunityConfEntry 2 }

    zxDslCommunityConfViewName  OBJECT-TYPE
        SYNTAX SnmpAdminString (SIZE(1..32))
        MAX-ACCESS read-create
        STATUS current
        DESCRIPTION
            "
             This object is reserved now.
              
             DURABLE: { 'internet':all }
             At runtime (i.e., not when this object is SET), this view name
             is compared to the 'vacmViewTreeFamilyViewName' in the
             'vacmViewTreeFamilyTable' (see RFC2575).  If a match is
             found and the varbind(s) specify valid object type and instance,
             the 'zxDslCommunityConfPermission' privilege is permitted.
             
             Note that a null string is not a valid view name value.
             Also note that the value of this object does not have to match
             an existing entry in the 'vacmViewTreeFamilyTable' (if no match,
             no access is allowed).
             
             Note that the factory default value for this object is 'internet',
             which allows access to the subtree under '1.3.6.1'."
        ::= { zxDslCommunityConfEntry 3 }
        
    zxDslCommunityConfRowStatus OBJECT-TYPE
        SYNTAX  RowStatus
        MAX-ACCESS  read-create
        STATUS  current
        DESCRIPTION
            "DURABLE:
             This object indicates the status of this entry.  A row in this
             table can be created using the 'createAndGo(4)' (i.e., all
             parameters must be valid - supplied in a single SNMP PDU or have
             default values).
             
             Any object in a conceptual row can be modified independent of the
             value of this object (e.g., can be changed while 'active(1)')."
        ::= { zxDslCommunityConfEntry 4 }




--------------------------------------------------------------------------------
--  Ntp 
--------------------------------------------------------------------------------
    zxDslSntp               OBJECT IDENTIFIER ::= { zxDslSysctrlObjects  10 }


    zxDslSntpEnable OBJECT-TYPE
        SYNTAX  INTEGER{
                        enable(1),
                        disable(2)
                        }
        MAX-ACCESS  read-write
        STATUS      current
        DESCRIPTION
            "Enable/disable NTP in this system."
        DEFVAL { disable }
        ::= { zxDslSntp 1}


    zxDslSntpServerIp OBJECT-TYPE
      SYNTAX        IpAddress
      MAX-ACCESS    read-write
      STATUS        current
      DESCRIPTION
        " The NTP server's IP address "
      ::= { zxDslSntp 2}

    zxDslSntpPollInterval OBJECT-TYPE
      SYNTAX        Integer32
      UNITS         "seconds"
      MAX-ACCESS    read-write
      STATUS current
      DESCRIPTION
        " The NTP server's fetch time's interval time, the default is 64"
      DEFVAL { 64 }
      ::= { zxDslSntp 3}
      

    zxDslSntpStratum OBJECT-TYPE
      SYNTAX        Integer32
      MAX-ACCESS    read-only
      STATUS        current
      DESCRIPTION
        " The local NTP server 's stratum.
          If it is 16,then it means that this device has not synchronied time, 
          and it is a invalid value. "
      ::= { zxDslSntp 5}


    zxDslSntpSynchStatus OBJECT-TYPE
      SYNTAX        INTEGER
              {
                 alreadySyn(1),
                 neverSyn(2)
              }
      MAX-ACCESS    read-only
      STATUS        current
      DESCRIPTION
        " The NTP server whether is  synchronized or not "
      ::= { zxDslSntp 6}


    zxDslSntpSlaveServerIp OBJECT-TYPE
      SYNTAX        IpAddress
      MAX-ACCESS    read-write
      STATUS        current
      DESCRIPTION
        " The slave NTP server's IP address "
      ::= { zxDslSntp 7}


    zxDslSntpCurrTryingSynchServerIp OBJECT-TYPE
      SYNTAX        IpAddress
      MAX-ACCESS    read-only
      STATUS        current
      DESCRIPTION
        " The NTP server's IP which is being tried to synchronize time now."
      ::= { zxDslSntp 8}


    zxDslSntpLastSynchronizedServerIP OBJECT-TYPE
      SYNTAX        IpAddress
      MAX-ACCESS    read-only
      STATUS        current
      DESCRIPTION
        " The NTP server's IP address of last ntp synchronization."
      ::= { zxDslSntp 9}
    


    zxDslSysSntpCurrentOffset OBJECT-TYPE
      SYNTAX      Integer32
      UNITS       "seconds"
      MAX-ACCESS  read-only
      STATUS      current
      DESCRIPTION
          "The Time offset to the current selected reference time source.
          "
      ::= { zxDslSntp 10 }


    zxDslSysSntpOffsetAlarmThreshold OBJECT-TYPE
      SYNTAX      Integer32
      UNITS       "seconds"
      MAX-ACCESS  read-only
      STATUS      current
      DESCRIPTION
          "The alarm threshold of NTP time offset to the current selected 
          reference time source.When this threshold is across,the trap 
          zxDslSysSntpOffsetOverThreshTrap  should be sent to a manager. 
          "
      DEFVAL { 7 }
      ::= { zxDslSntp 11 }  



   zxDslOpticalPower   OBJECT IDENTIFIER   ::= {  zxDslSysctrlObjects  11  }

        zxDslOpticalPowerRx OBJECT-TYPE
          SYNTAX    DisplayString
          UNITS     "dBm"
          MAX-ACCESS read-only
          STATUS current
          DESCRIPTION
            "Received optical power"
          ::= { zxDslOpticalPower 1}

        zxDslOpticalPowerTx OBJECT-TYPE
          SYNTAX    DisplayString
          UNITS     "dBm"
          MAX-ACCESS read-only
          STATUS current
          DESCRIPTION
            "Transmitted optical power"
          ::= { zxDslOpticalPower 2}


   zxDslVoipDhcp   OBJECT IDENTIFIER   ::= {  zxDslSysctrlObjects  12  }

    zxDslVoipDhcpEnable OBJECT-TYPE
        SYNTAX     INTEGER{
            enable(1),
            disable(2)
        }
        MAX-ACCESS  read-write
        STATUS current
        DESCRIPTION
            "The VOIP DHCP status. The IP subnet for VOIP should be configed first."
        DEFVAL { disable }
        ::= { zxDslVoipDhcp 1 } 
        
    zxDslVoipDhcpIpAddress   OBJECT-TYPE 
        SYNTAX          IpAddress
        MAX-ACCESS      read-only
        STATUS          current
        DESCRIPTION     
            "The IP address for VOIP when zxDslVoipDhcpEnable is enable.
             When zxDslVoipDhcpEnable is disable, VOIP IP address should be getted from IP subnet table."
        ::= { zxDslVoipDhcp 2 } 

    zxDslVoipDhcpIpMask  OBJECT-TYPE 
        SYNTAX          IpAddress
        MAX-ACCESS      read-only
        STATUS          current
        DESCRIPTION     
            "The IP mask for VOIP when zxDslVoipDhcpEnable is enable.
             When zxDslVoipDhcpEnable is disable, VOIP IP mask should be getted from IP subnet table."
        ::= { zxDslVoipDhcp 3 } 

    zxDslVoipDhcpRoute  OBJECT-TYPE 
        SYNTAX          IpAddress
        MAX-ACCESS      read-only
        STATUS          current
        DESCRIPTION     
            "The route for VOIP when zxDslVoipDhcpEnable is enable.
             When zxDslVoipDhcpEnable is disable, VOIP route should be getted from IP route table."
        ::= { zxDslVoipDhcp 4 } 
        
    zxDslVoipDhcpOption60Enable OBJECT-TYPE
        SYNTAX     INTEGER{
            enable(1),
            disable(2)
        }
        MAX-ACCESS  read-write
        STATUS current
        DESCRIPTION
            "The VOIP DHCP Option60 status. "
        DEFVAL { enable }
        ::= { zxDslVoipDhcp 5 } 
        
    zxDslVoipDhcpOption60Vendor OBJECT-TYPE
        SYNTAX     DisplayString (SIZE(1..32))
        MAX-ACCESS  read-write
        STATUS current
        DESCRIPTION
            "The VOIP DHCP Option60 Vendor. "
        ::= { zxDslVoipDhcp 6 } 
    
    zxDslVoipDhcpOption60Category OBJECT-TYPE
        SYNTAX     DisplayString (SIZE(1..32))
        MAX-ACCESS  read-write
        STATUS current
        DESCRIPTION
            "The VOIP DHCP Option60 Category. "
        ::= { zxDslVoipDhcp 7 }  
        
    zxDslVoipDhcpOption60Model OBJECT-TYPE
        SYNTAX     DisplayString (SIZE(1..32))
        MAX-ACCESS  read-write
        STATUS current
        DESCRIPTION
            "The VOIP DHCP Option60 Model. "
        ::= { zxDslVoipDhcp 8} 
        
    zxDslVoipDhcpOption60Version OBJECT-TYPE
        SYNTAX     DisplayString (SIZE(1..32))
        MAX-ACCESS  read-write
        STATUS current
        DESCRIPTION
            "The VOIP DHCP Option60 Version. "
        ::= { zxDslVoipDhcp 9 } 
        
    zxDslVoipDhcpReRequestEnable OBJECT-TYPE
        SYNTAX  INTEGER {
            enable(1),
            disable(2)
        }
        MAX-ACCESS  read-write
        STATUS      current
        DESCRIPTION
            "When zxDslVoipDhcpReRequestEnable is enable, device will
             re-request an IP address by DHCP as VoIP service is broken.
             This object is valid when zxDslVoipDhcpEnable is enable."
        DEFVAL  { disable }  
        ::= {zxDslVoipDhcp 10 }

    zxDslVoipDhcpReRequestInterval OBJECT-TYPE
        SYNTAX      Integer32(1..20)
        UNITS       "minutes"
        MAX-ACCESS  read-write
        STATUS      current
        DESCRIPTION
            "The interval that device re-requests an IP address after VoIP 
             service is broken.
             This object is valid when zxDslVoipDhcpReRequestEnable is enable."
        DEFVAL  { 10 }
        ::= {zxDslVoipDhcp 11 }
        
    zxDslSyslog   OBJECT IDENTIFIER   ::= {  zxDslSysctrlObjects  13  }  
     
    zxDslSyslogGlobalObjects  OBJECT IDENTIFIER  ::= {zxDslSyslog 1}
    
    zxDslSyslogFacility  OBJECT-TYPE 
        SYNTAX           Integer32(0..23)
        MAX-ACCESS       read-write
        STATUS           current
        DESCRIPTION      
          "The syslog message facility. The priority value of PRI is calculated by first multiplying 
           the Facility number by 8 and then adding the numerical value of the Severity.             
             
            Numerical Code       Facility             
            0              kernel messages
            1              user-level messages
            2              mail system
            3              system daemons
            4              security/authorization messages (note 1)
            5              messages generated internally by syslogd
            6              line printer subsystem
            7              network news subsystem
            8              UUCP subsystem
            9              clock daemon (note 2)
            10             security/authorization messages (note 1)
            11             FTP daemon
            12             NTP subsystem
            13             log audit (note 1)
            14             log alert (note 1)
            15             clock daemon (note 2)
            16             local use 0  (local0)
            17             local use 1  (local1)
            18             local use 2  (local2)
            19             local use 3  (local3)
            20             local use 4  (local4)
            21             local use 5  (local5)
            22             local use 6  (local6)
            23             local use 7  (local7)     
            
            More information, please refer to rfc3164.  
            " 
        ::=  {  zxDslSyslogGlobalObjects  1  }      
        
    zxDslSyslogSeverity  OBJECT-TYPE 
        SYNTAX           Integer32(0..7)
        MAX-ACCESS       read-write
        STATUS           current
        DESCRIPTION      
          "The syslog message severity, The priority value of PRI is calculated by first multiplying 
           the Facility number by 8 and then adding the numerical value of the Severity.             
                          
           Numerical Code       Severity          
            0             Emergency: system is unusable
            1             Alert: action must be taken immediately
            2             Critical: critical conditions
            3             Error: error conditions
            4             Warning: warning conditions
            5             Notice: normal but significant condition
            6             Informational: informational messages
            7             Debug: debug-level messages    
            
            More information, please refer to rfc3164.  
            " 
        ::=  {  zxDslSyslogGlobalObjects  2  }    
        
    zxDslSyslogSrcPort   OBJECT-TYPE 
        SYNTAX           Integer32
        MAX-ACCESS       read-write
        STATUS           current
        DESCRIPTION      
             "The syslog source udp port. "
        ::=  {  zxDslSyslogGlobalObjects  3  }
        
    zxDslSyslogCmdLogEnable OBJECT-TYPE 
        SYNTAX           INTEGER{
            enable(1),
            disable(2)
        }
        MAX-ACCESS       read-write
        STATUS           deprecated
        DESCRIPTION      
             "Enable/Disable the cmd log in syslog. " 
        ::=  {  zxDslSyslogGlobalObjects  4  }
        
    zxDslSyslogSnmpLogEnable OBJECT-TYPE 
        SYNTAX           INTEGER{
            enable(1),
            disable(2)
        }
        MAX-ACCESS       read-write
        STATUS           deprecated
        DESCRIPTION      
             "Enable/Disable the snmp log in syslog. " 
        ::=  {  zxDslSyslogGlobalObjects  5  }
         
    zxDslSyslogAlarmLogEnable OBJECT-TYPE 
        SYNTAX           INTEGER{
            enable(1),
            disable(2)
        }
        MAX-ACCESS       read-write
        STATUS           deprecated
        DESCRIPTION      
             "Enable/Disable the alarm log in syslog. " 
        ::=  {  zxDslSyslogGlobalObjects  6  }
        
    zxDslSyslogAlarmLogLevel OBJECT-TYPE 
        SYNTAX           Integer32(0..7)
        MAX-ACCESS       read-write
        STATUS           deprecated
        DESCRIPTION      
             "The alarm log level in syslog. " 
        ::=  {  zxDslSyslogGlobalObjects  7  }                                
     
         
    zxDslSyslogHostTable  OBJECT-TYPE
        SYNTAX      SEQUENCE  OF  ZxDslSyslogHostEntry
        MAX-ACCESS  not-accessible
        STATUS      current
        DESCRIPTION "syslog host table."
        ::=  { zxDslSyslog  2 }

    zxDslSyslogHostEntry  OBJECT-TYPE
        SYNTAX      ZxDslSyslogHostEntry
        MAX-ACCESS  not-accessible
        STATUS      current
        DESCRIPTION "An entry in zxDslSyslogHostTable."
        INDEX       {  zxDslSyslogHostIpAddr  }
        ::=  { zxDslSyslogHostTable 1 }

    ZxDslSyslogHostEntry  ::=  SEQUENCE {
        zxDslSyslogHostIpAddr      IpAddress,
        zxDslSyslogDesPort         Integer32,    
        zxDslSyslogHostRowStatus   RowStatus
        }  
          
    zxDslSyslogHostIpAddr  OBJECT-TYPE 
        SYNTAX             IpAddress
        MAX-ACCESS         not-accessible
        STATUS             current
        DESCRIPTION      
             "The syslog server ip address. "
        ::=  {  zxDslSyslogHostEntry  1  }                   

    zxDslSyslogDesPort  OBJECT-TYPE 
        SYNTAX           Integer32
        MAX-ACCESS       read-create
        STATUS           current
        DESCRIPTION      
             "The syslog destination udp port. " 
        ::=  {  zxDslSyslogHostEntry  2  }        
    
    zxDslSyslogHostRowStatus  OBJECT-TYPE 
        SYNTAX          RowStatus
        MAX-ACCESS      read-create
        STATUS          current
        DESCRIPTION     ""
        ::=  {  zxDslSyslogHostEntry  10  }
        
        
        
--------------------------------------------------------------------------------
-- definition of sysctrl traps.

    zxDslPrimaryCtrlCardSwapped NOTIFICATION-TYPE
        STATUS  current
        DESCRIPTION
            "A zxDslPrimaryCtrlCardSwapped trap indicates that the main control 
            card has swapped to slave card."
        ::= { zxDslSysctrlTrapObjects 1 }
    
    zxDslCardUp NOTIFICATION-TYPE
        OBJECTS { zxDslBoardAdminStatus, zxDslBoardOperStatus }
        STATUS  current
        DESCRIPTION
            "A zxDslCardUp trap indicates that the agent has detected that the
            card has been online."
       ::= { zxDslSysctrlTrapObjects 2 }
       
    zxDslCardDown NOTIFICATION-TYPE
        OBJECTS { zxDslBoardAdminStatus, zxDslBoardOperStatus }
        STATUS  current
        DESCRIPTION
            "A zxDslCardDown trap indicates that the agent has detected that the
            card has been offline."
       ::= { zxDslSysctrlTrapObjects 3 }
       
    zxDslCpuLoadAlarm NOTIFICATION-TYPE
        OBJECTS { zxDslBoardCpuLoad, zxDslBoardCpuLoadThreshhold }
        STATUS  current
        DESCRIPTION
            "A zxDslCpuLoadAlarm trap indicates that the agent has detected that the
            zxDslCardCPULoad object of one card has exceeded the configured threshhold value of 
            zxDslBoardCpuLoadThreshhold."
       ::= { zxDslSysctrlTrapObjects 4 }
    
    zxDslCpuLoadAlarmCleard NOTIFICATION-TYPE
        OBJECTS { zxDslBoardCpuLoad, zxDslBoardCpuLoadThreshhold }
        STATUS  current
        DESCRIPTION
            "A zxDslCpuLoadAlarmCleard trap indicates that the agent has detected that the
            zxDslCardCPULoad object of one card has less than the configured threshhold value of 
            zxDslBoardCpuLoadThreshhold."
       ::= { zxDslSysctrlTrapObjects 5 }
              
    zxDslMemoryOverLoad NOTIFICATION-TYPE
        OBJECTS { zxDslBoardMemUsage, zxDslBoardMemUsageThreshhold }
        STATUS  current
        DESCRIPTION
            "A zxDslMemoryOverLoad trap indicates that the agent has detected that the
            zxDslCardMemUsage object of one card has exceeded the configured threshhold value of 
            zxDslBoardMemUsageThreshhold."
       ::= { zxDslSysctrlTrapObjects 6 }
    
    zxDslMemoryAlarmCleard NOTIFICATION-TYPE
        OBJECTS { zxDslBoardMemUsage, zxDslBoardMemUsageThreshhold }
        STATUS  current
        DESCRIPTION
            "A zxDslMemoryAlarmCleard trap indicates that the agent has detected that the
            zxDslCardMemUsage object of one card has less than the configured threshhold value of 
            zxDslBoardMemUsageThreshhold."
       ::= { zxDslSysctrlTrapObjects 7 }            




-- env trap
    zxDslEnvTrapGroup OBJECT IDENTIFIER  ::= { zxDslSysctrlTrapObjects 8 }
    
    zxDslEnvTempExceeded NOTIFICATION-TYPE
        OBJECTS {
                  zxDslEnvChassisTemperature,
                  zxDslEnvTemperatureThreshold
                }
        STATUS             current
        DESCRIPTION
           "A temperature inside the chassis has exceeded
            normal operating temperature zxDslEnvTemperatureThreshold. 
            The zxDslEnvChassisTemperature object identifies the current status."
       ::= { zxDslEnvTrapGroup 1 }            

    zxDslEnvTempNormal NOTIFICATION-TYPE
        OBJECTS {
                  zxDslEnvChassisTemperature,
                  zxDslEnvTemperatureThreshold
                }
        STATUS             current
        DESCRIPTION
           "A temperature inside the chassis has returned to
            normal operating temperature zxDslEnvTemperatureThreshold. 
            The zxDslEnvChassisTemperature object identifies the current status."
       ::= { zxDslEnvTrapGroup 2 }            

   zxDslEnvFanFailed NOTIFICATION-TYPE
        OBJECTS { 
                zxDslEnvFanAdminstatus,
                zxDslEnvFanOperstatus  }
        STATUS             current
        DESCRIPTION
           "A Fan tray on the device has failed. The
            zxDslEnvFanOperstatus object identifies the failed fan Operstatus."
        ::= { zxDslEnvTrapGroup 3 }
 
   zxDslEnvFanRecovered NOTIFICATION-TYPE
        OBJECTS { 
                zxDslEnvFanAdminstatus,
                zxDslEnvFanOperstatus  }
        STATUS             current
        DESCRIPTION
           "A Fan tray on the device has recovered
            after failure. The zxDslEnvFanOperstatus object identifies
            the recovered Fan Operstatus."
        ::= { zxDslEnvTrapGroup 4 }

   zxDslEnvLossOfPower NOTIFICATION-TYPE
        STATUS             current
        DESCRIPTION
           "This is device dying gasp event.It is generated when the device is 
           power off or power failure."
        ::= { zxDslEnvTrapGroup 5 }

   zxDslEnvSwitchFailed NOTIFICATION-TYPE
        OBJECTS {
            zxDslEnvDeviceId,
            zxDslEnvSwitchNormalStatus,
            zxDslEnvSwitchCurrentStatus
        }   
        STATUS      current
        DESCRIPTION
           "It is generated when the switch is Faild."
        ::= { zxDslEnvTrapGroup 6 }

   zxDslEnvSwitchRecovered NOTIFICATION-TYPE
        OBJECTS {
            zxDslEnvDeviceId,
            zxDslEnvSwitchNormalStatus,
            zxDslEnvSwitchCurrentStatus
        }    
        STATUS      current
        DESCRIPTION
           "It is generated when the switch is Recovered."
        ::= { zxDslEnvTrapGroup 7 }

   zxDslEnvExteriorPowerFailed NOTIFICATION-TYPE
        STATUS      current
        DESCRIPTION
           "It is generated when the Exterior Power is Faild."
        ::= { zxDslEnvTrapGroup 8 }

   zxDslEnvExteriorPowerRecovered NOTIFICATION-TYPE
        STATUS      current
        DESCRIPTION
           "It is generated when the Exterior Power is Recovered."
        ::= { zxDslEnvTrapGroup 9 }
        
   zxDslEnvBatteriesVoltageFailed NOTIFICATION-TYPE
        STATUS      current
        DESCRIPTION
           "It is generated when the Batteries Voltage is Faild."
        ::= { zxDslEnvTrapGroup 10 }

   zxDslEnvBatteriesVoltageRecovered NOTIFICATION-TYPE
        STATUS      current
        DESCRIPTION
           "It is generated when the Batteries Voltage is Recovered."
        ::= { zxDslEnvTrapGroup 11 }
        
   zxDslEnvPowerFailed NOTIFICATION-TYPE
        STATUS      current
        DESCRIPTION
           "It is generated when the Power is Faild."
        ::= { zxDslEnvTrapGroup 12 }

   zxDslEnvPowerRecovered NOTIFICATION-TYPE
        STATUS      current
        DESCRIPTION
           "It is generated when the Power is Recovered."
        ::= { zxDslEnvTrapGroup 13 }                                               


  zxDslEnvMonitorInterfaceLinkDown NOTIFICATION-TYPE
       STATUS  current
       DESCRIPTION
          "It indicates that the agent has detected that the
           link at the enviroment monitoring inerface has been down."
       ::= { zxDslEnvTrapGroup 14 }
    
       
  zxDslEnvMonitorInterfaceLinkUp NOTIFICATION-TYPE
       STATUS  current
       DESCRIPTION
          "It indicates that the agent has detected that the
           link at the enviroment monitoring inerface has been up."
       ::= { zxDslEnvTrapGroup 15 }      
       
  zxDslTempUnderThreshTrap NOTIFICATION-TYPE
       OBJECTS {
                  zxDslEnvChassisTemperature,
                  zxDslEnvTemperatureLowerThreshold
               }  
       STATUS  current
       DESCRIPTION
          "It indicates that the zxDslEnvChassisTemperature is lower 
          than zxDslEnvTemperatureLowerThreshold."
       ::= { zxDslEnvTrapGroup 16 }
    
       
  zxDslTempUnderThreshTrapCleared NOTIFICATION-TYPE
       OBJECTS {
                  zxDslEnvChassisTemperature,
                  zxDslEnvTemperatureLowerThreshold
               }  
       STATUS  current
       DESCRIPTION
          "It indicates that the zxDslTempUnderThreshTrap has Cleared."
       ::= { zxDslEnvTrapGroup 17 }            

   zxDslEnvFanFaultStateChangedTrap NOTIFICATION-TYPE
        OBJECTS { 
                zxDslEnvFanFaultInfo,
                zxDslEnvFanTotalNumber
                }
        STATUS             current
        DESCRIPTION
           "This trap signifies that fault state of a fan has been changed.
            zxDslEnvFanFailedInfo indicates the failed fan list.
            zxDslEnvFanTotalNumber indicates the total number of fans.
            ."
        ::= { zxDslEnvTrapGroup 18 }                

--- Port Traps

    zxDslIfUplinkUp NOTIFICATION-TYPE
        OBJECTS { ifAdminStatus, ifOperStatus, ifType }
        STATUS  current
        DESCRIPTION
            "The operational status of uplink interface changes to up."
        ::= { zxDslSysctrlTrapObjects 20 }

    zxDslIfUplinkDown NOTIFICATION-TYPE
        OBJECTS { ifAdminStatus, ifOperStatus, ifType }
        STATUS  current
        DESCRIPTION
            "The operational status of uplink interface changes to down."
        ::= { zxDslSysctrlTrapObjects 21 }

    zxDslIfAccesslinkUp NOTIFICATION-TYPE
        OBJECTS { ifAdminStatus, ifOperStatus, ifType }
        STATUS  current
        DESCRIPTION
            "The operational status of access link interface changes to up."
        ::= { zxDslSysctrlTrapObjects 22 }

    zxDslIfAccesslinkDown NOTIFICATION-TYPE
        OBJECTS { ifAdminStatus, ifOperStatus, ifType }
        STATUS  current
        DESCRIPTION
            "The operational status of access link interface changes to down."
        ::= { zxDslSysctrlTrapObjects 23 }
    
    zxDslUnexpectedCardTypePlugin NOTIFICATION-TYPE
        OBJECTS { zxDslBoardType }
        STATUS  current
        DESCRIPTION
            "A zxDslUnexpectedCardTypePlugin trap indicates that the card plug 
             in the given slot is unexpected.
             
             For example, the ethernet user card can be plug in slot 2 of F821 
             NE with HSMV, when ei8e card be pluged in other slot, this alarm 
             will be generated."
        REFERENCE    "F821"
        ::= { zxDslSysctrlTrapObjects 24 }
       
    zxDslUnexpectedCardTypePluginCleared NOTIFICATION-TYPE
        OBJECTS { zxDslBoardType }
        STATUS  current
        DESCRIPTION
            "A zxDslUnexpectedCardTypePluginCleared trap indicates that the 
             unexpected card plug-in is Recovered.
             
             For example, when ei8e card be unpluged from slot 3 of F821 NE 
             with HSMV, this clear trap will be generated. "          
        REFERENCE    "F821"
        ::= { zxDslSysctrlTrapObjects 25 }
     
    zxDslMaxPortNumPerSlotChanged NOTIFICATION-TYPE
        OBJECTS { zxDslSysMaxPortNumPerSlot }
        STATUS  current
        DESCRIPTION
            "A zxDslMaxPortNumPerSlotChanged trap indicates that the value of
             zxDslSysMaxPortNumPerSlot changed."
        ::= { zxDslSysctrlTrapObjects 26 }
        
    zxDslCardChipDown NOTIFICATION-TYPE
        OBJECTS { zxDslBoardType }
        STATUS  current
        DESCRIPTION
            "A zxDslCardChipDown trap indicates that the card is in abnormal
             status."
        ::= { zxDslSysctrlTrapObjects 27 }
       
    zxDslCardChipDownCleared NOTIFICATION-TYPE
        OBJECTS { zxDslBoardType }
        STATUS  current
        DESCRIPTION
            "A zxDslCardChipDownCleared trap indicates that the abnormal card is
             Recovered."
        ::= { zxDslSysctrlTrapObjects 28 }

--------------------------------------------------------------------------------
--  Ntp Trap
--------------------------------------------------------------------------------
    zxDslSysSntpTrapGroup  OBJECT IDENTIFIER  ::= { zxDslSysctrlTrapObjects 50 }

    zxDslSysSntpOffsetOverThreshTrap      NOTIFICATION-TYPE
            OBJECTS { zxDslSysSntpCurrentOffset,
                      zxDslSysSntpOffsetAlarmThreshold  }
            STATUS  current
            DESCRIPTION
                "zxDslSysSntpOffsetAlarmThreshold is reached."
            ::= { zxDslSysSntpTrapGroup 1 }

    zxDslSysSntpOffsetUnderThreshTrap      NOTIFICATION-TYPE
            OBJECTS { zxDslSysSntpCurrentOffset,
                      zxDslSysSntpOffsetAlarmThreshold  }
            STATUS  current
            DESCRIPTION
                " zxDslSysSntpCurrentOffset is below zxDslSysSntpOffsetAlarmThreshold.
                "
            ::= { zxDslSysSntpTrapGroup 2 }


    zxDslSysSntpSynchFailed      NOTIFICATION-TYPE
            OBJECTS { zxDslSntpCurrTryingSynchServerIp }
            STATUS  current
            DESCRIPTION
                "Faied to synchronize time from SNTP server."
            ::= { zxDslSysSntpTrapGroup 3 }


    zxDslSysSntpSynchFailedCleard   NOTIFICATION-TYPE
            OBJECTS { zxDslSntpCurrTryingSynchServerIp }
            STATUS  current
            DESCRIPTION
                "Cleared the alarm of zxDslSysSntpSynchFailed."
            ::= { zxDslSysSntpTrapGroup 4 }            
                        

    zxDslSysCompatible  OBJECT-TYPE
              SYNTAX      OCTET STRING (SIZE (4))
              MAX-ACCESS  read-only
              STATUS      current
              DESCRIPTION
                      "The compatibility of DSLAM. Every bit denotes the 
                       compatibility of some function. If the value of the 
                       bit is 1, the related function has compatible problem.
                       The related function of the first bit is the naming 
                       rules of string.
                       
                       bit 1: QoS Flow Policy of NE supports CCoS.
                       bit 2: zxDslInBandIpUseType.  value 1 of this bit means normalSecondary(5), 0 means normalSecondary(3).
                       bit 3: zxDslSyslog. value 1 means use zxDslSyslogHostTable, value 0 means just scalar value for Finland test.
                       bit 4: zxDslTrapHostTable. value 1 means support event level and type.
                       bit 5: QoS Queue Expand,include zxDslQosSchedulerID and zxDslQos8021p2CosQPortNumber. value 1 means zxDslQosSchedulerID 
                              and zxDslQos8021p2CosQPortNumber support UNI-ETCA.
                       bit 6: Different unit of ifLastChange, value 1 means 10 millisecond, 0 means 1 second.
                       bit 7: value 1 means support IAP Igmp and Multicast MIB.
                       bit 8: value 1 means support a200mgcinfo in a200mgccfgTable.
                       bit 9: value 1 means support zxDslPortLocationIfaceDhcpv6Enable and Dhcpv6OptionTrust in zxDslPortLocationIfaceTable.
                       bit 10: value 1 means support IPV6.
                       bit 11: value 1 means support zxAnMvlanHostVersion.                       
                       bit 12: For port egress QoS policy, value 1 means support zxDslQosPortEgressPolicyTable.
                       bit 13: value 1 means support zxDslPortLocationIfaceCircuitIdSyntaxPrfName and zxDslPortLocationIfaceActualCircuitId
                               in zxDslPortLocationIfaceTable.             
                       bit 14: value 1 means support VdslDataRateTrap.            
                       bit 15: value 1 means support zxDslDhcpv6PvcIfIpSourceGuardEnable,zxDslDhcpv6IfDhcpSnoopingEnable and zxDslDhcpv6IfDhcpSnoopingLimit
                               for DHCPv6 in zxDslDhcpPvcIfTable and zxDslDhcpIfTable.      
                       bit 16: value 1 means flowcontrol inndependent to auto-negotiation.            
                       bit 17: value 1 means zxDslFtpManagedObjectType support DSL_PORT_INFO.      
                       bit 18: value 1 means support zxDslMacAddressExtTable. 
                       bit 19: value 1 means support pccw DSL_PORT_INFO (Modem Vendor, Modem Serial Number, Modem Firmware).  
                       bit 20: value 1 means support aturInitFailureTrapEnable of ADSL and atucInitFailureTrapEnable and aturInitFailureTrapEnable of VDSL.
                       bit 21: value 1 means support zxVoiceFlowStatisticRecordTime in zxVoipVoiceFlowStatisticTable.
                       bit 22: value 1 means support a200sipproxysvrPort in a200sipproxysvrTable and the range of a200sipproxysvrindex is 1..4.
                       bit 23: value 1 means support zxDslPortPppoeSyntaxPrfName and zxDslPortActPppoeCircuitId in zxDslPortLocationIfaceTable.
                       bit 24: value 1 means support a200slcFeedCurrent in a200slcTable and
                               msagSlcHighImpedacneOper and msagSlcNoneHighImpedanceOper in msagSlcCtrlTable.
                       bit 25: value 1 means support a200sipproxysvrInfo and a200sipproxysvrDomainName in a200sipproxysvrTable. 
                       bit 26: value 1 means support G.INP for VDSL Line.
                       bit 27: value 1 means support G.INP for ADSL Line.
                       bit 28: value 1 means support DPBO,PSDMASK(PSD mask) 
                               and TXREFVN(transmitter referred virtual noise)
                               for ADSL Line.
                       bit 29: value 1 means support zxDslDevSecAclDestIpType,
                               zxDslDevSecAclDestIp,
                               zxDslDevSecAclDestIpMask, 
                               zxDslDevSecAclDestIpv6PfxLen,
                               zxDslDevSecAclEtherType,
                               zxDslDevSecAclVlan 
                               and zxDslDevSecAclPktRateLimit
                               in zxDslDevSecurityAclTable.
                       bit 30: value 1 means support pccw DSL_PORT_INFO (Modem Mode).
                       "
              REFERENCE
                      ""
              ::= { zxDslSysCompatibility 1 }
END
