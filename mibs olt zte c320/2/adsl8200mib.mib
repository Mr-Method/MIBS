ZXDSLAM-MIB DEFINITIONS ::= BEGIN
IMPORTS
        MODULE-IDENTITY, TimeTicks,	OBJECT-TYPE,
		NOTIFICATION-TYPE, enterprises,IpAddress FROM SNMPv2-SMI
        DateAndTime  	FROM SNMPv2-TC
		atmVcCrossConnectIndex FROM ATM-MIB
		InterfaceIndex,ifEntry,ifIndex				FROM IF-MIB
		system                                      FROM RFC1213-MIB;
-- 		PhysicalIndex                  		  		FROM ENTITY-MIB;

zte MODULE-IDENTITY
LAST-UPDATED "2703200000Z"
ORGANIZATION ""
CONTACT-INFO ""
DESCRIPTION  "Initial Version"
::= { enterprises 5000 } 


zxDslam	    OBJECT IDENTIFIER ::= { zte 29 }
zxDslamAim  OBJECT IDENTIFIER ::= { zxDslam 1 }
zxDslamTrap OBJECT IDENTIFIER ::= { zxDslam 2 }
zxDslamCommon OBJECT IDENTIFIER ::= { zxDslam 3 }
zxDslamCommonLoad OBJECT IDENTIFIER ::= { zxDslamCommon 1 }
zxDslamCommonVer  OBJECT IDENTIFIER ::= { zxDslamCommon 2 }
zxDslamCommonData  OBJECT IDENTIFIER ::= { zxDslamCommon 3 }
zxDslamGroup	OBJECT IDENTIFIER ::= { zxDslam 4 }

zxCsv          OBJECT IDENTIFIER ::= { zte               1009  }                         
-- csv product
zxAccessProduct     OBJECT IDENTIFIER ::= { zxCsv        3     } 
-- access product

selfMake       OBJECT IDENTIFIER ::= { zxAccessProduct   1     }                        
-- self develop

zxCsvObj       OBJECT IDENTIFIER ::= { selfMake     1     }
-- csv product

zxCsvCmd       OBJECT IDENTIFIER ::= { zxCsvObj     1     }
-- csv command

zxCsvTrap      OBJECT IDENTIFIER ::= { zxCsvObj     2     }
-- csv trap
                      
zxEpm          OBJECT IDENTIFIER ::= { zte               1010  }
                      
                      
DisplayString ::= OCTET STRING


sysOutBandMacAddr OBJECT-TYPE
    SYNTAX      MacAddress
    MAX-ACCESS  read-only
    STATUS      current
    DESCRIPTION
            "system outBand hardware address."
    ::= { system 8 }


sysInBandMacAddr OBJECT-TYPE
    SYNTAX  MacAddress
    MAX-ACCESS  read-only
    STATUS      current
    DESCRIPTION
            "system inBand hardware address."
    ::= { system 9 }

sysUpLinks OBJECT-TYPE
    SYNTAX      INTEGER (0..4096)
    MAX-ACCESS  read-only
    STATUS      current
    DESCRIPTION
            "system current up links."
    ::= { system 10 }



-- the card table

zxDslamCardTable OBJECT-TYPE
	SYNTAX		SEQUENCE OF ZxDslamCardEntry
	MAX-ACCESS	not-accessible
	STATUS		current
	DESCRIPTION	"A list of card entries."
	::= { zxDslamAim 1 }

zxDslamCardEntry OBJECT-TYPE
	SYNTAX		ZxDslamCardEntry
	MAX-ACCESS	not-accessible
	STATUS		current
	DESCRIPTION	
        "An card entry containing objects describing the card in some slot."
	INDEX	{ zxDslamCardIndex }
	::= { zxDslamCardTable 1 }

ZxDslamCardEntry ::= SEQUENCE {
    zxDslamCardIndex				INTEGER,
    zxDslamCardType				INTEGER,
    zxDslamCardFrame       INTEGER,
    zxDslamCardShelf       INTEGER,
    zxDslamCardSlot				INTEGER,
    zxDslamCardPortNum       INTEGER,
    zxDslamCardstandbyStatus         INTEGER,
   	zxDslamCardDescr				DisplayString,
    zxDslamCardAdminStatus		INTEGER,
    zxDslamCardOperStatus		INTEGER,
  	zxDslamCardLastChange		TimeTicks,
    zxDslamHardwareVersion             		DisplayString, 	
    zxDslamSoftwareVersion             		DisplayString
--  zxDslamCardEntPhysicalIndex	PhysicalIndex            
--    zxDslamBuildtimeVersion	           		DisplayString, 	
--    zxDslamBackupSoftwareVersion            DisplayString, 
--    zxDslamBackupBuildtimeVersion          	DisplayString, 	
--    zxDslamVersionNum				INTEGER,
--    zxDslamCardChipsOperStatus		INTEGER
	}

zxDslamCardIndex OBJECT-TYPE
	  SYNTAX		INTEGER
    MAX-ACCESS  not-accessible
    STATUS      current
    DESCRIPTION
          "The index for this entry."
	::= { zxDslamCardEntry 1 }

zxDslamCardType 	OBJECT-TYPE
	SYNTAX	INTEGER {
                unknown(0),  
                core(1),
                wan-ds3(2),
                wan-sdh(3),
                power(4),
	        atuc-ti(5),  -- ATUC card
        	atuc-al(6),  -- ATUC card
        	other(7) ,
        	corea (8),
                corec(9),
                wana1(10),
                wanad(11),
                wane(12),
                esu(13),
                atucd(14),
                atuce(15),
                atucf(16),
                atucg(17),
                atuch(18),
                atuci(19),
				ima(20),
				coreA2(21),
                coreB2(22),
                coreC2(23),
                coreA3(24),
                coreB3(25),
                coreC3(26),
                imab(27),
                lanaa(28),
                lanab(29),
                lanac(30),
                lanad(31),
                lanba(32),
                lanbb(33),
                lanca(34),
                lancb(35),
                lancc(36),
                lancd(37),
                landa(38),
                landb(39),
                stuca(40),
                atugi(41)
            }
	MAX-ACCESS	read-only
	STATUS		current
	DESCRIPTION	
   		"The type of card, distinguished according to 
		service type carried or function."
	::= { zxDslamCardEntry 2 }

zxDslamCardFrame   OBJECT-TYPE   
  SYNTAX  INTEGER
  MAX-ACCESS  read-only
  STATUS current
  DESCRIPTION	
		"The number of frame which contained this card."
	::= { zxDslamCardEntry 3 }
	
zxDslamCardShelf   OBJECT-TYPE   
  SYNTAX  INTEGER
  MAX-ACCESS read-only
  STATUS current
  DESCRIPTION	
		"The number of shelf which contained this card."
	::= { zxDslamCardEntry 4 }
	
zxDslamCardSlot	OBJECT-TYPE
 	SYNTAX		INTEGER
 	MAX-ACCESS	read-only
 	STATUS		current
 	DESCRIPTION	
		"The number of slot which contained this card."
 	::= { zxDslamCardEntry 5 }

zxDslamCardPortNum   OBJECT-TYPE
    SYNTAX   INTEGER
	MAX-ACCESS read-only
	STATUS    current
	DESCRIPTION	
		"The number of port which contained in this card."
 	::= { zxDslamCardEntry 6 }

zxDslamCardstandbyStatus   OBJECT-TYPE
	SYNTAX	INTEGER {
	            unknown(0),
	            single(1),
                    standby(2), 
                    master(3)                    
                }
	MAX-ACCESS	read-write
	STATUS		current
	DESCRIPTION	
		"The type of card, distinguished according to 
		service type carried  or function."
	::= { zxDslamCardEntry 7 }

zxDslamCardDescr OBJECT-TYPE
	SYNTAX		DisplayString (SIZE (0..255))
	MAX-ACCESS	read-only
	STATUS		current
    	DESCRIPTION	
		"A textual string containing information about the card.
		This string should include the manufacturer, 
		the product name, type, function and version of the hardware."
	::= { zxDslamCardEntry 8 }

zxDslamCardAdminStatus	OBJECT-TYPE
	SYNTAX	INTEGER {
				up(1),		-- ready
				down(2),	-- deactiivate
				testing(3)	-- in some test mode
			}
	MAX-ACCESS	read-write
	STATUS		current
	DESCRIPTION	
		"The desired state of the card. 
		The down (2) and testing (3) state indicate	
		the card doesn't present service currently."
	::= { zxDslamCardEntry 9 }
	
zxDslamCardOperStatus	OBJECT-TYPE
	SYNTAX	INTEGER {
				up(1),		-- ready
				down(2),	-- fault occur or pulled out from the slot
				testing(3)	-- in some test mode
			}
	MAX-ACCESS	read-only
	STATUS		current
	DESCRIPTION	
		"The current operational state of the card. 
		The down (2) and testing (3) mode indicate that 
		no service can be presented by the card."
	::= { zxDslamCardEntry 10 }

zxDslamCardLastChange	OBJECT-TYPE
	SYNTAX		TimeTicks
	MAX-ACCESS	read-only
	STATUS		current
	DESCRIPTION	
			"The value of sysUpTime at the time 
			the card entered its current operational state. 
			If the current state was entered prior to the last 
			reinitialization of the	local network management subsystem, 
			then this object contains a zero value."
	::= { zxDslamCardEntry 11 }
	
zxDslamHardwareVersion  OBJECT-TYPE
	SYNTAX		DisplayString (SIZE (0..32))
	MAX-ACCESS	read-only
	STATUS		current
        DESCRIPTION	"hardware Version of this card"
	::= { zxDslamCardEntry 12 } 
	
--zxDslamVersionNum	OBJECT-TYPE
--	SYNTAX      INTEGER (1..2)
--	MAX-ACCESS	read-only
--	STATUS		current
--	DESCRIPTION	
--		"version number."
--	::= { zxDslamCardEntry 13 }
	
zxDslamSoftwareVersion  OBJECT-TYPE
	SYNTAX		DisplayString (SIZE (0..32))
	MAX-ACCESS	read-only
	STATUS		current
        DESCRIPTION	"running software Version of this card"
	::= { zxDslamCardEntry 14 } 
	
--zxDslamBuildtimeVersion	OBJECT-TYPE
--	SYNTAX      DisplayString (SIZE (0..32))
--	MAX-ACCESS	read-only
--	STATUS		current
--	DESCRIPTION	
--		"running Version buildtime of this card."
--	::= { zxDslamCardEntry 15 }
--zxDslamBackupSoftwareVersion	OBJECT-TYPE
--	SYNTAX      DisplayString (SIZE (0..32))
--	MAX-ACCESS	read-only
--	STATUS		current
--	DESCRIPTION	
--		"backup software version."
--	::= { zxDslamCardEntry 16 }
--
--zxDslamBackupBuildtimeVersion	OBJECT-TYPE
--	SYNTAX      DisplayString (SIZE (0..32))
--	MAX-ACCESS	read-only
--	STATUS		current
--	DESCRIPTION	
--		"backup version buildtime."
--	::= { zxDslamCardEntry 17 }
	

--zxDslamCardChipsOperStatus	OBJECT-TYPE
--	SYNTAX      INTEGER (0..63)
--	MAX-ACCESS	read-only
--	STATUS		current
--	DESCRIPTION	
--		"The current operational state of the card chips. 
--		!!!!!!!!!!!!!!!!!The down (2) and testing (3) mode indicate that 
--		no service can be presented by the card."
--	::= { zxDslamCardEntry 18 }
	

-- definition of 
-- definition of zxDslamPortIfIndexMappingTable

zxDslamPortIfIndexMappingTable OBJECT-TYPE
	SYNTAX		SEQUENCE OF ZxDslamPortIfIndexMappingEntry
	MAX-ACCESS		not-accessible
	STATUS		current
	DESCRIPTION
		"zxDslamPortIfIndexMappingTable  is used to show the mapping from 
		Port	to ifIndex."
	::= {zxDslamAim 2 }

zxDslamPortIfIndexMappingEntry	OBJECT-TYPE
	SYNTAX		ZxDslamPortIfIndexMappingEntry
	MAX-ACCESS		not-accessible
	STATUS		current
	DESCRIPTION
		"An entry in the zxDslamPortIfIndexMappingTable. There is one 
		 entry  in the table corresponding to each active row in the
		 ifTable for which there is a non-zero cpn and ifindex."
	INDEX	{ zxDslamMappingFrame,zxDslamMappingShelf,
	zxDslamMappingSlot,zxDslamMappingPort,zxDslamPortMappingifIndex}
	::= {zxDslamPortIfIndexMappingTable 1 }

ZxDslamPortIfIndexMappingEntry	::= SEQUENCE {
	zxDslamMappingFrame INTEGER,
	zxDslamMappingShelf INTEGER,
	zxDslamMappingSlot  INTEGER,
    zxDslamMappingPort  INTEGER,
    zxDslamPortMappingifIndex       InterfaceIndex
}

zxDslamMappingFrame    OBJECT-TYPE
    SYNTAX  INTEGER
    MAX-ACCESS  not-accessible
    STATUS      current
    DESCRIPTION
            "The sub-index for this entry."
  ::= {zxDslamPortIfIndexMappingEntry 1 } 
zxDslamMappingShelf    OBJECT-TYPE
    SYNTAX  INTEGER
    MAX-ACCESS  not-accessible
    STATUS      current
    DESCRIPTION
            "The sub-index for this entry."
  ::= {zxDslamPortIfIndexMappingEntry 2 } 
zxDslamMappingSlot     OBJECT-TYPE
    SYNTAX  INTEGER
    MAX-ACCESS  not-accessible
    STATUS      current
    DESCRIPTION
            "The sub-index for this entry."
  ::= {zxDslamPortIfIndexMappingEntry 3 } 
zxDslamMappingPort     OBJECT-TYPE
    SYNTAX  INTEGER
    MAX-ACCESS  not-accessible
    STATUS      current
    DESCRIPTION
            "The sub-index for this entry."
  ::= {zxDslamPortIfIndexMappingEntry 4 }             
  
zxDslamPortMappingifIndex	OBJECT-TYPE
	SYNTAX			InterfaceIndex
	MAX-ACCESS		read-only
	STATUS			current
	DESCRIPTION
		 "The value of InterfaceIndex of the same circuitnum."
	::= {zxDslamPortIfIndexMappingEntry 5 } 
--		
-- zxDslamSysDateAndTime	OBJECT-TYPE
--	SYNTAX		DateAndTime
--	MAX-ACCESS	read-write
--	STATUS		current
--	DESCRIPTION	"The system time of ZX Dslam "
--	::= { zxDslamAim 3 }
 
zxDslamCardNumber  OBJECT-TYPE
  SYNTAX		INTEGER
  MAX-ACCESS read-only
  STATUS  current
  DESCRIPTION	"The  Cards number of ZX Dslam "
  ::= {zxDslamAim 4 }

zxDslamVcxSubscriberMappingTable OBJECT-TYPE
  SYNTAX		SEQUENCE OF ZxDslamVcxSubscriberMappingEntry
  MAX-ACCESS		not-accessible
  STATUS		current
  DESCRIPTION
	"zxDslamSubscriberVcxIndexMappingTab  is used to show the mapping from 
	Vcx	to subscriber name."
  ::= {zxDslamAim 5 }

zxDslamVcxSubscriberMappingEntry OBJECT-TYPE
    SYNTAX		ZxDslamVcxSubscriberMappingEntry
	MAX-ACCESS		not-accessible
	STATUS		current
	DESCRIPTION
		"An entry in the zxDslamVcxSubscriberMappingTable. There is one 
		 entry  in the table corresponding to each active row in the
		 AtmVcCrossConnectTable, there is subscriber name."
	INDEX	{atmVcCrossConnectIndex }
	::= {zxDslamVcxSubscriberMappingTable 1 } 

ZxDslamVcxSubscriberMappingEntry ::= SEQUENCE {
	zxDslamVcxSubscribeName DisplayString	
}

zxDslamVcxSubscribeName OBJECT-TYPE
  SYNTAX	DisplayString(SIZE(0..32))
  MAX-ACCESS read-write
  STATUS  current
  DESCRIPTION	"The  subscriber name of vcx "
  ::= {zxDslamVcxSubscriberMappingEntry 1 }   

zxDslamCommandTable        OBJECT-TYPE
     SYNTAX         SEQUENCE OF ZxDslamCommandEntry
     MAX-ACCESS     not-accessible
     STATUS         current
     DESCRIPTION
        	"The ZXDslam command Execute table. "
     ::= {zxDslamAim 6 }

zxDslamCommandEntry		OBJECT-TYPE
     SYNTAX         ZxDslamCommandEntry
     MAX-ACCESS     not-accessible
     STATUS         current
     DESCRIPTION
		"An entry in the ZXDslam command Execute table  "
     INDEX  {  zxDslamCommandType }	
     ::= { zxDslamCommandTable  1}

ZxDslamCommandEntry  ::= SEQUENCE  {
     zxDslamCommandType			INTEGER ,
     zxDslamCommandLastChange	TimeTicks ,
     zxDslamCommandStatus	    INTEGER
  }
	
	
zxDslamCommandType			OBJECT-TYPE
     SYNTAX          INTEGER 	{	
                saveAdslFlash(1),
		saveAtmFlash(2),
		saveSysFlash(3),
		initAdslFlash(4),
		initAtmFlash(5),
		initSysFlash(6),
		swich(7),
		sysReboot(8),
		download(9),
		switchVer(10),
		creatPvcGroup(11),
		deletePvcAll(12),
		disablePvcGroup(13),
		enablePvcGroup(14),
		setLinGroup(15),
        enableLinGroup(16),
        disableLinGroup(17),
		setAlamGroup(18),
		resetDslGroup(19),
		resetCardGroup(20),
		getCoreData(21),
		pushCoreData(22),
		setVdslLinGroup(23),
		setCliDefautPassword(24)		
	        }
	MAX-ACCESS     read-only
	STATUS         current
	DESCRIPTION
			" The operation type of the commands."
	::= { zxDslamCommandEntry	1}
	

zxDslamCommandLastChange	OBJECT-TYPE
	SYNTAX         TimeTicks
	MAX-ACCESS     read-only
	STATUS         current
	DESCRIPTION
		  "The value of MIB-II's sysUpTime at the time this
                   Command is excuted.	When the command hasn't been excuted,
	           the value is always  zero. " 
          ::= { zxDslamCommandEntry	2 }

zxDslamCommandStatus		OBJECT-TYPE
        SYNTAX    INTEGER 	{	
         			cmdNeverExecuted(0),
 				lastCmdSuccessfulExecuted(1),
				lastCmdFailed(2),
				executing(3),
				execute(4)
				}
	MAX-ACCESS     read-write
	STATUS         current
	DESCRIPTION
		" Indicates the status of this type of command
			When the command hasn't been excuted,
		        the value is always  zero. 	
		        If want to execute the command , the manager should 
			        set the value to Execute(3)	."
	DEFVAL { 0 }
	::= {zxDslamCommandEntry 3}
zxDslamSystemVersion OBJECT-TYPE
	SYNTAX		DisplayString (SIZE (0..64))
	MAX-ACCESS	read-only
	STATUS		current
        DESCRIPTION	"the Dslam System Version of this card."
::= {zxDslamAim 7 }

zxDslamSnmpManagerServerIpAddress OBJECT-TYPE
	SYNTAX		IpAddress
	MAX-ACCESS	read-write
	STATUS		current
        DESCRIPTION	"The IpAddress of the Snmp Manager Server for Trap."
::= {zxDslamAim 8 }

--Fan Table
zxDslamFanTable  OBJECT-TYPE
     SYNTAX         SEQUENCE OF ZxDslamFanEntry
     MAX-ACCESS     not-accessible
     STATUS         current
     DESCRIPTION
        	"The ZXDslam fan table. "
     ::= {zxDslamAim 9 }

zxDslamFanEntry	    OBJECT-TYPE
     SYNTAX         ZxDslamFanEntry   
     MAX-ACCESS     not-accessible
     STATUS         current
     DESCRIPTION
		"An entry in the ZXDslam fan table  "
     INDEX  {  zxDslamFanIndex }	
     ::= { zxDslamFanTable  1}

ZxDslamFanEntry  ::= SEQUENCE  {
     zxDslamFanIndex		INTEGER ,
     zxDslamFanLastChange	TimeTicks ,
     zxDslamFanOperStatus	    INTEGER
  }
	
zxDslamFanIndex		OBJECT-TYPE
        SYNTAX          INTEGER
        MAX-ACCESS     not-accessible
	STATUS         current
	DESCRIPTION
		" The Identifier of the fan."
	::= { zxDslamFanEntry	1}
	

zxDslamFanLastChange	OBJECT-TYPE
	SYNTAX         TimeTicks
	MAX-ACCESS     read-only
	STATUS         current
	DESCRIPTION
		  "The value of MIB-II's sysUpTime at the time this
                   entry changes.	When the fan hasn't been changed,
	           the value is always  zero. " 
          ::= { zxDslamFanEntry	2 }

zxDslamFanOperStatus	    OBJECT-TYPE
        SYNTAX    INTEGER 	{	
         	               up(1),
         	               down(2)
				}
	MAX-ACCESS     read-only
	STATUS         current
	DESCRIPTION
		" Indicates the status of this fan."
	DEFVAL { 2 }
	::= {zxDslamFanEntry 3}
zxDslamFanNumber OBJECT-TYPE
        SYNTAX	INTEGER
        MAX-ACCESS read-only
        STATUS  current
        DESCRIPTION	"The  fan number of ZX Dslam "
        DEFVAL {6}
  ::= {zxDslamAim  10}
  
zxDslamPowerTable OBJECT-TYPE
     SYNTAX         SEQUENCE OF ZxDslamPowerEntry  
     MAX-ACCESS     not-accessible
     STATUS         current
     DESCRIPTION
        	"The ZXDslam power table. "
     ::= {zxDslamAim 11 }

zxDslamPowerEntry   OBJECT-TYPE
     SYNTAX         ZxDslamPowerEntry   
     MAX-ACCESS     not-accessible
     STATUS         current
     DESCRIPTION
		"An entry in the ZXDslam Power table  "
     INDEX  {  zxDslamPowerIndex }  
     ::= { zxDslamPowerTable  1}

ZxDslamPowerEntry  ::= SEQUENCE  {    
     zxDslamPowerIndex		INTEGER ,
     zxDslamPowerLastChange	TimeTicks ,
     zxDslamPowerOperStatus	INTEGER
  }
	
zxDslamPowerIndex	OBJECT-TYPE
        SYNTAX          INTEGER
        MAX-ACCESS      not-accessible
	STATUS          current
	DESCRIPTION
		" The Identifier of the power."
	::= { zxDslamPowerEntry	1}
	

zxDslamPowerLastChange	OBJECT-TYPE
	SYNTAX         TimeTicks
	MAX-ACCESS     read-only
	STATUS         current
	DESCRIPTION
		  "The value of MIB-II's sysUpTime at the time this
                   power changes. When the power hasn't been changed,
	           the value is always  zero. " 
          ::= { zxDslamPowerEntry 2 }

  zxDslamPowerOperStatus		OBJECT-TYPE 
	SYNTAX    INTEGER  {	
				up(1), 
	 			down(2) 
			   } 
	MAX-ACCESS     read-only 
	STATUS         current 
	DESCRIPTION 
		"Indicates the status of this power." 
	DEFVAL { down } 
	::= {zxDslamPowerEntry 3}
	
    zxDslamPowerNumber OBJECT-TYPE         
	SYNTAX		INTEGER 
	MAX-ACCESS 	read-only
  	STATUS  	current 
	DESCRIPTION	
		"The  Power number of ZX Dslam " 
	DEFVAL {2} 
	::={zxDslamAim  12}
  

    zxDslamifTable        OBJECT-TYPE
       SYNTAX      SEQUENCE OF ZxDslamIfEntry
       MAX-ACCESS  not-accessible
       STATUS      current
       DESCRIPTION
               "A list of interface entries for sdh interface(ifType = ifType = VAL_ifType_sonet ,
                VAL_ifType_sonetPath).  This table contains additional objects for the interface table of sdh interface."
       ::= { zxDslamAim 13 }

     zxDslamifEntry        OBJECT-TYPE
       SYNTAX      ZxDslamIfEntry
       MAX-ACCESS  not-accessible
       STATUS      current
       DESCRIPTION
               "An entry containing additional management information
               applicable to a sdh 155M interface."
       AUGMENTS    { ifEntry }
       ::= { zxDslamifTable 1 }
       
      ZxDslamIfEntry  ::= SEQUENCE  {    
        zxDslamIfTxOperStatus	INTEGER,
        zxDslamIfRxOperStatus	INTEGER
      }
     
      zxDslamIfTxOperStatus OBJECT-TYPE
         SYNTAX  INTEGER {
                   up(1),        -- ready to pass packets
                   down(2),
                   testing(3)   -- in some test mode
               }
        MAX-ACCESS  read-only
        STATUS      current
        DESCRIPTION
               "The current Tx direction operational state of the sdh  interface.
               If sdh interface recieve LRDI or PRDI signal ,it will change to be down"
        ::= { zxDslamifEntry 1 }
       
      zxDslamIfRxOperStatus OBJECT-TYPE
        SYNTAX  INTEGER {
                   up(1),        -- ready to pass packets
                   down(2),
                   testing(3)   -- in some test mode
               }
       MAX-ACCESS  read-only
       STATUS      current
       DESCRIPTION
               "The current rx direction operational state of the sdh  interface.
               if sdh interface can't receive the signal from its peer(LOS) , it will 
               change to be down "
       ::= { zxDslamifEntry 2 }
       
    zxDslamConfigureDataSynStatus     OBJECT-TYPE
       SYNTAX      INTEGER{
                    outOfSyn(1),
                    synchronizing(2),
                    inSyn(3)
       }
       MAX-ACCESS  read-only
       STATUS      current
       DESCRIPTION
       "1 sigle core running,it's value is outOfSyn(1)
        2 when tow core running ,synchronizing(2) means starting syn
        3 when syn completed ,the value changes to be inSyn(3)"
        
       ::= { zxDslamAim 14 }     

      zxDslamNetWorkUserNum     OBJECT-TYPE
       SYNTAX      INTEGER
       MAX-ACCESS  read-only
       STATUS      current
       DESCRIPTION
       "stat the networks usr number "      
       ::= { zxDslamAim 15 }  
       

      zxDslamLinkupNumTable     OBJECT-TYPE
       SYNTAX      SEQUENCE OF ZxDslamLinkupNumEntry
       MAX-ACCESS  not-accessible
       STATUS      current
       DESCRIPTION
       "The linkup-num of adsl users "      
       ::= { zxDslamAim 16 }      
       
       zxDslamLinkupNumEntry        OBJECT-TYPE
       SYNTAX      ZxDslamLinkupNumEntry
       MAX-ACCESS  not-accessible
       STATUS      current
       DESCRIPTION
               "An Entry of linkup-num of adsl users "    
       INDEX  { ifIndex }  
       ::= { zxDslamLinkupNumTable 1 }
       
      ZxDslamLinkupNumEntry  ::= SEQUENCE  {    
        zxDslamLinkupNum	INTEGER
      }
     
      zxDslamLinkupNum OBJECT-TYPE
         SYNTAX  INTEGER 
        MAX-ACCESS  read-write
        STATUS      current
        DESCRIPTION
               "linkup num of a port"
        ::= { zxDslamLinkupNumEntry 1 }
       
     zxDslamSplitterStatus     OBJECT-TYPE
       SYNTAX      INTEGER
       MAX-ACCESS accessible-for-notify
       STATUS      current
       DESCRIPTION
       "the status of splitter board"      
       ::= { zxDslamAim 17 }  
        
       zxDslamSynchDataLanLocate     OBJECT-TYPE
   	SYNTAX  INTEGER 
        MAX-ACCESS  read-write
        STATUS      current
        DESCRIPTION
               "the board locatation flag for synch lan data "
         
       ::= { zxDslamAim 18 } 
      
     zxDslamVersionId     OBJECT-TYPE
       SYNTAX      INTEGER
       MAX-ACCESS  read-only
       STATUS      current
       DESCRIPTION
       "the cores version id "      
       ::= { zxDslamAim 19 }  
       
     zxDslamWandSurMulticast     OBJECT-TYPE
       SYNTAX      INTEGER
       MAX-ACCESS  read-write
       STATUS      current
       DESCRIPTION
       "support iptv wand card index"      
       ::= { zxDslamAim 20 }        
 

  zxDslamCommonLoadTftpAddress OBJECT-TYPE
        SYNTAX IpAddress
        MAX-ACCESS read-write
        STATUS current
        DESCRIPTION
            "DURABLE:
             The IP Address for the TFTP server used for downloading
             and/or uploading files." 
        ::= { zxDslamCommonLoad 1 }

    zxDslamCommonLoadTftpFileName OBJECT-TYPE
        SYNTAX DisplayString (SIZE (1..64))
        MAX-ACCESS read-write
        STATUS current
        DESCRIPTION
            "DURABLE:
             The TFTP file path and name."
        ::= { zxDslamCommonLoad 2 }
        
    
    zxDslamCommonLoadExecuteStatus OBJECT-TYPE
        SYNTAX INTEGER {
               notStarted(1),       -- download has not yet started
               inProgress(2),       -- download has not yet finished
               success(3),          -- download has finished successfully
               errorConnection(4),  -- download cannot connect
               errorFilename(5),    -- download has bad image path/filename
               errorFault(6)        -- download has fault condition on device
        }
        MAX-ACCESS read-only 
        STATUS current
        DESCRIPTION
            "Provides status on the execute file load progress."
        ::= { zxDslamCommonLoad 3 }
      
   zxDslamCommonVerInforTable   OBJECT-TYPE
        SYNTAX SEQUENCE OF ZxDslamCommonVerInforEntry
        MAX-ACCESS not-accessible
        STATUS current
        DESCRIPTION
            "A table of version information in flash."
        ::= { zxDslamCommonVer 1 }

    zxDslamCommonVerInforEntry OBJECT-TYPE
        SYNTAX ZxDslamCommonVerInforEntry
        MAX-ACCESS not-accessible
        STATUS current
        DESCRIPTION
            "A list of version in flash."
        INDEX { zxDslamCommonVerIndex }
        ::= { zxDslamCommonVerInforTable 1 }

    ZxDslamCommonVerInforEntry ::= SEQUENCE {
        zxDslamCommonVerIndex           INTEGER,
        zxDslamCommonVersion            DisplayString,
        zxDslamCommonVerFileName        DisplayString,
        zxDslamCommonVerReleaseDate     DisplayString,
        zxDslamCommonVerCurrStatus      INTEGER
    }
    zxDslamCommonVerIndex  OBJECT-TYPE
        SYNTAX         INTEGER
        MAX-ACCESS  not-accessible
        STATUS current
        DESCRIPTION 
             "The index of version in flash"  
        ::= { zxDslamCommonVerInforEntry 1 }     
        
    zxDslamCommonVersion  OBJECT-TYPE
        SYNTAX         DisplayString(SIZE(1..32))
        MAX-ACCESS     read-only
        STATUS current
        DESCRIPTION 
             "The number of version in flash"  
        ::= { zxDslamCommonVerInforEntry 2 }                  
    zxDslamCommonVerFileName  OBJECT-TYPE
        SYNTAX         DisplayString(SIZE(1..32))
        MAX-ACCESS     read-only
        STATUS current
        DESCRIPTION 
             "The  file name of version in flash"  
        ::= { zxDslamCommonVerInforEntry 3 }
        
   zxDslamCommonVerReleaseDate   OBJECT-TYPE
        SYNTAX         DisplayString(SIZE(1..32))
        MAX-ACCESS     read-only
        STATUS current
        DESCRIPTION 
             "The release date of version in flash"  
        ::= { zxDslamCommonVerInforEntry 4 }                  
        
   zxDslamCommonVerCurrStatus  OBJECT-TYPE
        SYNTAX         INTEGER
                       {
                          notAvailable(0), 
                          running(1),
                          backup(2)
                       }
        MAX-ACCESS     read-only
        STATUS current
        DESCRIPTION 
             "The current status of version in flash"  
        ::= { zxDslamCommonVerInforEntry 5 }   


zxDslamCommonDataFtpAddress OBJECT-TYPE
        SYNTAX IpAddress
        MAX-ACCESS read-write
        STATUS current
        DESCRIPTION
            "DURABLE:
             The IP Address for the TFTP server used for downloading
             and/or uploading files." 
        ::= { zxDslamCommonData 1 }

   zxDslamCommonDataTableIndex OBJECT-TYPE
        SYNTAX INTEGER { 
		ifTable(1),
		adslLineTable (2),
		adslLineConfProfileTable(3),
		adslLineAlarmConfProfileTable(4),
		adslAtucChanTable(5),
		adslAturChanTable(6),
		adslAtucPhysTable(7),
		adslAturPhysTable(8),
		atmTrafficDescrParamTable(9),
		atmVclTable(10),
		atmVcCrossConnectTable(11),
		zxDslamVcxSubscriberMappingTable(12),
		zxDslamCardTable(13),
		zxDslamPortIfIndexMappingTable(14),
		hdsl2ShdslSpanConfTable(15),
		hdsl2ShdslSpanConfProfileTable(16),
        hdsl2ShdslEndpointAlarmConfProfileTable(17),
        hdsl2ShdslEndpointConfTable(18),

		adslflash(19),
		systemflash(20),
		atmflash(21),
		shdslflash(22),
		wanbflash(23),

        wanedata(24),
        waneconfig(25),

        imaadata(26),
        imaaconfig(27),

        imabdata(28),
        imabconfig(29),

        lanadata(30),
        lanaconfig(31),

        wanddata(32),
        wandconfig(33),

        wandbdata(34),
        wandbconfig(35)
        
               }
        MAX-ACCESS read-write
        STATUS current
        DESCRIPTION
            " Table Index."
    ::= { zxDslamCommonData 2 }


    zxDslamCommonDataFtpFilePath OBJECT-TYPE
        SYNTAX DisplayString (SIZE (1..64))
        MAX-ACCESS read-write
        STATUS current
        DESCRIPTION
            "
             The FTP File Path."
        ::= { zxDslamCommonData 3 }

    zxDslamCommonDataFtpUserName OBJECT-TYPE
        SYNTAX DisplayString (SIZE (1..64))
        MAX-ACCESS read-write
        STATUS current
        DESCRIPTION
            "The FTP username."
    ::= { zxDslamCommonData 4 }
    
    zxDslamCommonDataFtpUserPassword OBJECT-TYPE
        SYNTAX DisplayString (SIZE (1..64))
        MAX-ACCESS read-write
        STATUS current
        DESCRIPTION
            "
             The FTP User Password."
    ::= { zxDslamCommonData 5 }

    zxDslamCommonDataFtpFileName OBJECT-TYPE
        SYNTAX DisplayString (SIZE (1..64))
        MAX-ACCESS read-write
        STATUS current
        DESCRIPTION
            "
             The FTP file path and name."
    ::= { zxDslamCommonData 6 }

   zxDslamCommonDataExecuteStatus OBJECT-TYPE
        SYNTAX INTEGER { 
               notStarted(1),       -- download has not yet started
               inProgress(2),       -- download has not yet finished
               success(3),          -- download has finished successfully
               errorConnection(4),  -- download cannot connect
               errorFilename(5),    -- download has bad image path/filename
               errorFault(6) ,       -- download has fault condition on device
               errorUsername(7),    -- 
               errorUserPassword(8) --
               }
        MAX-ACCESS read-only
        STATUS current
        DESCRIPTION
            "  operatioanl status."
    ::= { zxDslamCommonData 7 }
               
-- zxDslamGroup subtree 
--This sub tree is for group operation. operations is: 
	--creatPvcGroup(9)
	--deletePvcAll(10)
	--disablePvcGroup(11)
	--enablePvcGroup(12)
	--setLinGroup(13)
	--enableLinGroup(14)
	--disableLinGroup(15)
	--setAlamGroup(16)

	zxDslamFromAtucCard	OBJECT-TYPE
		SYNTAX		INTEGER (1..34)
		MAX-ACCESS	read-write
		STATUS		current
		DESCRIPTION	"The number of ATUC card to config from"
		::= { zxDslamGroup 1 }

	zxDslamToAtucCard	OBJECT-TYPE
		SYNTAX		INTEGER (1..34)
		MAX-ACCESS	read-write
		STATUS		current
		DESCRIPTION	"The number of ATUC card to config last"
		::= { zxDslamGroup 2 }


	zxDslamAtucVpi	OBJECT-TYPE
		SYNTAX		INTEGER (0..255)
		MAX-ACCESS	read-write
		STATUS		current
		DESCRIPTION	"The vpi created for ATUC card"
		::= { zxDslamGroup 3 }


	zxDslamFromAtucVci	OBJECT-TYPE
		SYNTAX		INTEGER (32..65535)
		MAX-ACCESS	read-write
		STATUS		current
		DESCRIPTION	"The vci created from for ATUC card"
		::= { zxDslamGroup 4 }

	zxDslamAtucVcxNum	OBJECT-TYPE
		SYNTAX		INTEGER (1..65535)
		MAX-ACCESS	read-write
		STATUS		current
		DESCRIPTION	"The number of VCXs of every port "
		::= { zxDslamGroup 5 }

	zxDslamVclTrafficIndex	OBJECT-TYPE
		SYNTAX		INTEGER (1..20)
		MAX-ACCESS	read-write
		STATUS		current
		DESCRIPTION	"The vcl traffic index "
		::= { zxDslamGroup 6 }

	zxDslamWanPort	OBJECT-TYPE
		SYNTAX		INTEGER (1..2)
		MAX-ACCESS	read-write
		STATUS		current
		DESCRIPTION	"port numer for WANE/WANA card "
		::= { zxDslamGroup 7 }


	zxDslamFromWanVpi	OBJECT-TYPE
		SYNTAX		INTEGER (0..255)
		MAX-ACCESS	read-write
		STATUS		current
		DESCRIPTION	"The vpi created from for WANE/WANA card"
		::= { zxDslamGroup 8 }

	zxDslamToWanVpi	OBJECT-TYPE
		SYNTAX		INTEGER (0..255)
		MAX-ACCESS	read-write
		STATUS		current
		DESCRIPTION	"The vpi created last for WANE/WANA card"
		::= { zxDslamGroup 9 }

	zxDslamFromWanVci	OBJECT-TYPE
		SYNTAX		INTEGER (0..65535)
		MAX-ACCESS	read-write
		STATUS		current
		DESCRIPTION	"The vci created from for WANE/WANA card"
		::= { zxDslamGroup 10 }

	zxDslamToWanVci	OBJECT-TYPE
		SYNTAX		INTEGER (0..65535)
		MAX-ACCESS	read-write
		STATUS		current
		DESCRIPTION	"The vci created last for WANE/WANA card"
		::= { zxDslamGroup 11 }

	zxDslamAtucVcxName	OBJECT-TYPE
		SYNTAX		DisplayString (SIZE (0..100))
		MAX-ACCESS	read-write
		STATUS		current
		DESCRIPTION	"The name head of VCX "
		::= { zxDslamGroup 12 }

	zxDslamLineCoding	OBJECT-TYPE
		SYNTAX		INTEGER {
					gdmt (2),
					glite(5)
					}
		MAX-ACCESS	read-write
		STATUS		current
		DESCRIPTION	"The type of linecode"
		::= { zxDslamGroup 13 }

	zxDslamLineType	OBJECT-TYPE
		SYNTAX		INTEGER {
					fastOnly(2), 
					interleaveOnly(3)
					}
		MAX-ACCESS	read-write
		STATUS		current
		DESCRIPTION	"The type of linetype"
		::= { zxDslamGroup 14 }


	 	zxDslamAdslLineProfile	OBJECT-TYPE
		SYNTAX		DisplayString (SIZE (0..32))
		MAX-ACCESS	read-write
		STATUS		current
		DESCRIPTION	"A textual string containing profile filename,
		             the file should include the information about
					 ADSL line configration."
		::= { zxDslamGroup 15 }

	 	zxDslamAdslLineAlarmProfile	OBJECT-TYPE
		SYNTAX		DisplayString (SIZE (0..32))
		MAX-ACCESS	read-write
		STATUS		current
		DESCRIPTION	"A textual string containing profile filename,
		             the file should include the information about
					 ADSL line alarm configration."
		::= { zxDslamGroup 16 }
		
		zxDslamLocalCard  OBJECT-TYPE
		SYNTAX		INTEGER (1..2)
		MAX-ACCESS	read-write
		STATUS		current
		DESCRIPTION	"The slot which the WANE card on"
		::= { zxDslamGroup 17 }

--end define zxDslamGroup
         
         
         

-- Epm command table
zxEpmOnOff  OBJECT-TYPE
  SYNTAX      INTEGER { off(0), on(1) }
  MAX-ACCESS read-write
  STATUS  current
  DESCRIPTION	"Enables and disables this Epm control function.  
                 This object is defaulted off(2)."
  ::= {zxEpm 1 }

zxEpmCmdTable OBJECT-TYPE
	SYNTAX		SEQUENCE OF ZxEpmCmdEntry
	MAX-ACCESS	not-accessible
	STATUS		current
	DESCRIPTION	"A list of epm command."
	::= { zxEpm 2 }

zxEpmCmdEntry OBJECT-TYPE
	SYNTAX		ZxEpmCmdEntry
	MAX-ACCESS	not-accessible
	STATUS		current
	DESCRIPTION	
        "An command entry containing objects describing the epm control command."
	INDEX	{ zxEpmCmdIndex }
	::= { zxEpmCmdTable 1 }

ZxEpmCmdEntry ::= SEQUENCE {
    zxEpmCmdIndex	INTEGER,
    zxEpmCmdtype        OCTET STRING,
    zxEpmCmdEnable	INTEGER,
    zxEpmCmdLength      INTEGER
            
}

zxEpmCmdIndex OBJECT-TYPE
    SYNTAX	INTEGER
    MAX-ACCESS  not-accessible
    STATUS      current
    DESCRIPTION
          "The index for this entry."
	::= { zxEpmCmdEntry 1 }

zxEpmCmdtype 	OBJECT-TYPE
    SYNTAX      OCTET STRING(SIZE(32))
	MAX-ACCESS	read-write
	STATUS		current
	DESCRIPTION	
   		"The command for control the epm alarm."
	::= { zxEpmCmdEntry 2 }

zxEpmCmdEnable   OBJECT-TYPE   
    SYNTAX      INTEGER { enabled(1), disabled(2) }
    MAX-ACCESS  read-write
    STATUS current
    DESCRIPTION	
		"Enables and disables this alarm.  This
                 object is defaulted disable(2)."
	::= { zxEpmCmdEntry 3 }
         
zxEpmCmdLength   OBJECT-TYPE   
    SYNTAX      INTEGER 
    MAX-ACCESS  read-write
    STATUS current
    DESCRIPTION	
		"the length of the command"
	::= { zxEpmCmdEntry 4 }         

         
-- zxDslamTrap 
zxDslamCardUp	NOTIFICATION-TYPE
    OBJECTS   {  zxDslamCardOperStatus }
    STATUS    current
    DESCRIPTION 
		"A cardUp trap signifies that the SNMP agent has detectd 
		that the cardOperStatus object for the card has transitioned 
		out of the down state.This trap indicates that some card has 
		recovered from fault or been inserted into one switch slot"
     ::= { zxDslamTrap 0 1 }

zxDslamCardDown 	NOTIFICATION-TYPE
    OBJECTS   { zxDslamCardOperStatus }
    STATUS    current
    DESCRIPTION	
		"A cardDown trap signifies that the SNMP agent has deected that 
		the cardOperStatus object for the card has transitioned into 
		the down state. This trap indicates that some card has occured 
		fault or been pulled out from one switch slot."
     ::= { zxDslamTrap 0 2 }
     
zxDslamCommandTabStatusLastChange NOTIFICATION-TYPE
    OBJECTS   { zxDslamCommandStatus }
    STATUS    current
    DESCRIPTION	
		"This trap signifies that the SNMP agent has detected that 
		the zxDslamCommandStatus object for the command has been changed."
     ::= { zxDslamTrap 0 3 }

zxDslamCoreStandbyStatusChange NOTIFICATION-TYPE
    OBJECTS   { zxDslamCardstandbyStatus }
    STATUS    current
    DESCRIPTION	
		"This trap signifies that the SNMP agent has detected that the	
		zxDslamCardstandbyStatus object for the core card has been changed."
     ::= { zxDslamTrap 0 4 }
     
zxDslamFanOperStatusChange NOTIFICATION-TYPE
    OBJECTS   { zxDslamFanOperStatus}
    STATUS    current
    DESCRIPTION	
		"This trap signifies that the SNMP agent has detected that the	
		zxDslamFanOperStatus object for the fan has been changed."
     ::= { zxDslamTrap 0 5 }
     
zxDslamPowerOperStatusChange NOTIFICATION-TYPE
    OBJECTS   { zxDslamPowerOperStatus }
    STATUS    current
    DESCRIPTION	
		"This trap signifies that the SNMP agent has detected that the	
		zxDslamPowerOperStatus object for the power has been changed."
     ::= { zxDslamTrap 0 6 }
     
zxDslamConfigureDataSynStatusChange NOTIFICATION-TYPE
    OBJECTS   { zxDslamConfigureDataSynStatus }
    STATUS    current
    DESCRIPTION	
		"This trap signifies that the SNMP agent has detected that the	
		zxDslamCofigureDataSynStatus object for the syn Status has been changed."
     ::= { zxDslamTrap 0 7 }

zxDslamChipDown 	NOTIFICATION-TYPE
    OBJECTS   { zxDslamCardChipsOperStatus }
    STATUS    current
    DESCRIPTION	
		"!A chipDown trap signifies that the SNMP agent has deected that 
		the cardChipsOperStatus object for the card chip has transitioned into 
		the down state. This trap indicates that some card chip has occured 
		fault."
     ::= { zxDslamTrap 0 8 }

zxCsvNmSendToCsvMessage OBJECT-TYPE
     SYNTAX      OCTET STRING (SIZE (1..64))
     MAX-ACCESS  read-write
     STATUS  current
     DESCRIPTION	"The message string which recv from manager and sent to csv"
   ::= {zxCsvCmd  1}
  
 zxCsvCsvSendToNmMessage OBJECT-TYPE
     SYNTAX      OCTET STRING (SIZE (1..64))
     MAX-ACCESS  read-only
     STATUS  current
     DESCRIPTION	"The message string which recv from csv and sent to manager"
   ::= {zxCsvCmd  2}
       
 zxCsvCsvSendToNmNotification  NOTIFICATION-TYPE
     OBJECTS   { zxCsvCsvSendToNmMessage }
     STATUS    current
     DESCRIPTION  "A  zxCsvCsvCommandResponseToNm trap signifies that 
		the SNMP agent has recieved a  msg from Csv and send to manager"
   ::= { zxCsvTrap 0 1 }

END

ZXWANE-MIB DEFINITIONS ::= BEGIN
IMPORTS
        MODULE-IDENTITY, TimeTicks,	OBJECT-TYPE,
		NOTIFICATION-TYPE, enterprises,IpAddress	FROM SNMPv2-SMI
		MacAddress                      		FROM SNMPv2-TC
        	InterfaceIndex					FROM IF-MIB;

zte MODULE-IDENTITY
LAST-UPDATED "2703200000Z"
ORGANIZATION ""
CONTACT-INFO ""
DESCRIPTION  "Initial Version"

::= { enterprises 3902 } 
zxDsl	OBJECT IDENTIFIER ::= { zte 1004 }
zxDslam OBJECT IDENTIFIER ::= { zxDsl 1 }
zxWane	OBJECT IDENTIFIER ::= { zxDslam 2 }
zxWaneTrap OBJECT IDENTIFIER ::= { zxWane 1}

-- definition of zxWaneVcl2PortMappingTable

zxWaneVcl2PortMappingTable OBJECT-TYPE
	SYNTAX		SEQUENCE OF ZxWaneVcl2PortMappingEntry
	MAX-ACCESS		not-accessible
	STATUS		current
	DESCRIPTION
		"zxWaneVcl2PortMappingTable  is used to show the mapping from 
		vcl to port."
	::= {zxWane 2 }

zxWaneVcl2PortMappingEntry	OBJECT-TYPE
	SYNTAX		ZxWaneVcl2PortMappingEntry
	MAX-ACCESS		not-accessible
	STATUS		current
	DESCRIPTION
--!!!
		""
	INDEX	{ zxWaneifIndex,zxWaneVclVpi,zxWaneVclVci}
	::= {zxWaneVcl2PortMappingTable 1 }

ZxWaneVcl2PortMappingEntry	::= SEQUENCE {

    	zxWaneifIndex			InterfaceIndex,
        zxWaneVclVpi 		INTEGER,
        zxWaneVclVci 		INTEGER,
        zxWaneBasePort		INTEGER

}


zxWaneifIndex    OBJECT-TYPE
    SYNTAX  InterfaceIndex
    MAX-ACCESS  not-accessible
    STATUS      current
    DESCRIPTION
--!!!
            ""
  ::= {zxWaneVcl2PortMappingEntry 1 } 


zxWaneVclVpi    OBJECT-TYPE
    SYNTAX  INTEGER
    MAX-ACCESS  not-accessible
    STATUS      current
    DESCRIPTION
--!!!
            ""
  ::= {zxWaneVcl2PortMappingEntry 2 } 


zxWaneVclVci    OBJECT-TYPE
    SYNTAX  INTEGER
    MAX-ACCESS  not-accessible
    STATUS      current
    DESCRIPTION
--!!!
            ""
  ::= {zxWaneVcl2PortMappingEntry 3 } 


zxWaneBasePort    OBJECT-TYPE
    SYNTAX  INTEGER
    MAX-ACCESS  read-only
    STATUS      current
    DESCRIPTION
--!!!
            ""
  ::= {zxWaneVcl2PortMappingEntry 4 } 

zxWaneBridgeFloodStatus OBJECT-TYPE
    SYNTAX      INTEGER {
                    noFlood(1),
                    floodAll(2),
                    floodOnlyUnicast(3)
                }
    MAX-ACCESS  read-write
    STATUS      current
    DESCRIPTION
        "When this is floodAll(2),the device will
        flood broadcast frame and unicast frames
        to pvc ports.  When floodOnlyUnicast(3), flood unicast frames
        to pvc ports.When noFlood(1),the device will not flood any frames."
        
    DEFVAL      { noFlood}
    ::= { zxWane 3 }
    
    
zxWaneCommandTable        OBJECT-TYPE
     SYNTAX         SEQUENCE OF ZxWaneCommandEntry
     MAX-ACCESS     not-accessible
     STATUS         current
     DESCRIPTION
        	"The ZXWane command Execute table. "
     ::= {zxWane 4}

zxWaneCommandEntry		OBJECT-TYPE
     SYNTAX         ZxWaneCommandEntry
     MAX-ACCESS     not-accessible
     STATUS         current
     DESCRIPTION
		"An entry in the ZXWane command Execute table  "
     INDEX  {  zxWaneCommandType }	
     ::= { zxWaneCommandTable  1}

ZxWaneCommandEntry  ::= SEQUENCE  {
     zxWaneCommandType		INTEGER ,
     zxWaneCommandLastChange	TimeTicks ,
     zxWaneCommandStatus	INTEGER
  }
	
zxWaneCommandType	OBJECT-TYPE
     SYNTAX      INTEGER {	
        saveWanedb(1)
	}
	MAX-ACCESS     read-only
	STATUS         current
	DESCRIPTION
			" The operation type of the commands."
	::= { zxWaneCommandEntry	1}
	

zxWaneCommandLastChange	OBJECT-TYPE
	SYNTAX         TimeTicks
	MAX-ACCESS     read-only
	STATUS         current
	DESCRIPTION
		  "The value of MIB-II's sysUpTime at the time this
                   Command is excuted.	When the command hasn't been excuted,
	           the value is always  zero. " 
          ::= { zxWaneCommandEntry	2 }

zxWaneCommandStatus		OBJECT-TYPE
        SYNTAX    INTEGER 	{	
         			cmdNeverExecuted(0),
 				lastCmdSuccessfulExecuted(1),
				lastCmdFailed(2),
				executing(3),
				execute(4)
				}
	MAX-ACCESS     read-write
	STATUS         current
	DESCRIPTION
		" Indicates the status of this type of command
			When the command hasn't been excuted,
		        the value is always  zero. 	
		        If want to execute the command , the manager should 
			        set the value to Execute(3)	."
	DEFVAL { 0 }
	::= {zxWaneCommandEntry 3}

zxWaneIGMPSnoopEnabled        OBJECT-TYPE
     SYNTAX         INTEGER {
			enabled(1),
			disabled(2)
			}
     MAX-ACCESS     read-write
     STATUS         current
     DESCRIPTION
        	"Setting this object to (1) enables IGMP Snooping.  Setting
                 it to (2) disables IGMP Snooping."
     ::= {zxWane 5}

zxWaneIgmpSnoopAging        OBJECT-TYPE
     SYNTAX         INTEGER (30..3600)
     MAX-ACCESS     read-write
     STATUS         current
     DESCRIPTION
        	"The timeout period in seconds for aging out Multicast Groups
                 dynamically learned with IGMP Snooping."
     ::= {zxWane 6}
     
zxWaneVersion       OBJECT-TYPE
     SYNTAX         INTEGER
     MAX-ACCESS     read-only
     STATUS         current
     DESCRIPTION
        	"The WANE Version Number"
     ::= {zxWane 7}

     zxWaneMACToPortTable OBJECT-TYPE
     SYNTAX           SEQUENCE OF ZxWaneMACToPortEntry
     MAX-ACCESS       not-accessible
     STATUS current
     DESCRIPTION
           "This table, which provides port information,the index :macaddress 
             and vlanid"
        ::= { zxWane 8 }

     zxWaneMACToPortEntry OBJECT-TYPE
     SYNTAX 	ZxWaneMACToPortEntry
     MAX-ACCESS not-accessible
     STATUS current
     DESCRIPTION
            ""
        INDEX  { mac ,vid }
        ::= { zxWaneMACToPortTable 1 }

     ZxWaneMACToPortEntry ::= SEQUENCE {
        mac                   MacAddress,        
        vid                   INTEGER,
        zxWaneMACToPort       INTEGER,
        zxWanePortToVPI       INTEGER,
        zxWanePortToVCI       INTEGER      	
    }

    mac OBJECT-TYPE
    SYNTAX      MacAddress
    MAX-ACCESS  not-accessible
    STATUS      current
    DESCRIPTION
      " the mac address of port "
    REFERENCE
        ""
    ::= { zxWaneMACToPortEntry 1 }
  
   
   vid OBJECT-TYPE
   SYNTAX      INTEGER
   MAX-ACCESS  not-accessible
   STATUS      current
   DESCRIPTION
      "the vlan id of the  port "
   REFERENCE
        ""
    ::= { zxWaneMACToPortEntry 2 }
   
    zxWaneMACToPort  OBJECT-TYPE
    SYNTAX INTEGER
    MAX-ACCESS read-only
    STATUS current
    DESCRIPTION
            "the port id according to mac and vlan id"
        ::= { zxWaneMACToPortEntry 3 }
    
    zxWanePortToVPI  OBJECT-TYPE
    SYNTAX INTEGER
    MAX-ACCESS read-only
    STATUS current
    DESCRIPTION
            "the port vpi"
        ::= { zxWaneMACToPortEntry 4 }
        
    zxWanePortToVCI  OBJECT-TYPE
    SYNTAX INTEGER
    MAX-ACCESS read-only
    STATUS current
    DESCRIPTION
            "the port vci"
        ::= { zxWaneMACToPortEntry 5}

--add by xieyan 2004-1-3
zxWanePVCToIPTable OBJECT-TYPE
     SYNTAX           SEQUENCE OF ZxWanePVCToIPEntry
     MAX-ACCESS       not-accessible
     STATUS current
     DESCRIPTION
           "This table, which provides port information :ip address "
        ::= { zxWane 9 }

 
   zxWanePVCToIPEntry OBJECT-TYPE
     SYNTAX 	ZxWanePVCToIPEntry
     MAX-ACCESS not-accessible
     STATUS current
     DESCRIPTION
            "the entry of zxWanePVCToIPTable "
        INDEX  { zxWanePvcPortNum}
        
        ::= { zxWanePVCToIPTable 1 }

     ZxWanePVCToIPEntry ::= SEQUENCE {
        zxWanePvcPortNum 	INTEGER,
        zxWanePvcToIpAddress    IpAddress
     }
     
     zxWanePvcPortNum        OBJECT-TYPE
     SYNTAX        	 INTEGER(4..512)
     MAX-ACCESS    	 not-accessible
     STATUS        	 current
     DESCRIPTION
         "the pvc port number  "
      REFERENCE
        ""
    ::= { zxWanePVCToIPEntry 1 }
    
    zxWanePvcToIpAddress  OBJECT-TYPE
    SYNTAX        	 IpAddress
    MAX-ACCESS    	 read-write
    STATUS        	 current
    DESCRIPTION
      " the port derect ip address  "
    REFERENCE
        ""
    ::= { zxWanePVCToIPEntry 2 }
     
--add end    
     
    zxWaneDestIpAddress   OBJECT-TYPE
    	SYNTAX        	 IpAddress
    	MAX-ACCESS    	 read-write
    	STATUS        	 current
    	DESCRIPTION
      	   " the port ip address  "
    	REFERENCE
        	""
     ::= {zxWane 10}
               
     zxWaneDestPortNum        OBJECT-TYPE
     	SYNTAX        	 INTEGER
     	MAX-ACCESS    	 read-only
     	STATUS        	 current
     	DESCRIPTION
           "the pvc port number  "
        REFERENCE
           ""
    ::= { zxWane 11 }
-- zxWaneTrap 
     
zxWaneCommandTabStatusLastChange NOTIFICATION-TYPE
    OBJECTS   { zxWaneCommandStatus }
    STATUS    current
    DESCRIPTION	"This trap signifies that the SNMP agent has detected that the	
			zxWaneCommandStatus object for the command has been changed."
     ::= { zxWaneTrap 0 1 }


END


WRS-MASTER-MIB DEFINITIONS ::= BEGIN

IMPORTS
    MODULE-IDENTITY, enterprises              FROM SNMPv2-SMI;

    zte MODULE-IDENTITY
        LAST-UPDATED    "0008290000Z"  -- August 29, 2000
        ORGANIZATION    "Wind River Systems, Inc."
        CONTACT-INFO    "Wind River Systems, Inc.
                         E-mail: support@windriver.com"

        DESCRIPTION     "WRS Master MIB OID defines and documentation."

        REVISION        "0008290000Z"  -- August 29, 2000
        DESCRIPTION     "Initial MIB creation."

        ::= { enterprises 3902 }
    
-- ZXA1- Products
	zxDsl	OBJECT IDENTIFIER ::= { zte 1004 }
	zxDslam OBJECT IDENTIFIER ::= { zxDsl 1 }
	zxLan	OBJECT IDENTIFIER ::= { zxDslam 10 }
	zxIma   OBJECT IDENTIFIER ::= { zxDslam 11 }
       zxWand  OBJECT IDENTIFIER  ::= { zxDslam 12 }
       uas  OBJECT IDENTIFIER  ::= { zxDslam 13 }

-- TMS Major MIB Categories
    idb             OBJECT IDENTIFIER ::= { zxLan 1 }     -- IDB MIBs
--    tmsGeneric      OBJECT IDENTIFIER ::= { zxLan 2 }     -- TMS Generic MIBs
    oemSwapi        OBJECT IDENTIFIER ::= { zxLan 3 }     -- OEM swAPI MIBs
    oemProd         OBJECT IDENTIFIER ::= { zxLan 4 }     -- OEM Product MIBs   
    lanGeneric      OBJECT IDENTIFIER ::= { zxLan 3 }  

-- TMS Major MIB Categories
    idb             OBJECT IDENTIFIER ::= { zxWand 1 }     -- IDB MIBs
    oemSwapi        OBJECT IDENTIFIER ::= { zxWand 2 }     -- OEM swAPI MIBs
    wandOemProd         OBJECT IDENTIFIER ::= { zxWand 3 }     -- OEM Product MIBs
    ixpGeneric      OBJECT IDENTIFIER ::= { zxWand 4 }     -- IXP Generic MIBs
    wandGeneric     OBJECT IDENTIFIER ::= { zxWand 5 }     -- IXP Generic MIBs

-- TMS IDB Internal Module MIBs
    rmonMib         OBJECT IDENTIFIER ::= { idb 1 }
--  garpMib         OBJECT IDENTIFIER ::= { idb 2 }         SMIv2
--  stpMib          OBJECT IDENTIFIER ::= { idb 3 }         SMIv2

-- wand MIBs
	 wandComLagMib    OBJECT IDENTIFIER ::= { wandGeneric 1 } 
	 wandCommMib      OBJECT IDENTIFIER ::= { wandGeneric 2 }
	 wandPvcMib       OBJECT IDENTIFIER ::= { wandGeneric 3 }
	 wandVlanMultMib        OBJECT IDENTIFIER ::= { wandGeneric 4 }
	 wandPortStaticMACMib  	OBJECT IDENTIFIER ::= { wandGeneric 5 }
    
-- TMS Generic MIBs
--  tmsCommonMib    OBJECT IDENTIFIER ::= { tmsGeneric 1 }  SMIv2
--  lacpMib         OBJECT IDENTIFIER ::= { tmsGeneric 2 }  SMIv2

-- OEM swAPI MIBs
--  pmSwapi         OBJECT IDENTIFIER ::= { oemSwapi 1 }    SMIv2
--  bcmSwapi        OBJECT IDENTIFIER ::= { oemSwapi 2 }    SMIv2
--  pcSwapi         OBJECT IDENTIFIER ::= { oemSwapi 3 }    SMIv2

-- OEM Product MIBs
--  pm3575          OBJECT IDENTIFIER ::= { oemProd 1 }     SMIv2
--  bcm5600         OBJECT IDENTIFIER ::= { oemProd 2 }     SMIv2
--  pcSwitch        OBJECT IDENTIFIER ::= { oemProd 3 }     SMIv2

--
-- END of WRS-MASTER-MIB
--


END


--------------------------------------------------------------------------
--
-- LAGSTATIC
--
--------------------------------------------------------------------------
    WAND-LAG-MIB DEFINITIONS ::= BEGIN
    
    IMPORTS
        MODULE-IDENTITY, OBJECT-TYPE,
        Integer32                               FROM SNMPv2-SMI   
        wandGeneric                             FROM WRS-MASTER-MIB ;                

    zte MODULE-IDENTITY
        LAST-UPDATED    "2002-05-21-00"  -- August 29, 2000
        ORGANIZATION    "ZTE Corporation."
        CONTACT-INFO    "ZTE Corporation.
                         http://www.zte.com.cn"
        DESCRIPTION     "ZTE ADSL lan Bridge MIB OID defines and documentation."
        REVISION        "0008290000Z"  -- August 29, 2000
        DESCRIPTION     "Initial MIB creation."

        ::= { enterprises 3902 }
 
  wandComLagMib         OBJECT IDENTIFIER  ::= { wandGeneric 1 } 
  wandLagStatic         OBJECT IDENTIFIER  ::= {wandComLagMib 1}  

  wandDot8023adPortTable OBJECT-TYPE
        SYNTAX      SEQUENCE OF WandDot8023adPortEntry
        MAX-ACCESS  not-accessible
        STATUS      current
        DESCRIPTION
          "A table containing per port control and status
           information for port configuration in the device."
        ::= { wandLagStatic 1 }

    wandDot8023adPortEntry OBJECT-TYPE
        SYNTAX      WandDot8023adPortEntry
        MAX-ACCESS  not-accessible
        STATUS      current
        DESCRIPTION
        "Information controlling Aggregator configuration for a port
        on the device.  This is indexed by dot1dBasePort."
 	INDEX   {wandDot8023adPortId}
         ::= { wandDot8023adPortTable 1 }

    WandDot8023adPortEntry ::=
        SEQUENCE {
           wandDot8023adPortId  Integer32 ,
           wandDot8023adAggNo   Integer32
        }


	wandDot8023adPortId OBJECT-TYPE
  	SYNTAX      Integer32
  	MAX-ACCESS  not-accessible
  	STATUS      current
  	DESCRIPTION
      " the lag port id ,the range from 1 to 4"
  	REFERENCE
        ""
    ::= { wandDot8023adPortEntry 1 }
    
    wandDot8023adAggNo OBJECT-TYPE
        SYNTAX      Integer32
        MAX-ACCESS  read-write
        STATUS      current
        DESCRIPTION
          "The aggIndex  assigned to this port."
        REFERENCE
          "IEEE 802.3ad"
        ::= { wandDot8023adPortEntry 2 }
END

------------------------------------------------------------------------------
--
--  File         : wandCommMib.mib
--  Description  : ZTE WAND MIB  
--
------------------------------------------------------------------------------
WAND-COMM-MIB DEFINITIONS ::= BEGIN

	IMPORTS
			MODULE-IDENTITY, OBJECT-TYPE,
			enterprises					FROM SNMPv2-SMI
			MODULE-COMPLIANCE, OBJECT-GROUP			FROM SNMPv2-CONF		
			MacAddress                           FROM SNMPv2-TC
			wandCommMib                          FROM WRS-MASTER-MIB
			PortList, dot1qStaticMulticastEntry		FROM Q-BRIDGE-MIB;       

    wandCleanFlash OBJECT-TYPE
        SYNTAX INTEGER {
               noop(1),            -- no operation
               clean(2),           -- clean the data in flash
               cleanInProgress(3)  -- read-only: flash clean in progress
        }
        MAX-ACCESS read-write
        STATUS current
        DESCRIPTION
            "When set to 'clean(2)', the data in flash are cleaned . This
             operations may be slow . Consequently, all or many updates 
             should be made before cleaning the flash.  Note that the SNMP
             set to 'clean(2)' returns immediately to the caller.  Gets on
             this object then return  'cleanInProgress(3)' until the clean
             operation completes, at which time 'noop(1)' is returned.  
             Consequently, a get operation always returns 'noop(1)' or 
             'cleanInProgress(3)' depending on the current state.
            
             The agent returns 'badValue' for SNMPv1 or 'inconsistentValue'
             for SNMPv2c/v3 for a set to 'clean(2)' while the current get
             state is 'cleanInProgress(3)'.
             
             Attempts to set this object to 'cleanInProgress(3)' returns
             'badValue' for SNMPv1 or 'wrongValue' for SNMPv2c/v3."
        ::= { wandCommMib 1 }

    wandReset OBJECT-TYPE
        SYNTAX INTEGER {
               noop(1),           -- no operation
               reset(2),          -- reset unit
               resetToDefaults(3) -- reset to factory defaults/reset unit
        }
        MAX-ACCESS read-write
        STATUS current
        DESCRIPTION
            "Physically performs a hardware reset of the unit. 
             Use with care.  A 'reset(2)' resets the unit, a
             'resetToDefaults(3)' resets the NVM configuration
             to factory defaults and then resets the unit, and 'noop(1)'
             does nothing.  A value of 'noop(1)' is always returned for a
             GET operation."
        ::= { wandCommMib 2 }

    wandVersionNumber OBJECT-TYPE
        SYNTAX OCTET STRING (SIZE (0..4))
        MAX-ACCESS read-only
        STATUS current
        DESCRIPTION
            "Get this MIB Major version number.  This number should 
             match the Major version given in the documentation header
             at the beginning text of this MIB.  Note that the '.c' file
             corresponding to this MIB has to be manually edited to
             change the version number if this file is modified and
             the version number is therefore changed."
        ::= { wandCommMib 3 }


    wandSaveFlash OBJECT-TYPE
        SYNTAX INTEGER {
               noop(1),           -- no operation
               save(2),           -- save all configuration parameters to NVM
               saveInProgress(3)  -- read-only: NVM save in progress
        }
        MAX-ACCESS read-write
        STATUS current
        DESCRIPTION
            "When set to 'save(2)', all nonvolatile configuration
             parameters are saved to NVM (Nonvolatile Memory).  NVM save
             operations may be slow (e.g., erasing/writing Flash device).
             Consequently, all or many updates should be made before
             saving to NVM.  Note that the SNMP set to 'save(2)' returns
             immediately to the caller.  Gets on this object then return
             'saveInProgress(3)' until the save operation completes, at
             which time 'noop(1)' is returned.  Consequently, a get
             operation always returns 'noop(1)' or 'saveInProgress(3)'
             depending on the current state.
             
             The agent returns 'badValue' for SNMPv1 or 'inconsistentValue'
             for SNMPv2c/v3 for a set to 'Save(2)' while the current get
             state is 'saveInProgress(3)'.
             
             Attempts to set this object to 'saveInProgress(3)' returns
             'badValue' for SNMPv1 or 'wrongValue' for SNMPv2c/v3."
        ::= { wandCommMib 4 }

    wandSpanOnOff OBJECT-TYPE
        SYNTAX INTEGER {
               enable(1),
               disable(2)
        }
        MAX-ACCESS read-write
        STATUS current
        DESCRIPTION
            "DURABLE: { enable }
             Enable/Disable Spanning Tree for the bridge.
             When 'disable(2)', all ports of the device are placed in the
             forwarding mode, regardless of current Spanning Tree state.
             When 'enable(1)', the normal STP state transitions take place."
        ::= { wandCommMib 5 }

    wandLACPOnOff OBJECT-TYPE
        SYNTAX INTEGER {
               enable(1),
               disable(2)
        }
        MAX-ACCESS read-write
        STATUS current
        DESCRIPTION
            "DURABLE: { disable }
             Enable/Disable LACP operation for the TMS agent.
             When 'disable(2)', no LACP's are transmitted by the Application.
             When enabled, the Application sends LACP requests during
             system startup."
        ::= { wandCommMib 6 }

       wandBroadcasdOnOff OBJECT-TYPE
               SYNTAX INTEGER {
               enable(1),
               disable(2)
        }
        MAX-ACCESS read-write
        STATUS current
        DESCRIPTION
            "DURABLE: { disable }
             disable/enable forward broadcast pkt to ARM  "
        ::= { wandCommMib 7 }
      
       wandMulticastOnOff OBJECT-TYPE
               SYNTAX INTEGER {
               enable(1),
               disable(2)
        }
        MAX-ACCESS read-write
        STATUS current
        DESCRIPTION
            "DURABLE: { disable }
             disable/enable forward multicast  pkt to ARM  "
        ::= { wandCommMib 8 }        
        

    wandBoardID  OBJECT-TYPE
        SYNTAX INTEGER 
        MAX-ACCESS read-only
        STATUS current
        DESCRIPTION
            "wand Board standing in the dislam"
        ::= { wandCommMib 9 }
       
   wandCommonIPMACAddr OBJECT-TYPE
        SYNTAX MacAddress
        MAX-ACCESS read-write
        STATUS current
        DESCRIPTION
            "DURABLE: { '000000000000'H }
             The base (i.e., first) MAC address used by the TMS agent for its
             in-band ports."
        ::= { wandCommMib 10 }


    wandIgmpSnoopOnOff  OBJECT-TYPE
        SYNTAX INTEGER {
               enable(1),
               disable(2)
        }
        MAX-ACCESS read-write
        STATUS current
        DESCRIPTION
            "DURABLE: { disable }
             Enable/Disable IGMP Snooping operation for the TMS agent.
             Setting this object to enable(1) enables IGMP Snooping.  Setting
             it to disable(2) disables IGMP Snooping.
             
             Note that IGMP Snooping can function with or without GVRP and
             GMRP enabled."
        ::= { wandCommMib 11}

    wandIgmpSnoopAlertsOnOff  OBJECT-TYPE
        SYNTAX INTEGER {
               enable(1),
               disable(2)
        }
        MAX-ACCESS read-write
        STATUS current
        DESCRIPTION
            "DURABLE: { disable }
             Setting this object to enable(1) enables the IP Router Alert
             Option (as defined in RFC2113) for transmitted IGMP packets.
             Setting it to disable(2) disables this option."
        ::= { wandCommMib 12 }

    wandIgmpSnoopAging  OBJECT-TYPE
        SYNTAX INTEGER (30..3600)
        MAX-ACCESS read-write
        STATUS current
        DESCRIPTION
            "DURABLE: { 300 }
             The timeout period in seconds for aging out Multicast Groups
             dynamically learned with IGMP Snooping.  Note that aging operates
             on a per interface per VLAN per multicast group basis."
        ::= { wandCommMib 13 }

    wandIgmpSnoopTable OBJECT-TYPE
        SYNTAX           SEQUENCE OF WandIgmpSnoopEntry
        MAX-ACCESS not-accessible
        STATUS current
        DESCRIPTION
            "This table, which provides IGMP Snooping information, augments
             the 'dot1qStaticMulticastTable' in the Q-MIB (RFC2674)."
        ::= { wandCommMib 14 }

    wandIgmpSnoopEntry OBJECT-TYPE
        SYNTAX 	WandIgmpSnoopEntry
        MAX-ACCESS not-accessible
        STATUS current
        DESCRIPTION
            "Displays by VLAN, Multicast Group, and Multicast receive port
             the set of ports enabled to forward Multicast Group traffic as
             determined by the IGMP Snooping task."
        AUGMENTS { dot1qStaticMulticastEntry }
        ::= { wandIgmpSnoopTable 1 }

    WandIgmpSnoopEntry ::= SEQUENCE {
        wandIgmpSnoopEgressPorts   PortList
    }

    wandIgmpSnoopEgressPorts  OBJECT-TYPE
        SYNTAX PortList
        MAX-ACCESS read-only
        STATUS current
        DESCRIPTION
            "This read-only object displays the set of ports enabled to
             forward specific Multicast Group traffic as determined by the
             IGMP Snooping task.
            
             It should be noted that the IGMP Snooping task generates a pseudo-
             static (i.e., not saved in NVM) port list similar to the RFC2674
             Q-MIB 'dot1qStaticMulticastStaticEgressPorts' object. Consequently,
             a port will not be a member of 'tmsCommonIgmpSnoopEgressPorts' if
             it is a member of 'dot1qStaticMulticastForbiddenEgressPorts'."
        ::= { wandIgmpSnoopEntry 1 }
         
        wandBoradcastToAtmPortStatus  OBJECT-TYPE
        SYNTAX INTEGER {
               enable(1),
               disable(2)
        }
        MAX-ACCESS read-write
        STATUS current
        DESCRIPTION
            " "
           ::= { wandCommMib 15 }
    
        wandStatisticStatus  OBJECT-TYPE
        SYNTAX INTEGER {
               enable(1),
               disable(2)
        }
        MAX-ACCESS read-write
        STATUS current
        DESCRIPTION
            "enable or disable the port statistics information  "
           ::= { wandCommMib 16 }
                    
      wandFloodToAtmPortStatus OBJECT-TYPE
               SYNTAX INTEGER {
               enable(1),
               disable(2)
        }
        MAX-ACCESS read-write
        STATUS current
        DESCRIPTION
            "DURABLE: { disable }
             disable/enable forward flood unicast pkt to ARM  "
        ::= { wandCommMib 17 }
        
       
       wandMuliticastToAtmPortStatus OBJECT-TYPE
               SYNTAX INTEGER {
               enable(1),
               disable(2)
        }
        MAX-ACCESS read-write
        STATUS current
        DESCRIPTION
            "DURABLE: { disable }
             disable/enable forward multciast pkt to ARM  "
        ::= { wandCommMib 18 }
                    

       wandMACToPortTable OBJECT-TYPE
        SYNTAX           SEQUENCE OF WandMACToPortEntry
        MAX-ACCESS       not-accessible
        STATUS current
        DESCRIPTION
            "This table, which provides port information,the index :macaddress 
             and vlanid"
        ::= { wandCommMib 19 }

       wandMACToPortEntry OBJECT-TYPE
        SYNTAX 	WandMACToPortEntry
        MAX-ACCESS not-accessible
        STATUS current
        DESCRIPTION
            ""
        INDEX  { MAC ,VID }
        ::= { wandMACToPortTable 1 }

    WandMACToPortEntry ::= SEQUENCE {
        MAC            
        	MacAddress,        
        VID            
        	INTEGER,

        wandMACToPort  

        	INTEGER     
    }

    MAC OBJECT-TYPE
    SYNTAX      MacAddress
    MAX-ACCESS  not-accessible
    STATUS      current
    DESCRIPTION
      " the mac address of port "
    REFERENCE
        ""
    ::= { wandMACToPortEntry 1 }
  
   
   VID OBJECT-TYPE
   SYNTAX      INTEGER
   MAX-ACCESS  not-accessible
   STATUS      current
   DESCRIPTION
      "the vlan id of the  port "
   REFERENCE
        ""
    ::= { wandMACToPortEntry 2 }
   
    wandMACToPort  OBJECT-TYPE
    SYNTAX INTEGER
    MAX-ACCESS read-only
    STATUS current
        DESCRIPTION
            "the port id according to mac and vlan id"
        ::= { wandMACToPortEntry 3 }
    wandMibErrorCode  OBJECT-TYPE
        SYNTAX INTEGER {
               no_error(0),
               multicast_exceed(1),
               vlan_surport_multicast_exceed(2)
        }
        MAX-ACCESS read-only
        STATUS current
        DESCRIPTION
            ""
        ::= { wandCommMib 20 }

     dslamMacaddress OBJECT-TYPE
        SYNTAX MacAddress
        MAX-ACCESS read-write
        STATUS current
        DESCRIPTION
            "DURABLE: { '000000000000'H }
             The base (i.e., first) MAC address used by the TMS agent for its
             in-band ports."
        ::= { wandCommMib 21 }   
        
     wandVbasUserCardType OBJECT-TYPE
        SYNTAX INTEGER {
           atuca (12),
           atuga (32)
          }
        MAX-ACCESS read-write
        STATUS current
        DESCRIPTION
            ""
        ::= { wandCommMib 22 }  
        
     wandVbaseOrVmacFlag OBJECT-TYPE
        SYNTAX INTEGER {
           normal (0),
           vmacMode (1),
           vbasMode (2)
          }
        MAX-ACCESS read-write
        STATUS current
        DESCRIPTION
            ""
        ::= { wandCommMib 23 }  
        
    wandDslamCorpName OBJECT-TYPE
        SYNTAX OCTET STRING (SIZE (0..20))
        MAX-ACCESS read-write
        STATUS current
        DESCRIPTION
            " "
        ::= { wandCommMib 24 }
        
     wandDslamCorpId OBJECT-TYPE
        SYNTAX INTEGER(0..63)
        MAX-ACCESS read-write
        STATUS current
        DESCRIPTION
            ""
        ::= { wandCommMib 25 }  
        
    wandDslamDeviceName OBJECT-TYPE
        SYNTAX OCTET STRING (SIZE (0..20))
        MAX-ACCESS read-write
        STATUS current
        DESCRIPTION
            ""
        ::= { wandCommMib 26 }
        
    wandDslamDeviceId OBJECT-TYPE
        SYNTAX INTEGER (0..255)
        MAX-ACCESS read-write
        STATUS current
        DESCRIPTION
            ""
        ::= { wandCommMib 27 }  
        
      wandPvcDestIpAddress   OBJECT-TYPE
    	SYNTAX      IpAddress
    	MAX-ACCESS  read-write
    	STATUS      current
    	DESCRIPTION
        	"get destation ip address from nms"
    	::= { wandCommMib 28}    
        
   wandPvcDestPort  OBJECT-TYPE
    	SYNTAX INTEGER
    	MAX-ACCESS read-only
    	STATUS current
        DESCRIPTION
            " get destation port num by wandPvcDestIpAddress"
        ::= { wandCommMib 29 }     


-- END of WAND-COMM-MIB                
END


-------------------------------------------------------------------------
--
--  WANDPVCMIB
--
-------------------------------------------------------------------------
------------------------------------------------------------------------------
--
--  File         : wandPvcMIB.mib
--  Description  : ZTE ADSL WAND PVC MANAGER MIB  
--
------------------------------------------------------------------------------
WAND-PVC-MIB DEFINITIONS ::= BEGIN

	IMPORTS
    		MODULE-IDENTITY, OBJECT-TYPE,
    		Counter32, Counter64, Unsigned32, TimeTicks,
			  Integer32, enterprises ,IpAddress   FROM SNMPv2-SMI
    
    		RowStatus, TruthValue, TEXTUAL-CONVENTION, MacAddress
        											FROM SNMPv2-TC
        											
			  MODULE-COMPLIANCE, OBJECT-GROUP			FROM SNMPv2-CONF
		    wandPvcMib									        FROM WRS-MASTER-MIB
			  dot1dBridge, dot1dBasePortEntry, dot1dBasePort
													FROM BRIDGE-MIB;


wandCurrManagePortNum  OBJECT-TYPE
    SYNTAX      INTEGER
    MAX-ACCESS  read-only
    STATUS      current
    DESCRIPTION
        "all ports in the system at present"
    REFERENCE
        ""
    ::= { wandPvcMib 1 }


wandPvcManagerTable   OBJECT-TYPE
		SYNTAX      SEQUENCE OF WandPvcManagerEntry
    MAX-ACCESS  not-accessible
    STATUS      current
    DESCRIPTION
        " "
    ::= { wandPvcMib 2 }

wandPvcManagerEntry OBJECT-TYPE
    SYNTAX      WandPvcManagerEntry
    MAX-ACCESS  not-accessible
    STATUS      current
    DESCRIPTION
        ""
    INDEX   {VPI ,VCI}
    ::= { wandPvcManagerTable 1 }

WandPvcManagerEntry ::=
    SEQUENCE {
        VPI
             INTEGER,
        VCI
             INTEGER,
        port
             INTEGER,      
              
        pvcMacNumSupport
             INTEGER,
             
        pvcPortForwBroad
             INTEGER,
             
        pvcPortPriority
             INTEGER ,  
              
        pvcRowStatus 
             RowStatus,
             
        pvcVlanId
             INTEGER,
                  
       pvcPortVmacSwitch 
           INTEGER ,
                
        pvcBindIpAddress 
            IpAddress  
        
    }

VPI OBJECT-TYPE
  SYNTAX      INTEGER
  MAX-ACCESS  not-accessible
  STATUS      current
  DESCRIPTION
      " the vpi index of wand pvc port "
  REFERENCE
        ""
    ::= { wandPvcManagerEntry 1 }

VCI OBJECT-TYPE
    SYNTAX      INTEGER 
    MAX-ACCESS  not-accessible
    STATUS      current
    DESCRIPTION
 				 " the vci index of wand pvc port "
    REFERENCE
        ""
    ::= { wandPvcManagerEntry 2 }
    
port OBJECT-TYPE
  SYNTAX      INTEGER
  MAX-ACCESS  read-only
  STATUS      current
  DESCRIPTION
      " according vpi and vpi ,to get the port id "
  REFERENCE
        ""
    ::= { wandPvcManagerEntry 3 }

pvcMacNumSupport OBJECT-TYPE
  SYNTAX      INTEGER
  MAX-ACCESS  read-write
  STATUS      current
  DESCRIPTION
      "the learning macaddresses of every pvc port"
  REFERENCE
        ""
    ::= { wandPvcManagerEntry 4}

pvcPortForwBroad OBJECT-TYPE
 SYNTAX INTEGER {
               enable(1),           
               disable(2)
             }
            
  MAX-ACCESS  read-write
  STATUS      current
  DESCRIPTION
      " disable/enable the port receive broad packet"
  REFERENCE
        ""
    ::= { wandPvcManagerEntry 5}

pvcPortPriority OBJECT-TYPE
  SYNTAX      INTEGER(0..7)
  MAX-ACCESS  read-write
  STATUS      current
  DESCRIPTION
      "the prority of every pvc port"
  REFERENCE
        ""
    ::= { wandPvcManagerEntry 6}

pvcRowStatus OBJECT-TYPE
    SYNTAX      RowStatus
    MAX-ACCESS  read-create
    STATUS      current
    DESCRIPTION
        "the create port command object"
    ::= { wandPvcManagerEntry 7 }
   
pvcVlanId OBJECT-TYPE
    SYNTAX      INTEGER
    MAX-ACCESS  read-write
    STATUS      current
    DESCRIPTION
        ""
    ::= { wandPvcManagerEntry 8 } 
    
pvcPortVmacSwitch OBJECT-TYPE
    SYNTAX      INTEGER{
       enable (1),
       disable (2)
     }
    MAX-ACCESS  read-write
    STATUS      current
    DESCRIPTION
        "enable/disable pvc port working in vmac mode "
    ::= { wandPvcManagerEntry 9 } 

 pvcBindIpAddress   OBJECT-TYPE
    SYNTAX      IpAddress
    MAX-ACCESS  read-write
    STATUS      current
    DESCRIPTION
        " "
    ::= { wandPvcManagerEntry 10} 

-- END of WAND-PVCMANAGER-MIB                
END

----
--- IXPOEM.MIB
---
    WAND-OEM-BCM5600-MIB DEFINITIONS ::= BEGIN

    IMPORTS
        MODULE-IDENTITY, OBJECT-TYPE,
        Integer32, Counter64                    FROM SNMPv2-SMI
        
        DisplayString, TruthValue               FROM SNMPv2-TC
        
        MODULE-COMPLIANCE, OBJECT-GROUP         FROM SNMPv2-CONF
        
        wandOemProd                             FROM WRS-MASTER-MIB;       

    wandBcm5600 MODULE-IDENTITY
        LAST-UPDATED    "0105030000Z"  -- May 03,2001  
        ORGANIZATION    "Wind River Systems, Inc."
        CONTACT-INFO    "Wind River Systems, Inc.
                         E-mail: support@windriver.com"

        DESCRIPTION     "TMS Broadcom BCM5600 StrataSwitch OEM-Product
                         Enterprise MIB definition."

        REVISION        "0105030000Z"  -- May 03,2001
        DESCRIPTION     "Initial MIB creation."

        ::= { wandOemProd 2 }

------------------------------------------------------------------------------
-- Textual Conventions (i.e., these do not affect object encoding):
------------------------------------------------------------------------------
--
-- "DURABLE":
--    Objects that are saved across a system reset and/or power cycle
--    are noted as "DURABLE" for convenience in the DESCRIPTION
--    section of the object definition.  Code must be explicitly
--    written to implement these DURABLE objects.
--

------------------------------------------------------------------------------
--  define groups in OEM-BCM5600-MIB
------------------------------------------------------------------------------
    wandOemArchIface            OBJECT IDENTIFIER ::= { wandBcm5600 1 }
    wandOemChip                 OBJECT IDENTIFIER ::= { wandBcm5600 2 }
    wandOemProdConformance      OBJECT IDENTIFIER ::= { wandBcm5600 3 }
    wandOemProdGroups           OBJECT IDENTIFIER ::= { wandOemProdConformance 1 }
    wandOemProdCompliances      OBJECT IDENTIFIER ::= { wandOemProdConformance 2 }


    wandOemArchIfaceTable OBJECT-TYPE
        SYNTAX SEQUENCE OF WandOemArchIfaceEntry
        MAX-ACCESS not-accessible
        STATUS current
        DESCRIPTION
            "A table of switch interfaces and associated properties."
        ::= { wandOemArchIface 1 }

    wandOemArchIfaceEntry OBJECT-TYPE
        SYNTAX WandOemArchIfaceEntry
        MAX-ACCESS not-accessible
        STATUS current
        DESCRIPTION
            "Table entry for switch interface control and status information."
        INDEX { wandOemArchIfaceUnit, wandOemArchIfacePort }
        ::= { wandOemArchIfaceTable 1 }

    WandOemArchIfaceEntry ::= SEQUENCE {
        wandOemArchIfaceUnit                Integer32,
        wandOemArchIfacePort                Integer32,
        wandOemArchIfaceLLWHPort            Integer32,
        wandOemArchIfaceIfIndex             Integer32,
        wandOemArchIfaceName                DisplayString,
        wandOemArchIfaceEnable              TruthValue,
        wandOemArchIfaceLink                INTEGER,
        wandOemArchIfaceDuplexSpeed         INTEGER,
        wandOemArchIfPriority               INTEGER,
        wandOemArchIfBroadCast              INTEGER
    }

    wandOemArchIfaceUnit OBJECT-TYPE
        SYNTAX Integer32 (1..4)
        MAX-ACCESS not-accessible
        STATUS current
        DESCRIPTION
            "An index that uniquely identifies a unit in the TMS BCM5600
             stack.  If an invalid value is used for the index, a SNMP
             'noSuchName' error (SNMPv1) or 'noSuchInstance' exception
             (SNMPv2/v3) is returned.  For implementations that do not support
             stacking, the same response is returned for any unit index other
             than 1."
        ::= { wandOemArchIfaceEntry 1 }

    wandOemArchIfacePort OBJECT-TYPE
        SYNTAX Integer32 (1..26)
        MAX-ACCESS not-accessible
        STATUS current
        DESCRIPTION
            "An index that uniquely identifies a TMS Application 'logical port'
             (i.e., IEEE 802.3ad Aggregator) within the oemArchIfaceUnit."
        ::= { wandOemArchIfaceEntry 2 }

    wandOemArchIfaceLLWHPort OBJECT-TYPE
        SYNTAX Integer32 (8193..8296)
        MAX-ACCESS read-only
        STATUS current
        DESCRIPTION
            "A value that uniquely identifies a TMS Application 'logical port'
             (i.e., IEEE 802.3ad Aggregator) in the TMS BCM5600 stack.  This is
             a 'Layered Linear With Holes' (LLWH) port number that may may have
             holes for missing ports or units.  For this MIB, 26 port numbers
             are reserved for each unit in the stack.  For example, LLHW port
             8193 is unit 1, port 1 and LLHW 8228 is unit 2, port 10."
        ::= { wandOemArchIfaceEntry 3 }

    wandOemArchIfaceIfIndex OBJECT-TYPE
        SYNTAX Integer32
        MAX-ACCESS read-only
        STATUS current
        DESCRIPTION
            "The ifIndex of this TMS Application 'logical port' (i.e., IEEE
             802.3ad Aggregator).  Note that an ifIndex value of 34603009 
             (0x02100001) represents the Aggregator layer, unit 1, slot 0
             (base unit ports), port 1."
        ::= { wandOemArchIfaceEntry 4 }

    wandOemArchIfaceName OBJECT-TYPE
        SYNTAX DisplayString (SIZE (0..16))
        MAX-ACCESS read-write
        STATUS current
        DESCRIPTION
            "DURABLE:
             The textual name of this interface, e.g., 'John'."
        ::= { wandOemArchIfaceEntry 5 }

    wandOemArchIfaceEnable OBJECT-TYPE
        SYNTAX TruthValue
        MAX-ACCESS read-write
        STATUS current
        DESCRIPTION
            "DURABLE: { true:all }
             This object is true(1) when this interface is enabled and
             false(1) when it is disabled.  For this product, this is the
             ONLY way to enable or disable this interface.  Note that
             'ifAdminStatus' in RFC1213 and RFC2233 and 'dot1dStpPortEnable'
             in RFC1493 are each implemented as 'read-only'."
        ::= { wandOemArchIfaceEntry 6 }

    wandOemArchIfaceLink OBJECT-TYPE
        SYNTAX INTEGER {
             up(1), 
             down(2)
        }
        MAX-ACCESS read-only
        STATUS current
        DESCRIPTION
            "The state of Link Detect on this interface."
        ::= { wandOemArchIfaceEntry 7 }

   wandOemArchIfaceDuplexSpeed OBJECT-TYPE
        SYNTAX INTEGER {
             autonegotiate(1),
             half-10(2),
             full-10(3),
             half-100(4),
             full-100(5),
             illegal(99)
        }
        MAX-ACCESS read-write
        STATUS current
        DESCRIPTION
            "DURABLE: { autonegotiate:all }
            The desired speed and duplex for this interface. If the selected
            control is not possible on the interface, a value of illegal(99)
            is returned.  If the port type does NOT support the default
            of autonegotiate(1), then the application initializes the
            port to a valid value (e.g., 1000full(6)).  Note that not all
            controls are possible for all interfaces.  For example, only
            full-1000(6) is available for Gigabit Ethernet interfaces."
        ::= { wandOemArchIfaceEntry 8 }

   wandOemArchIfPriority OBJECT-TYPE
        SYNTAX INTEGER (0..7)
        MAX-ACCESS read-write
        STATUS current
        DESCRIPTION
            " "
        ::= { wandOemArchIfaceEntry 9 } 
  
    wandOemArchIfBroadCast OBJECT-TYPE
     SYNTAX INTEGER(0..4)
        MAX-ACCESS read-write
        STATUS current
        DESCRIPTION
            " forbit broadcast or not
             0--0k;
             1--128k;
             2--512k;
             3--1024k;
             4--no limit;
            "
        ::= { wandOemArchIfaceEntry 10 }  
------------------------------------------------------------------------------
--  Chip Interface Section  
------------------------------------------------------------------------------
--
    wandOemChipStub OBJECT-TYPE
        SYNTAX INTEGER {  
            noop(1),
            chip-value2(2),
            chip-value3(3)
        }
        MAX-ACCESS read-write
        STATUS current
        DESCRIPTION
            "This object is a place holder for the OEM Chip interface." 
        ::= { wandOemChip 1 }


------------------------------------------------------------------------------
--  conformance information
------------------------------------------------------------------------------

--  --------------------------------------------------------------------------
--  units of conformance
--  --------------------------------------------------------------------------

    wandOemArchIfaceGroup   OBJECT-GROUP
        OBJECTS {
	        wandOemArchIfaceUnit    ,
	        wandOemArchIfacePort    ,
	        wandOemArchIfaceLLWHPort   ,
	        wandOemArchIfaceIfIndex    ,
	        wandOemArchIfaceName       ,
	        wandOemArchIfaceEnable,
	        wandOemArchIfaceLink  ,
	        wandOemArchIfaceDuplexSpeed ,
	        wandOemArchIfPriority,
	        wandOemArchIfBroadCast       
           }
        STATUS  current
        DESCRIPTION
           "This group configures and retrieves Architecture interface
            specific objects."
        ::= { wandOemProdGroups 1 }
    
    wandOemChipGroup    OBJECT-GROUP
        OBJECTS {
            wandOemChipStub
        }
        STATUS  current
        DESCRIPTION
           "This group configures OEM Chip specific objects."
        ::= { wandOemProdGroups 2 }
    

--  --------------------------------------------------------------------------
--  compliance statements
--  --------------------------------------------------------------------------

    wandOemProdCompliance MODULE-COMPLIANCE
        STATUS  current
        DESCRIPTION
           "The compliance statement."
        MODULE  -- this module
        MANDATORY-GROUPS {
             wandOemArchIfaceGroup
        }
        
    GROUP   wandOemChipGroup
    DESCRIPTION
        "This group is optional."
        
        ::= { wandOemProdCompliances 1 }

--
-- END of OEM-BCM5600-MIB                
--
END




------------------------------------------------------------------------------
--
--  File         : wandVlanMult.mi2
--  Description  : ZTE WAND VLAN SURRPOR MULTICAST NUMBER MIB  
--
------------------------------------------------------------------------------

WAND-VLANMULT-MIB DEFINITIONS ::= BEGIN

	IMPORTS
		MODULE-IDENTITY, OBJECT-TYPE,
		enterprises					FROM SNMPv2-SMI
		MODULE-COMPLIANCE, OBJECT-GROUP			FROM SNMPv2-CONF
		wandVlanMultMib					FROM WRS-MASTER-MIB;
	
	   
        wandVlanSurportMultNum  OBJECT-TYPE
        SYNTAX INTEGER 
        MAX-ACCESS read-only
        STATUS current
        DESCRIPTION
            " at present the vlan numbers of surporting multicast "
           ::= { wandVlanMultMib 1 }
                  
       wandPvcSurMultTable   OBJECT-TYPE
       SYNTAX      SEQUENCE OF WandPvcSurMultEntry
       MAX-ACCESS  not-accessible
       STATUS      current
       DESCRIPTION
        " the vlan of surporting multicast table  "
            ::= { wandVlanMultMib 2 }

       wandPvcSurMultEntry OBJECT-TYPE
       SYNTAX      WandPvcSurMultEntry
       MAX-ACCESS  not-accessible
       STATUS      current
       DESCRIPTION
        "the vlan of surporting multicast entry"
       INDEX   {wandVlanId}
       ::= { wandPvcSurMultTable 1 }

       WandPvcSurMultEntry ::=
         SEQUENCE {
            wandVlanId
                INTEGER,              
            wandVlanSurMultFlag 
                RowStatus
           }

       wandVlanId OBJECT-TYPE
         SYNTAX      INTEGER
         MAX-ACCESS  not-accessible
         STATUS      current
         DESCRIPTION
            " the vlan id of surporting multicast  "
         REFERENCE
              ""
        ::= { wandPvcSurMultEntry 1 }

       wandVlanSurMultFlag OBJECT-TYPE
          SYNTAX      RowStatus
          MAX-ACCESS  read-write
          STATUS      current
          DESCRIPTION
             "the set the flag of surporting multicast  "
    ::= { wandPvcSurMultEntry 2 }        

END
------------------------------------------------------------------------------
--
--  File         : wandPortStaticMACMib.mib
--  Description  : ZTE ADSL WAND PORT SURPORT MACADDRESS MIB  
--
------------------------------------------------------------------------------
WAND-PORTSTATICMAC-MIB DEFINITIONS ::= BEGIN

	IMPORTS
    		MODULE-IDENTITY, OBJECT-TYPE,
    		Counter32, Counter64, Unsigned32, TimeTicks,
			  Integer32, enterprises		FROM SNMPv2-SMI
    
    		RowStatus, TruthValue, TEXTUAL-CONVENTION, MacAddress
        							FROM SNMPv2-TC
        											
			  MODULE-COMPLIANCE, OBJECT-GROUP	FROM SNMPv2-CONF
		wandPortStaticMACMib	  		        FROM WRS-MASTER-MIB
			  dot1dBridge, dot1dBasePortEntry, dot1dBasePort
								FROM BRIDGE-MIB;



wandPortStaticMacTable   OBJECT-TYPE
    SYNTAX      SEQUENCE OF WandPortStaticMacEntry
    MAX-ACCESS  not-accessible
    STATUS      current
    DESCRIPTION
        " "
    ::= { wandPortStaticMACMib 1 }

wandPortStaticMacEntry OBJECT-TYPE
    SYNTAX      WandPortStaticMacEntry
    MAX-ACCESS  not-accessible
    STATUS      current
    DESCRIPTION
        ""
    INDEX   {MACADDRESS,VID,PortId}
    ::= { wandPortStaticMacTable 1 }

WandPortStaticMacEntry ::=
    SEQUENCE{
        MACADDRESS 
             MacAddress,
	VID
             INTEGER,
	PortId
             INTEGER,
        status
             INTEGER        
    }

 MACADDRESS OBJECT-TYPE
    SYNTAX      MacAddress 
    MAX-ACCESS  not-accessible
    STATUS      current
    DESCRIPTION
 	 "the port Staticport mac address value "
    REFERENCE
        ""
    ::= { wandPortStaticMacEntry 1 }
    

 VID OBJECT-TYPE
  SYNTAX      INTEGER
  MAX-ACCESS  not-accessible
  STATUS      current
  DESCRIPTION
      "the vlan id of port exsist "
  REFERENCE
        ""
    ::= { wandPortStaticMacEntry 2 }

 PortId OBJECT-TYPE
  SYNTAX      INTEGER
  MAX-ACCESS  not-accessible
  STATUS      current
  DESCRIPTION
      "the pvc port id "
  REFERENCE
        ""
    ::= { wandPortStaticMacEntry 3 }

status OBJECT-TYPE
   SYNTAX INTEGER {
          enable(1),
          disable(2)
       }
   MAX-ACCESS  read-write
   STATUS      current
   DESCRIPTION
      " according vpi and vpi ,to get the port id "
   REFERENCE
        ""
    ::= { wandPortStaticMacEntry 4 }

-- END of WAND-PORTSTATICMAC-MIB                
END


 IMA-GROUP-MIB DEFINITIONS ::= BEGIN
 IMPORTS
  	MODULE-IDENTITY, OBJECT-TYPE, Integer32, 
  	Counter32, Gauge32, NOTIFICATION-TYPE     FROM SNMPv2-SMI
		
	MODULE-COMPLIANCE, OBJECT-GROUP, 
	NOTIFICATION-GROUP                        FROM SNMPv2-CONF
		                                
	TEXTUAL-CONVENTION, DateAndTime, 
	RowStatus                                 FROM SNMPv2-TC
	
	InterfaceIndex, InterfaceIndexOrZero, 
	ifIndex					  FROM IF-MIB

                    
	zxIma     	                          FROM WRS-MASTER-MIB;


atmfImaGroupMib MODULE-IDENTITY
	LAST-UPDATED "9902111830Z"
	ORGANIZATION "The ATM Forum"
	CONTACT-INFO
		"ATM Forum
		World Headquarters
		2570 West El Camino Real
		Suite 304
		Mountain View, CA 94040-1313
		USA
		Phone: +1 415 949 6700
		Fax: +1 415 949 6705
		email: info@atmforum.com"
	DESCRIPTION
		"The MIB module for managing ATM Forum Inverse Multiplexing
		for ATM (IMA) interfaces."
	REVISION "9902111830Z"
	DESCRIPTION
		"Updated and repaired version of the IMA-MIB released with the
		IMA v1.1 specification (af-phy-0086.001)."
	REVISION "9701092245Z"
	DESCRIPTION
		"Initial incomplete version of the IMA-MIB as published in the
		IMA v1.0 specification (af-phy-0086.000)."
	::= { zxIma 2 }

-- The object identifier subtree for the IMA-MIB

atmfImaGroupMibObjects OBJECT IDENTIFIER ::= { atmfImaGroupMib 1 }
atmfImaMibTraps OBJECT IDENTIFIER ::=  { atmfImaGroupMib 2 }
atmfImaMibTrapPrefix OBJECT IDENTIFIER ::= { atmfImaMibTraps 0 }

atmfImaMibGroupConformance OBJECT IDENTIFIER ::= { atmfImaGroupMib 3 }
atmfImaGroupGroups         OBJECT IDENTIFIER ::= { atmfImaMibGroupConformance 1}
atmfImaGroupCompliances    OBJECT IDENTIFIER ::= { atmfImaMibGroupConformance 2 }
	
-- Textual conventions
ImaGroupState ::= TEXTUAL-CONVENTION
	STATUS current
	DESCRIPTION
		"State of the IMA group."
	REFERENCE
		"ATM Forum IMA v1.1, Section 10.2.1 on page 55"
	SYNTAX INTEGER{
		notConfigured(1),
		startUp(2),
		startUpAck(3),
		configAbortUnsupportedM(4),
		configAbortIncompatibleSymmetry(5),
		configAbortOther(6),
		insufficientLinks(7),
		blocked(8),
		operational(9),
		configAbortUnsupportedImaVersion(10) }

ImaAlarmStatus ::= TEXTUAL-CONVENTION
	STATUS current
	DESCRIPTION
		"A qualification of the IMA trap which indicates if the
		condition causing the trap has been detected (declared)
		or is no longer present (cleared)."
	SYNTAX INTEGER{
		cleared(1),
		declared(2) }
		
ImaAlarmType ::= TEXTUAL-CONVENTION
	STATUS current
	DESCRIPTION
		"An identification of the event that caused the generation
		of the IMA trap."
	REFERENCE
		"ATM Forum IMA v1.1, Section 12.2.3 on page 79"
	SYNTAX INTEGER {
		imaAlarmLinkLif(1),
		imaAlarmLinkLods(2),
		imaAlarmLinkRfi(3),
		imaAlarmLinkTxMisConnect(4),
		imaAlarmLinkRxMisConnect(5),
		imaAlarmLinkTxFault(6),
		imaAlarmLinkRxFault(7),
		imaAlarmLinkTxUnusableFe(8),
		imaAlarmLinkRxUnusableFe(9),
		imaAlarmGroupStartupFe(10),
		imaAlarmGroupCfgAbort(11),
		imaAlarmGroupCfgAbortFe(12),
		imaAlarmGroupInsuffLinks(13),
		imaAlarmGroupInsuffLinksFe(14),
		imaAlarmGroupBlockedFe(15),
		imaAlarmGroupTimingSynch(16) }

ImaGroupTxClkMode ::= TEXTUAL-CONVENTION
	STATUS current
	DESCRIPTION
		"Indicate the transmit clock mode of the IMA group.
		There are two possible modes: the Common Transmit
		Clock (CTC) and the Independent Transmit Clock (ITC).
		The CTC mode corresponds to the case when the transmit clock
		of all IMA links are derived from the same source. The ITC
		configuration corresponds to the case where there is at least
		one IMA link whose transmit clock is derived from a source
		different than at least another link transmit clock."
	REFERENCE
		"ATM Forum IMA v1.1, Section 7 on page 38"
	SYNTAX INTEGER{
		ctc(1),
		itc(2) }

ImaGroupSymmetry ::= TEXTUAL-CONVENTION
	STATUS current
	DESCRIPTION
		"The group symmetry mode adjusted during the group start-up."
	REFERENCE
		"ATM Forum IMA v1.1, Section 5.2.2.7 on page 35"
	SYNTAX INTEGER {
		symmetricOperation(1),
		asymmetricOperation(2),
		asymmetricConfiguration(3) }

ImaFrameLength ::= TEXTUAL-CONVENTION
	STATUS current
	DESCRIPTION
		"Length of the IMA frames."
	REFERENCE
		"ATM Forum IMA v1.1, Section 5.2.2.4.2 on page 34"
	SYNTAX INTEGER {
		m32(32),
		m64(64),
		m128(128),
		m256(256) }

-- The IMA Group subtree
-- The IMA Group subtree consists of the number of IMA groups and a
-- table of IMA groups. Each entry in the table of IMA groups contains
-- information (configuration and status) specific to each group.

imaGroupNumber OBJECT-TYPE
	SYNTAX INTEGER  
	MAX-ACCESS read-only
	STATUS current
	DESCRIPTION
		"The number of IMA groups configured on this system."
::= { atmfImaGroupMibObjects 1 }

imaGroupTable OBJECT-TYPE
	SYNTAX SEQUENCE OF ImaGroupEntry
	MAX-ACCESS not-accessible
	STATUS current
	DESCRIPTION
	     "The IMA Group Configuration table."
::= { atmfImaGroupMibObjects 2 }

imaGroupEntry OBJECT-TYPE
	SYNTAX ImaGroupEntry
	MAX-ACCESS not-accessible
	STATUS current
	DESCRIPTION
		"An entry in the IMA Group table."
	INDEX { imaGroupIndex }
::= { imaGroupTable 1 }

ImaGroupEntry ::= SEQUENCE {
	imaGroupIndex           INTEGER,
	imaMemberOfGroup        INTEGER,
	imaGroupRowStatus       RowStatus,
	imaGroupIfIndex         InterfaceIndex,
	imaGroupNeState         ImaGroupState,
	imaGroupFeState         ImaGroupState,
	imaGroupSymmetry        ImaGroupSymmetry,
	imaGroupMinNumTxLinks   INTEGER,
	imaGroupMinNumRxLinks   INTEGER,
	imaGroupNeTxClkMode     ImaGroupTxClkMode,
	imaGroupTxImaId 	INTEGER,
	imaGroupRxImaId 	INTEGER,
	imaGroupTxFrameLength 	ImaFrameLength,
	imaGroupRxFrameLength 	ImaFrameLength,
	imaGroupLeastDelayLink 	INTEGER,
	imaGroupNumTxCfgLinks 	Gauge32,
	imaGroupNumRxCfgLinks 	Gauge32,
	imaGroupNumTxActLinks 	Gauge32,
	imaGroupNumRxActLinks 	Gauge32,
	imaGroupImaVersion    	INTEGER,
	imaGroupGtsmState     	INTEGER,
	imaGroupInhibitStatus   INTEGER,
	imaGroupRxTilLid       	INTEGER,
	imaGroupDiffDelayMaxObs Counter32,
	imaGroupCLKMode		INTEGER
}
	
imaGroupIndex OBJECT-TYPE
	SYNTAX 	   INTEGER
	MAX-ACCESS read-only
	STATUS     current
	DESCRIPTION
	"A unique value for the IMA Group."
::= { imaGroupEntry 1 }

imaMemberOfGroup   OBJECT-TYPE
	SYNTAX     INTEGER
	MAX-ACCESS read-write
	STATUS current
	DESCRIPTION
		"The links of the Group "
::= { imaGroupEntry 2 }

imaGroupRowStatus OBJECT-TYPE
	SYNTAX 		RowStatus
	MAX-ACCESS 	read-create
	STATUS current
	DESCRIPTION
	       "The imaGroupRowStatus object allows create, change, and delete
		operations on imaGroupTable entries.
		To create a new conceptual row (or instance) of the imaGroupTable,
		imaGroupRowStatus must be set to 'createAndWait' or 'createAndGo'.
		If settable, a successful set of the following objects must be
		performed before the imaGroupRowStatus of a new conceptual row can
		be set to 'active':
			imaGroupMinNumTxLinks
			imaGroupMinNumRxLinks
			imaGroupTxImaId
		Some objects in the imaGroupTable control settings which can only
		be established or changed at group start-up time. These objects
		include:
			imaGroupTxImaId
			imaGroupSymmetry
			imaGroupTxFrameLength
		To change (modify) the imaGroupTxImaId object, the manager must
		first set imaGroupRowStatus to 'notInService'. However, changes
		to the following two objects can be optionally allowed while the
			imaGroupRowStatus is 'active':
			imaGroupSymmetry
			imaGroupTxFrameLength
		These two objects can be changed when the imaGroupRowStatus is
		'active' in order to allow the far-end to recover from its
		Config-Aborted state without having to force the near-end Group
		State machine to go to the 'Not Configured' state. Changing
		these object values after group start-up has completed causes a
		restart of the IMA group.
		Alternatively, as noted above, the agent implementation may
		simply require the imaGroupRowStatus object to first be set to
		'notInService' before allowing changes to either of these two
		objects.
			To remove (delete) an imaGroupTable entry from this table, set
		imaGroupRowStatus to 'destroy'.
		Setting the imaGroupRowStatus to 'active' has the effect of
		activating the Group Startup Procedure. The Group Startup
		Procedure uses provisioned links that have imaLinkRowStatus set
		to 'active' and imaLinkGroupIndex set to the imaGroupIndex in
		this conceptual row.
			When the imaGroupRowStatus is not in 'active' state, the Group
		State machine is in its 'Not Configured' state."
::= { imaGroupEntry 3 }

imaGroupIfIndex OBJECT-TYPE
	SYNTAX InterfaceIndex
	MAX-ACCESS read-only
	STATUS current
	DESCRIPTION
		"This object identifies the logical interface number ('ifIndex')
		assigned to this IMA group, and is used to identify corresponding
		rows in the Interfaces MIB.
		Note that re-initialization of the management agent may cause
		a client's 'imaGroupIfIndex' to change."
::= { imaGroupEntry 4 }

imaGroupNeState OBJECT-TYPE
	SYNTAX ImaGroupState
	MAX-ACCESS read-only
	STATUS current
	DESCRIPTION
		"The current operational state of the near-end IMA Group State
	Machine."
	REFERENCE
		"ATM Forum IMA v1.1, Section 10.2.1 on page 55"
::= { imaGroupEntry 5 }

imaGroupFeState OBJECT-TYPE
	SYNTAX ImaGroupState
	MAX-ACCESS read-only
	STATUS current
	DESCRIPTION
		"The current operational state of the far-end IMA Group State
	Machine."
	REFERENCE
		"ATM Forum IMA v1.1, Section 10.2.1 on page 55"
::= { imaGroupEntry 6 }

imaGroupSymmetry OBJECT-TYPE
	SYNTAX ImaGroupSymmetry
	MAX-ACCESS read-only
	STATUS current
	DESCRIPTION
		"Symmetry of the IMA group."
	REFERENCE
	"ATM Forum IMA v1.1, Section 5.2.2.7 on page 35"
		DEFVAL { symmetricOperation }
::= { imaGroupEntry 7 }

imaGroupMinNumTxLinks OBJECT-TYPE
	SYNTAX INTEGER
	MAX-ACCESS read-write
	STATUS current
	DESCRIPTION
		"Minimum number of transmit links required to be Active for
	the IMA group to be in the Operational state."
	REFERENCE
		"ATM Forum IMA v1.1, Section 10.2.1.1 on page 55"
::= { imaGroupEntry 8 }

imaGroupMinNumRxLinks OBJECT-TYPE
	SYNTAX INTEGER
	MAX-ACCESS read-write
	STATUS current
	DESCRIPTION
		"Minimum number of receive links required to be Active for
	the IMA group to be in the Operational state."
	REFERENCE
		"ATM Forum IMA v1.1, Section 10.2.1.1 on page 55"
::= { imaGroupEntry 9 }

imaGroupNeTxClkMode OBJECT-TYPE
	SYNTAX ImaGroupTxClkMode{
	              ctc(1),
	              itc(2)
	}	
	MAX-ACCESS read-write
	STATUS current
	DESCRIPTION
		"Transmit clocking mode used by the near-end IMA group."
	REFERENCE
	"ATM Forum IMA v1.1, Section 7 on page 38"
	DEFVAL { ctc }
::= { imaGroupEntry 10 }

imaGroupTxImaId OBJECT-TYPE
	SYNTAX INTEGER
	MAX-ACCESS read-write
	STATUS current
	DESCRIPTION
		"The IMA ID currently in use by the near-end IMA function."
	REFERENCE
		"ATM Forum IMA v1.1, Section 5.2.2.6 on page 35"
::= { imaGroupEntry 11 }

imaGroupRxImaId OBJECT-TYPE
	SYNTAX INTEGER
	MAX-ACCESS read-only
	STATUS current
	DESCRIPTION
		"The IMA ID currently in use by the far-end IMA function."
	REFERENCE
		"ATM Forum IMA v1.1, Section 5.2.2.6 on page 35"
::= { imaGroupEntry 12 }

imaGroupTxFrameLength OBJECT-TYPE
	SYNTAX ImaFrameLength
	MAX-ACCESS read-write
	STATUS current
	DESCRIPTION
		"The frame length to be used by the IMA group in the transmit
	direction. Can only be set when the IMA group is startup."
	REFERENCE
		"ATM Forum IMA v1.1, Section 5.2.2.4.2 on page 34"
	DEFVAL { m128 }
::= { imaGroupEntry 13 }

imaGroupRxFrameLength OBJECT-TYPE
	SYNTAX ImaFrameLength
	MAX-ACCESS read-only
	STATUS current
	DESCRIPTION
		"Value of IMA frame length as received from remote IMA function."
	REFERENCE
		"ATM Forum IMA v1.1, Section 5.2.2.4.2 on page 34"
::= { imaGroupEntry 14 }

imaGroupLeastDelayLink OBJECT-TYPE
	SYNTAX INTEGER
	MAX-ACCESS read-only
	STATUS current
	DESCRIPTION
		"The ifIndex of the link configured in the IMA group which has
	the smallest link propagation delay. The distinguished value of
	zero may be used if no link has been configured in the IMA group,
	or if the link with the smallest link propagation delay has not
	yet been determined."
	REFERENCE
		"ATM Forum IMA v1.1, Section 9.2 on page 45"
::= { imaGroupEntry 15 }

imaGroupNumTxCfgLinks OBJECT-TYPE
	SYNTAX Gauge32
	MAX-ACCESS read-only
	STATUS current
	DESCRIPTION
		"The number of links that are configured to transmit in this IMA
	group. This attribute overwrites the value of the
	imaGroupNumRxActLinks attribute when the IMA group is configured
	in the Symmetrical Configuration group symmetry mode."
::= { imaGroupEntry 16 }

imaGroupNumRxCfgLinks OBJECT-TYPE
	SYNTAX Gauge32
	MAX-ACCESS read-only
	STATUS current
	DESCRIPTION
		"The number of links that are configured to receive in this IMA
	group. This attribute is overwritten by the value of the
	imaGroupNumTxActLinks attribute when the IMA group is configured
	in the Symmetrical Configuration group symmetry mode."
::= { imaGroupEntry 17 }

imaGroupNumTxActLinks OBJECT-TYPE
	SYNTAX Gauge32
	MAX-ACCESS read-only
	STATUS current
	DESCRIPTION
		"The number of links which are configured to transmit and are
	currently Active in this IMA group."
::= { imaGroupEntry 18 }

imaGroupNumRxActLinks OBJECT-TYPE
	SYNTAX Gauge32
	MAX-ACCESS read-only
	STATUS current
	DESCRIPTION
		"The number of links which are configured to receive and are
	currently Active in this IMA group."
::= { imaGroupEntry 19 }

imaGroupImaVersion OBJECT-TYPE
	SYNTAX     INTEGER{ 
	                    version10(0),
	                    version11(1)
	}
	MAX-ACCESS read-write
	STATUS current
	DESCRIPTION
		"The version of Group  "
::= { imaGroupEntry 20 }

imaGroupGtsmState OBJECT-TYPE
	SYNTAX     INTEGER
	MAX-ACCESS read-only
	STATUS current
	DESCRIPTION
		"The state of Group "
::= { imaGroupEntry 21 }

imaGroupInhibitStatus OBJECT-TYPE
	SYNTAX     INTEGER{
	                   up(1),
	                 down(2)
	}
	MAX-ACCESS read-write
	STATUS current
	DESCRIPTION
		"The state of Group  "
::= { imaGroupEntry 22 }

imaGroupRxTilLid OBJECT-TYPE
	SYNTAX     INTEGER
	MAX-ACCESS read-only
	STATUS current
	DESCRIPTION
		" "
::= { imaGroupEntry 23 }

imaGroupDiffDelayMaxObs OBJECT-TYPE
	SYNTAX     Counter32 
	MAX-ACCESS read-only
	STATUS current
	DESCRIPTION
		" The latest maximum differential delay observed (in milliseconds)
	between the links having the least and most link propagation delay,
	among the receive links that are currently configured in the IMA
	group."
::= { imaGroupEntry 24 }

imaGroupCLKMode   OBJECT-TYPE
	SYNTAX     INTEGER{
			master(0),
			 slave(1)
	}
	MAX-ACCESS read-write
	STATUS current
	DESCRIPTION
		"The clock mode of the Group "
::= { imaGroupEntry 25 }

-- IMA Failure Alarms
-- Implementation of the imaFailureAlarm Trap is optional.
imaAlarmStatus OBJECT-TYPE
	SYNTAX ImaAlarmStatus
	MAX-ACCESS accessible-for-notify
	STATUS current
	DESCRIPTION
		"Status of the IMA alarm."
::= { atmfImaGroupMibObjects 3 }

imaAlarmType OBJECT-TYPE
	SYNTAX ImaAlarmType
	MAX-ACCESS accessible-for-notify
	STATUS current
	DESCRIPTION
		"The Type of IMA alarm declared or cleared. The value of
	ImaAlarmType identifies the type of alarm according to the
	definitions in the IMA specification."
	REFERENCE
		"ATM Forum IMA v1.1, Section 12.2.3 on page 79"
::= { atmfImaGroupMibObjects 4 }

imaFailureAlarm NOTIFICATION-TYPE
	OBJECTS {
		ifIndex,
		imaAlarmStatus,
		imaAlarmType }
	STATUS current
	DESCRIPTION
		"The imaFailureAlarm provides a method for an agent implementing IMA
	to notify an NMS of an alarm condition."
	REFERENCE
		"ATM Forum IMA v1.1, Section 12.2.3 on page 79"
::= { atmfImaMibTrapPrefix 1 }

-- The IMA Group Current Statistics subtree
-- The IMA Group Current Statistics subtree consists of a single table:
-- the IMA Group Current Table.    This table contains various statistics
-- collected by each IMA group for the current 15 minute interval.
-- Implementation of IMA Group Current Table is optional.
imaGroupCurrentTable OBJECT-TYPE
           SYNTAX         SEQUENCE OF ImaGroupCurrentEntry
           MAX-ACCESS    not-accessible
           STATUS         current
           DESCRIPTION
              " The IMA Group Current table."
           ::=  {atmfImaGroupMibObjects 5 }

imaGroupCurrentEntry OBJECT-TYPE
           SYNTAX           ImaGroupCurrentEntry
           MAX-ACCESS      not-accessible
           STATUS           current
           DESCRIPTION
              " An entry in the IMA Group Current table."
           INDEX      {imaGroupIndex }
           ::= { imaGroupCurrentTable 1 }

ImaGroupCurrentEntry ::= SEQUENCE{ 
          imaGroupCurrentTxDiscardedCells   Gauge32,
          imaGroupCurrentTxCells            Gauge32,
          imaGroupCurrentTxFillerCells      Gauge32,
          imaGroupCurrentRxCells            Gauge32,
          imaGroupCurrentRxDroppedCells     Gauge32,
          imaGroupCurrentRxFilleredCells    Gauge32,
          imaGroupCurrentRxFillerCells      Gauge32}
                              
                    
imaGroupCurrentTxDiscardedCells OBJECT-TYPE
           SYNTAX         Gauge32
           MAX-ACCESS    read-only
           STATUS         current
           DESCRIPTION
              "The current value of Group TxDiscardedCells"
           REFERENCE
              " "
           ::=  {imaGroupCurrentEntry 1}

imaGroupCurrentTxCells    OBJECT-TYPE
           SYNTAX         Gauge32
           MAX-ACCESS    read-only
           STATUS         current
           DESCRIPTION
              " The current value of Group TxCells"
           REFERENCE
              " "
           ::=  {imaGroupCurrentEntry 2}
           
imaGroupCurrentTxFillerCells    OBJECT-TYPE
           SYNTAX         Gauge32
           MAX-ACCESS    read-only
           STATUS         current
           DESCRIPTION
              " The current value of Group RxFillerCells"
           REFERENCE
              " "
           ::=  {imaGroupCurrentEntry 3}
           
imaGroupCurrentRxCells    OBJECT-TYPE
           SYNTAX         Gauge32
           MAX-ACCESS    read-only
           STATUS         current
           DESCRIPTION
              " "
           REFERENCE
              " The current value of Group RxCells"
           ::=  {imaGroupCurrentEntry 4}           
           
imaGroupCurrentRxDroppedCells    OBJECT-TYPE
           SYNTAX         Gauge32
           MAX-ACCESS    read-only
           STATUS         current
           DESCRIPTION
              " The current value of Group DroppedCells"
           REFERENCE
              " "
           ::=  {imaGroupCurrentEntry 5}             

imaGroupCurrentRxFilleredCells    OBJECT-TYPE
           SYNTAX         Gauge32
           MAX-ACCESS    read-only
           STATUS         current
           DESCRIPTION
              " The current value of Group FilleredCells"
           REFERENCE
              " "
           ::=  {imaGroupCurrentEntry 6} 
           
           
imaGroupCurrentRxFillerCells    OBJECT-TYPE
           SYNTAX         Gauge32
           MAX-ACCESS    read-only
           STATUS         current
           DESCRIPTION
              " The current value of Group RxFillerCells"
           REFERENCE
              " "
           ::=  {imaGroupCurrentEntry 7}
           
           
-- The IMA Group Interval Statistics subtree
-- The IMA Group Interval Statistics subtree consists of a single table:
-- the IMA Group Interval Table. This table contains various statistics
-- collected by each IMA group over the previous 24 hours of operation.
-- The past 24 hours are broken into 96 completed 15 minute intervals.
-- Implementation of IMA Group Interval Table is optional.

imaGroupIntervalTable OBJECT-TYPE
	SYNTAX SEQUENCE OF ImaGroupIntervalEntry
	MAX-ACCESS not-accessible
	STATUS current
	DESCRIPTION
		"The IMA Group Interval table."
::= { atmfImaGroupMibObjects 6 }

imaGroupIntervalEntry OBJECT-TYPE
	SYNTAX ImaGroupIntervalEntry
	MAX-ACCESS not-accessible
	STATUS current
	DESCRIPTION
		"An entry in the IMA Group Interval table."
	INDEX { imaGroupIndex, imaGroupIntervalNumber }
::= { imaGroupIntervalTable 1 }

ImaGroupIntervalEntry ::= SEQUENCE{
	imaGroupIntervalNumber               INTEGER,
	imaGroupIntervalTxDiscardedCells     Gauge32,
	imaGroupIntervalTxCells              Gauge32,
	imaGroupIntervalTxFillerCells        Gauge32,
	imaGroupIntervalRxCells              Gauge32,
	imaGroupIntervalRxDroppedCells       Gauge32,
	imaGroupIntervalRxFilleredCells      Gauge32,
	imaGroupIntervalRxFillerCells        Gauge32}
			
imaGroupIntervalNumber OBJECT-TYPE
	SYNTAX INTEGER
	MAX-ACCESS read-only
	STATUS current
	DESCRIPTION
		"A number between 1 and 96, where 1 is the most
	recently completed 15 minute interval and 96 is the least
	recently completed 15 minutes interval (assuming that all
	96 intervals are valid)."
::= { imaGroupIntervalEntry 1 }

imaGroupIntervalTxDiscardedCells OBJECT-TYPE
	SYNTAX    Gauge32
	MAX-ACCESS read-only
	STATUS current
	DESCRIPTION
		" A number between 1 and 96, where 1 is the most
	recently completed 15 minute interval and 96 is the least
	recently completed 15 minutes interval (assuming that all
	96 intervals are valid)."
::= { imaGroupIntervalEntry 2 }

imaGroupIntervalTxCells     OBJECT-TYPE
	SYNTAX    Gauge32
	MAX-ACCESS read-only
	STATUS current
	DESCRIPTION
		" A number between 1 and 96, where 1 is the most
	recently completed 15 minute interval and 96 is the least
	recently completed 15 minutes interval (assuming that all
	96 intervals are valid)."
::= { imaGroupIntervalEntry 3 }

imaGroupIntervalTxFillerCells     OBJECT-TYPE
	SYNTAX    Gauge32
	MAX-ACCESS read-only
	STATUS current
	DESCRIPTION
		"A number between 1 and 96, where 1 is the most
	recently completed 15 minute interval and 96 is the least
	recently completed 15 minutes interval (assuming that all
	96 intervals are valid). "
::= { imaGroupIntervalEntry 4 }


imaGroupIntervalRxCells           OBJECT-TYPE
	SYNTAX    Gauge32
	MAX-ACCESS read-only
	STATUS current
	DESCRIPTION
		"A number between 1 and 96, where 1 is the most
	recently completed 15 minute interval and 96 is the least
	recently completed 15 minutes interval (assuming that all
	96 intervals are valid). "
::= { imaGroupIntervalEntry 5 }


imaGroupIntervalRxDroppedCells    OBJECT-TYPE
	SYNTAX    Gauge32
	MAX-ACCESS read-only
	STATUS current
	DESCRIPTION
		" A number between 1 and 96, where 1 is the most
	recently completed 15 minute interval and 96 is the least
	recently completed 15 minutes interval (assuming that all
	96 intervals are valid)."
::= { imaGroupIntervalEntry 6 }

imaGroupIntervalRxFilleredCells    OBJECT-TYPE
	SYNTAX    Gauge32
	MAX-ACCESS read-only
	STATUS current
	DESCRIPTION
		" A number between 1 and 96, where 1 is the most
	recently completed 15 minute interval and 96 is the least
	recently completed 15 minutes interval (assuming that all
	96 intervals are valid)."
::= { imaGroupIntervalEntry 7 }

imaGroupIntervalRxFillerCells    OBJECT-TYPE
	SYNTAX    Gauge32
	MAX-ACCESS read-only
	STATUS current
	DESCRIPTION
		" A number between 1 and 96, where 1 is the most
	recently completed 15 minute interval and 96 is the least
	recently completed 15 minutes interval (assuming that all
	96 intervals are valid)."
::= { imaGroupIntervalEntry 8 }

-- The IMA Group Total Statistics subtree
-- The IMA Group Total Statistics subtree consists of a single table:
-- the IMA Group Total Table. This table contains various statistics
-- collected by each IMA group over the previous 24 hours of operation.
-- The past 24 hours are broken into 96 completed 15 minute intervals.
-- Implementation of IMA Group Interval Table is optional.

imaGroupTotalTable OBJECT-TYPE
	SYNTAX SEQUENCE OF ImaGroupTotalEntry
	MAX-ACCESS not-accessible
	STATUS current
	DESCRIPTION
		"The IMA Group Total table."
::= { atmfImaGroupMibObjects 7 }

imaGroupTotalEntry OBJECT-TYPE
	SYNTAX ImaGroupTotalEntry
	MAX-ACCESS not-accessible
	STATUS current
	DESCRIPTION
		"An entry in the IMA Group Total table."
	INDEX { imaGroupIndex }
::= { imaGroupTotalTable 1 }

ImaGroupTotalEntry ::= SEQUENCE{
	imaGroupTotalTxDiscardedCells     Gauge32,
	imaGroupTotalTxCells              Gauge32,
	imaGroupTotalTxFillerCells        Gauge32,
	imaGroupTotalRxCells              Gauge32,
	imaGroupTotalRxDroppedCells       Gauge32,
	imaGroupTotalRxFilleredCells      Gauge32,
	imaGroupTotalRxFillerCells        Gauge32}
			
imaGroupTotalTxDiscardedCells OBJECT-TYPE
	SYNTAX    Gauge32
	MAX-ACCESS read-only
	STATUS current
	DESCRIPTION
		" The Total value of Group TxDiscardedCells"
::= { imaGroupTotalEntry 1 }

imaGroupTotalTxCells     OBJECT-TYPE
	SYNTAX    Gauge32
	MAX-ACCESS read-only
	STATUS current
	DESCRIPTION
		" The Total value of Group TxCells"
::= { imaGroupTotalEntry 2 }

imaGroupTotalTxFillerCells     OBJECT-TYPE
	SYNTAX    Gauge32
	MAX-ACCESS read-only
	STATUS current
	DESCRIPTION
		" The Total value of Group TxFillerCells"
::= { imaGroupTotalEntry 3 }


imaGroupTotalRxCells           OBJECT-TYPE
	SYNTAX    Gauge32
	MAX-ACCESS read-only
	STATUS current
	DESCRIPTION
		" The Total value of Group RxCells"
::= { imaGroupTotalEntry 4 }


imaGroupTotalRxDroppedCells    OBJECT-TYPE
	SYNTAX    Gauge32
	MAX-ACCESS read-only
	STATUS current
	DESCRIPTION
		" The Total value of Group RxDroppedCells"
::= { imaGroupTotalEntry 5 }

imaGroupTotalRxFilleredCells    OBJECT-TYPE
	SYNTAX    Gauge32
	MAX-ACCESS read-only
	STATUS current
	DESCRIPTION
		" The Total value of Group RxFilleredCells"
::= { imaGroupTotalEntry 6 }

imaGroupTotalRxFillerCells    OBJECT-TYPE
	SYNTAX    Gauge32
	MAX-ACCESS read-only
	STATUS current
	DESCRIPTION
		"The Total value of Group RxFillerCells "
::= { imaGroupTotalEntry 7 }

imaSlotStand  OBJECT-TYPE
	SYNTAX INTEGER
	MAX-ACCESS read-only
	STATUS current
	DESCRIPTION
		"the slot of ima in the dislam"
::= { atmfImaGroupMibObjects 8 }

--  units of conformance
imaGroupNumberGroup OBJECT-GROUP
  OBJECTS{
     imaGroupNumber
  }
 STATUS  current
 DESCRIPTION 
       "imaGroupNumber group"
 ::={atmfImaGroupGroups 1}
 
 imaGroupGroup OBJECT-GROUP
  OBJECTS{ 
    	imaGroupNumber,
	imaMemberOfGroup,
	imaGroupRowStatus,
	imaGroupIfIndex,
	imaGroupNeState,
	imaGroupFeState,
	imaGroupSymmetry,
	imaGroupMinNumTxLinks,
	imaGroupMinNumRxLinks,
	imaGroupNeTxClkMode,
	imaGroupTxImaId,
	imaGroupRxImaId,
	imaGroupTxFrameLength,
	imaGroupRxFrameLength ,
	imaGroupLeastDelayLink,
	imaGroupNumTxCfgLinks ,
	imaGroupNumRxCfgLinks ,
	imaGroupNumTxActLinks ,
	imaGroupNumRxActLinks ,
	imaGroupImaVersion    ,
	imaGroupGtsmState     ,
	imaGroupInhibitStatus   ,
	imaGroupRxTilLid       	 ,
	imaGroupDiffDelayMaxObs  ,
	imaGroupCLKMode 
}    
       STATUS          current
       DESCRIPTION
              " A set of objects providing configuration and status information for
              an IMA group definition."
       ::=  {atmfImaGroupGroups 2 }
       
   imaAlarmGroup OBJECT-GROUP
           OBJECTS {
              imaAlarmStatus,
              imaAlarmType }
           STATUS          current
           DESCRIPTION
              " Objects used in the imaFailureAlarm notification."
   ::=  {atmfImaGroupGroups 3}
   
   imaGroupCurrentGroup OBJECT-GROUP
   OBJECTS{
          imaGroupCurrentTxDiscardedCells   ,
          imaGroupCurrentTxCells            ,
          imaGroupCurrentTxFillerCells      ,
          imaGroupCurrentRxCells            ,
          imaGroupCurrentRxDroppedCells     ,
          imaGroupCurrentRxFilleredCells    ,
          imaGroupCurrentRxFillerCells}
        STATUS          current
        DESCRIPTION
              " Objects containing current statistics for an IMA group."
           ::=  {atmfImaGroupGroups 4} 

   imaGroupIntervalGroup OBJECT-GROUP
      OBJECTS{
        imaGroupIntervalNumber        ,
	imaGroupIntervalTxDiscardedCells     ,
	imaGroupIntervalTxCells              ,
	imaGroupIntervalTxFillerCells        ,
	imaGroupIntervalRxCells              ,
	imaGroupIntervalRxDroppedCells       ,
	imaGroupIntervalRxFilleredCells      ,
	imaGroupIntervalRxFillerCells }       
        STATUS          current
        DESCRIPTION
              " Objects containing interval statistics for an IMA group."
           ::=  {atmfImaGroupGroups 5}  
  
  imaGroupTotalGroup OBJECT-GROUP
     OBJECTS{ 
    	imaGroupTotalTxDiscardedCells     ,
		imaGroupTotalTxCells              ,
		imaGroupTotalTxFillerCells        ,
		imaGroupTotalRxCells              ,
		imaGroupTotalRxDroppedCells       ,
		imaGroupTotalRxFilleredCells      ,
		imaGroupTotalRxFillerCells  }
            STATUS          current
        DESCRIPTION
              " Objects containing total statistics for an IMA group."
           ::=  {atmfImaGroupGroups 6}  
 
     imaNotificationsGroup NOTIFICATION-GROUP
          NOTIFICATIONS 
             {imaFailureAlarm}
          STATUS          current
          DESCRIPTION
              " Notifications that must be implemented for IMA groups and links."
           ::=  {atmfImaGroupGroups 7} 
           
	imaSlotStandGroup OBJECT-GROUP
  	OBJECTS{
     			imaSlotStand
  		}
 	STATUS  current
 	DESCRIPTION 
              " Objects used in the imaGroup."
   ::=  {atmfImaGroupGroups 8}


                         
--  compliance statements
    atmfImaMibCompliance MODULE-COMPLIANCE
    STATUS  current
    DESCRIPTION
           "The compliance statement."
    MODULE  -- this module
    MANDATORY-GROUPS{
            imaGroupNumberGroup,
            imaGroupGroup,
            imaAlarmGroup,
            imaGroupCurrentGroup,
            imaGroupIntervalGroup,
            imaGroupTotalGroup,
            imaNotificationsGroup,
            imaSlotStandGroup
            }
        ::= { atmfImaGroupCompliances 1 }
END

 
 IMA-SYS-MIB DEFINITIONS ::= BEGIN
     IMPORTS
        MODULE-IDENTITY, OBJECT-TYPE,
        Counter32, Gauge32,
        Unsigned32, Integer32                  FROM SNMPv2-SMI
        
        RowStatus, TruthValue, 
        DisplayString, MacAddress               FROM SNMPv2-TC
       
        MODULE-COMPLIANCE, OBJECT-GROUP         FROM SNMPv2-CONF
        
        zxIma     	                        FROM WRS-MASTER-MIB;

 	
  atmfImaSysMib MODULE-IDENTITY
		LAST-UPDATED "9902111830Z"
		ORGANIZATION "The ATM Forum"
		CONTACT-INFO
			"ATM Forum	World Headquarters
			2570 West El Camino Real
			Suite 304 Mountain View, CA 94040-1313
			USA
			Phone: +1 415 949 6700
			Fax: +1 415 949 6705
			email: info@atmforum.com"
		DESCRIPTION
				"The MIB module for managing ATM Forum Inverse Multiplexing
			for ATM (IMA) interfaces."
			REVISION "9902111830Z"
		DESCRIPTION
				"Updated and repaired version of the IMA-MIB released with the
			IMA v1.1 specification (af-phy-0086.001)."
			REVISION "9701092245Z"
		DESCRIPTION
			"Initial incomplete version of the IMA-MIB as published in the
		IMA v1.0 specification (af-phy-0086.000)."
	::= { zxIma 1 }

-- The object identifier subtree for the IMA-MIB.

atmfImaSysMibObjects    OBJECT IDENTIFIER ::= { atmfImaSysMib 1 }
atmfImaSysMibConformance OBJECT IDENTIFIER ::= { atmfImaSysMib 2 }

atmfImaSysGroups         OBJECT IDENTIFIER ::= { atmfImaSysMibConformance 1}
atmfImaSysCompliances    OBJECT IDENTIFIER ::= { atmfImaSysMibConformance 2 }

imaSysMaxSupportedGroupNumber OBJECT-TYPE
	SYNTAX Integer32
	MAX-ACCESS read-only
	STATUS current
	DESCRIPTION
		"The max number of IMA groups supported in this system
	the default value:16 "
::= { atmfImaSysMibObjects 1 }

imaSysMaxSupportedLinkNumber OBJECT-TYPE
	SYNTAX Integer32
	MAX-ACCESS read-only
	STATUS current
	DESCRIPTION
		"The max number of IMA Links supported in this system
	the default value:16 "
::= { atmfImaSysMibObjects 2 }

imaSysSaveCommand OBJECT-TYPE
	SYNTAX INTEGER{
		noop(1),            -- no operation
                save(2),           -- save the data into flash
               inProgress(3)       -- read-only: process in progress
	}
	MAX-ACCESS read-write
	STATUS current
	DESCRIPTION
		"save  the data in the flash
	the default value:1 "
::= { atmfImaSysMibObjects 3 }

imaSysClearCommand OBJECT-TYPE
	SYNTAX INTEGER{
		noop(1),            -- no operation
                clear(2),           -- clear the data in flash
               inProgress(3)       -- read-only: process in progress
	}
	MAX-ACCESS read-write
	STATUS current
	DESCRIPTION
		"clear the data in the flash
	the default value:1 "
::= { atmfImaSysMibObjects 4 }

imaSysResetCommand OBJECT-TYPE
	SYNTAX INTEGER{
		noop(1),            -- no operation
                reset(2)           -- resets the unit
	}
	MAX-ACCESS read-write
	STATUS current
	DESCRIPTION
		"performs a hardware reset of the unit
	the default value:1 "
::= { atmfImaSysMibObjects 5 }

--the IMA system configuration MIB 
--
-- The IMA system subtree

imaSystemConfigurationTable OBJECT-TYPE
	SYNTAX SEQUENCE OF ImaSystemConfigurationEntry
	MAX-ACCESS not-accessible
	STATUS current
	DESCRIPTION
		"The system configuration table."
::= { atmfImaSysMibObjects 6 }

imaSystemConfigurationEntry OBJECT-TYPE
	SYNTAX ImaSystemConfigurationEntry
	MAX-ACCESS not-accessible
	STATUS current
	DESCRIPTION
		"An entry in the system configuration table."
	INDEX { imaSysIndex }
::= { imaSystemConfigurationTable 1 }

ImaSystemConfigurationEntry ::= SEQUENCE {
	imaSysIndex                 Integer32,
	imaSysAlphaValue            Integer32,
	imaSysBetaValue     	    Integer32,
	imaSysToutStartUpAck        Integer32,
	imaSysToutGrpCfgAbort       Integer32,
	imaSysToutRxUsable          Integer32,
	imaSysToutRxActive          Integer32,
	imaSysToutTxActive          Integer32,
	imaSysToutTxLinkDel         Integer32,
	imaSysToutRxLinkBlk         Integer32,
	imaSysToutRxLinkDel         Integer32,
	imaSysGamma                 Integer32,
	imaSysTimeTickCfg           Integer32
	}

imaSysIndex OBJECT-TYPE
	SYNTAX Integer32
	MAX-ACCESS read-only
	STATUS current
	DESCRIPTION
	    "A unique value for the IMA SystemGroup."
::= { imaSystemConfigurationEntry 1 }

imaSysAlphaValue OBJECT-TYPE
	SYNTAX Integer32
	MAX-ACCESS read-only
	STATUS current
	DESCRIPTION
	       "IFSM parameter of IMA system "
::= { imaSystemConfigurationEntry 2 }

imaSysBetaValue OBJECT-TYPE
	SYNTAX Integer32
	MAX-ACCESS read-only
	STATUS current
	DESCRIPTION
		"IFSM parameter of the IMA system "
::= { imaSystemConfigurationEntry 3 }

imaSysToutStartUpAck OBJECT-TYPE
	SYNTAX Integer32
	MAX-ACCESS read-only
	STATUS current
	DESCRIPTION
		"Determines how long GSM stays in 
	Startup-Ack state before moving back to Startup state(0-15) "
::= { imaSystemConfigurationEntry 4 }

imaSysToutGrpCfgAbort OBJECT-TYPE
	SYNTAX Integer32
	MAX-ACCESS read-only
	STATUS current
	DESCRIPTION
		"Determines how long GSM stays in Config-Aborted state
	before moving back to Startup state (0-15) "
::= { imaSystemConfigurationEntry 5 }


imaSysToutRxUsable OBJECT-TYPE
	SYNTAX Integer32
	MAX-ACCESS read-only
	STATUS current
	DESCRIPTION
		"Determine when a Group startup/LASR procedure times out 
	if RX links don't become usable "
::= { imaSystemConfigurationEntry 6 }

imaSysToutRxActive OBJECT-TYPE
	SYNTAX Integer32
	MAX-ACCESS read-only
	STATUS current
	DESCRIPTION
		"Determine when a Group startup/LASR procedure times out 
	if RX links don't move from usable to active state (0-15)"
::= { imaSystemConfigurationEntry 7 }

imaSysToutTxActive OBJECT-TYPE
	SYNTAX Integer32
	MAX-ACCESS read-only
	STATUS current
	DESCRIPTION
		"Determines how much time should elapse before moving TX 
	LSMs to active state in Group Startup/LASR procedures (0-15) "
::= { imaSystemConfigurationEntry 8}

imaSysToutTxLinkDel OBJECT-TYPE
	SYNTAX Integer32
	MAX-ACCESS read-only
	STATUS current
	DESCRIPTION
		"Determines how long the TX LSM should stay in deleted 
        state before it can move to unassigned state (0-15) "
::= { imaSystemConfigurationEntry 9}

imaSysToutRxLinkBlk OBJECT-TYPE
	SYNTAX Integer32
	MAX-ACCESS read-only
	STATUS current
	DESCRIPTION
		"Determines how long the RX LSM should stay in blocked 
	state before it can move to unusable state (0-15) "
::= { imaSystemConfigurationEntry 10}

imaSysToutRxLinkDel OBJECT-TYPE
	SYNTAX Integer32
	MAX-ACCESS read-only
	STATUS current
	DESCRIPTION
		"Determines how long the RX LSM should stay in deleted
	state before it can move to unassigned state (0-15) "
::= { imaSystemConfigurationEntry 11}

imaSysGamma OBJECT-TYPE
	SYNTAX     Integer32
	MAX-ACCESS read-only
	STATUS current
	DESCRIPTION
		"IFSM parameter(1-5)"
::= { imaSystemConfigurationEntry 12}

imaSysTimeTickCfg OBJECT-TYPE
	SYNTAX     Integer32
	MAX-ACCESS read-only
	STATUS current
	DESCRIPTION
		"Timer tick interval (divisor) (0-0xffff)"
::= { imaSystemConfigurationEntry 13}


--  units of conformance
--  add part of self_definition
          
  imaSysMaxSupportedGroupNumberGroup  OBJECT-GROUP
        OBJECTS {
            imaSysMaxSupportedGroupNumber        
        }
        STATUS  current
        DESCRIPTION
           "lanGenericObjects group "
        ::= { atmfImaSysGroups 1 }
        
   imaSysMaxSupportedLinkNumberGroup   OBJECT-GROUP
        OBJECTS {
            imaSysMaxSupportedLinkNumber        
        }
        STATUS  current
        DESCRIPTION
           "lanGenericObjects group "
        ::= { atmfImaSysGroups 2 }
        
   imaSysSaveCommandGroup  OBJECT-GROUP
        OBJECTS{
            imaSysSaveCommand        
        }
        STATUS  current
        DESCRIPTION
           " "
        ::= { atmfImaSysGroups 3 }
     
     imaSysClearCommandGroup  OBJECT-GROUP
        OBJECTS{
            imaSysClearCommand        
        }
        STATUS  current
        DESCRIPTION
           " "
        ::= { atmfImaSysGroups 4 }
        
      imaSysResetCommandGroup  OBJECT-GROUP
        OBJECTS{
            imaSysResetCommand        
        }
        STATUS  current
        DESCRIPTION
           " "
        ::= { atmfImaSysGroups 5 }	
        
   imaSystemConfigurationGroup  OBJECT-GROUP
    OBJECTS 
    {
		imaSysAlphaValue            ,
		imaSysBetaValue     	    ,
		imaSysToutStartUpAck        ,
		imaSysToutGrpCfgAbort       ,
		imaSysToutRxUsable          ,
		imaSysToutRxActive          ,
		imaSysToutTxActive          ,
		imaSysToutTxLinkDel         ,
		imaSysToutRxLinkBlk         ,
		imaSysToutRxLinkDel         ,
		imaSysGamma                 ,
		imaSysTimeTickCfg}           
	
	STATUS          current
    DESCRIPTION
              " Objects containing system configuration of IMA link."
::=  {atmfImaSysGroups 6} 
           
--  compliance statements

    atmfImaSysMibCompliance MODULE-COMPLIANCE
    STATUS  current
    DESCRIPTION
           "The compliance statement."
    MODULE  -- this module
    MANDATORY-GROUPS {
                  imaSysMaxSupportedGroupNumberGroup,
                  imaSysMaxSupportedLinkNumberGroup,
                  imaSysSaveCommandGroup,
                  imaSysClearCommandGroup,
                  imaSysResetCommandGroup,	
                  imaSystemConfigurationGroup}
       ::= { atmfImaSysCompliances 1 }
        
END
 
 IMA-LINK-MIB DEFINITIONS ::= BEGIN

 IMPORTS
  	MODULE-IDENTITY, OBJECT-TYPE, Integer32, Counter32, Gauge32,
	NOTIFICATION-TYPE, enterprises
		FROM SNMPv2-SMI
	MODULE-COMPLIANCE, OBJECT-GROUP, NOTIFICATION-GROUP
		FROM SNMPv2-CONF
	TEXTUAL-CONVENTION, DateAndTime, RowStatus
		FROM SNMPv2-TC
	InterfaceIndex, InterfaceIndexOrZero, ifIndex
		FROM IF-MIB
	zxIma     	  FROM WRS-MASTER-MIB;

atmfImaLinkMib MODULE-IDENTITY
	LAST-UPDATED "9902111830Z"
	ORGANIZATION "The ATM Forum"
	CONTACT-INFO
		"ATM Forum
		World Headquarters
		2570 West El Camino Real
		Suite 304
		Mountain View, CA 94040-1313
		USA
		Phone: +1 415 949 6700
		Fax: +1 415 949 6705
		email: info@atmforum.com"
	DESCRIPTION
		"The MIB module for managing ATM Forum Inverse Multiplexing
		for ATM (IMA) interfaces."
	REVISION "9902111830Z"
	DESCRIPTION
		"Updated and repaired version of the IMA-MIB released with the
		IMA v1.1 specification (af-phy-0086.001)."
	REVISION "9701092245Z"
	DESCRIPTION
		"Initial incomplete version of the IMA-MIB as published in the
		IMA v1.0 specification (af-phy-0086.000)."
	::= { zxIma 3 }

-- The object identifier subtree for the IMA-MIB.


atmfImaLinkMibObjects OBJECT IDENTIFIER ::= { atmfImaLinkMib 1 }
atmfImaMibGroupConformance OBJECT IDENTIFIER ::= { atmfImaLinkMib 2 }
atmfImaLinkGroups          OBJECT IDENTIFIER ::= { atmfImaMibGroupConformance 1}
atmfImaLinkCompliances     OBJECT IDENTIFIER ::= { atmfImaMibGroupConformance 2 }


-- Textual conventions		
ImaLinkState ::= TEXTUAL-CONVENTION
	STATUS current
	DESCRIPTION
		"State of a link belonging to an IMA group."
	REFERENCE
		"ATM Forum IMA v1.1, Section 10.1.2 on page 48"
	SYNTAX INTEGER {
		notInGroup(1),
		unusableNoGivenReason(2),
		unusableFault(3),
		unusableMisconnected(4),
		unusableInhibited(5),
		unusableFailed(6),
		usable(7),
		active(8) }

-- The IMA Link subtree
-- The IMA Link subtree consists of a table of IMA links. Each entry
-- in the table contains status information about a link which is part
-- of an IMA group, and also contains a configuration object to select
-- to which IMA group the link belongs.

imaLinkTable   OBJECT-TYPE
	SYNTAX SEQUENCE OF ImaLinkEntry
	MAX-ACCESS not-accessible
	STATUS current
	DESCRIPTION
	   "The IMA group Link Status and Configuration table."
::= { atmfImaLinkMibObjects 1 }

imaLinkEntry OBJECT-TYPE
	SYNTAX ImaLinkEntry
	MAX-ACCESS not-accessible
	STATUS current
	DESCRIPTION
		"An entry in the IMA Group Link table."
	INDEX { imaLinkIfIndex }
::= { imaLinkTable 1 }

ImaLinkEntry ::= SEQUENCE {
	imaLinkIfIndex    InterfaceIndex,
	imaLinkRowStatus  RowStatus,
	imaLinkGroupIndex INTEGER,
	imaLinkNeTxState  ImaLinkState,
	imaLinkNeRxState  ImaLinkState,
	imaLinkFeTxState  ImaLinkState,
	imaLinkFeRxState  ImaLinkState,
	imaLinkTxLid INTEGER,
	imaLinkRxLid INTEGER,
    	imaLinkIcpOffset       INTEGER,
    	imaLinkPhyLink      INTEGER,
	imaLinkScramble   INTEGER
}
		
imaLinkIfIndex OBJECT-TYPE
	SYNTAX InterfaceIndex
	MAX-ACCESS  read-only
	STATUS current
	DESCRIPTION
		"This corresponds to the 'ifIndex' of the MIB-II interface
	on which this link is established. This object also
	corresponds to the logical number ('ifIndex') assigned to
	this IMA link."
::= { imaLinkEntry 1 }

imaLinkRowStatus OBJECT-TYPE
	SYNTAX RowStatus
	MAX-ACCESS read-only
	STATUS current
	DESCRIPTION
		"The imaLinkRowStatus object allows create, change, and delete
	operations on imaLinkTable entries.
	To create a new conceptual row (or instance) of the imaLinkTable,
	imaLinkRowStatus must be set to 'createAndWait' or 'createAndGo'.
	A successful set of the imaLinkGroupIndex object must be performed
	before the imaLinkRowStatus of a new conceptual row can be set to
	'active'.
		To change (modify) the imaLinkGroupIndex in an imaLinkTable entry,
	the imaLinkRowStatus object must first be set to 'notInService'.
	Only then can this object in the conceptual row be modified.
	This is due to the fact that the imaLinkGroupIndex object provides
	the association between a physical IMA link and the IMA group to
	which it belongs, and setting the imaLinkGroupIndex object to a
	different value has the effect of changing the association between
	a physical IMA link and an IMA group. To place the link 'in group',
	the imaLinkRowStatus object is set to 'active'. While the row is
	not in 'active' state, both the Transmit and Receive IMA link state
	machines are in the 'Not In Group' state.
	To remove (delete) an imaLinkTable entry from this table, set
	this object to 'destroy'."
::= { imaLinkEntry 2 }

imaLinkGroupIndex OBJECT-TYPE
	SYNTAX INTEGER
	MAX-ACCESS read-only
	STATUS current
	DESCRIPTION
		"The value which identifies the IMA group (imaGroupIndex)
	of which this link is a member."
::= { imaLinkEntry 3 }

imaLinkNeTxState OBJECT-TYPE
	SYNTAX ImaLinkState
	MAX-ACCESS read-only
	STATUS current
	DESCRIPTION
		"The current state of the near-end transmit link."
	REFERENCE
		"ATM Forum IMA v1.1, Section 10.1.2 on page 48"
::= { imaLinkEntry 4 }

imaLinkNeRxState OBJECT-TYPE
	SYNTAX ImaLinkState
	MAX-ACCESS read-only
	STATUS current
	DESCRIPTION
		"The current state of the near-end receive link."
	REFERENCE
		"ATM Forum IMA v1.1, Section 10.1.2 on page 48"
::= { imaLinkEntry 5 }

imaLinkFeTxState OBJECT-TYPE
	SYNTAX ImaLinkState
	MAX-ACCESS read-only
	STATUS current
	DESCRIPTION
		"The current state of the far-end transmit link as reported
	via ICP cells."
	REFERENCE
		"ATM Forum IMA v1.1, Section 10.1.2 on page 48"
::= { imaLinkEntry 6 }

imaLinkFeRxState OBJECT-TYPE
	SYNTAX ImaLinkState
	MAX-ACCESS read-only
	STATUS current
	DESCRIPTION
		"The current state of the far-end receive link as reported
	via ICP cells."
	REFERENCE
		"ATM Forum IMA v1.1, Section 10.1.2 on page 48"
::= { imaLinkEntry 7 }

imaLinkTxLid OBJECT-TYPE
	SYNTAX INTEGER
	MAX-ACCESS read-only
	STATUS current
	DESCRIPTION
		"The outgoing LID used currently on the link by the local end.
	This value has meaning only if the link belongs to an IMA group."
	REFERENCE
		"ATM Forum IMA v1.1, Section 5.2.2.1 on page 26"
::= { imaLinkEntry 8 }

imaLinkRxLid OBJECT-TYPE
	SYNTAX        INTEGER
	MAX-ACCESS read-only
	STATUS current
	DESCRIPTION
		"The incoming LID used currently on the link by the remote
	end as reported via ICP cells. This value has meaning only
	if the link belongs to an IMA group."
	REFERENCE
		"ATM Forum IMA v1.1, Section 5.2.2.1 on page 26"
::= { imaLinkEntry 9 }


imaLinkIcpOffset OBJECT-TYPE
	SYNTAX        INTEGER
	MAX-ACCESS read-only
	STATUS current
	DESCRIPTION
		""
	REFERENCE
		"ATM Forum IMA v1.1, Section 5.2.2.1 on page 26"
::= { imaLinkEntry 10 }

imaLinkPhyLink OBJECT-TYPE
	SYNTAX        INTEGER
	MAX-ACCESS read-only
	STATUS current
	DESCRIPTION
		""
	REFERENCE
		"ATM Forum IMA v1.1, Section 5.2.2.1 on page 26"
::= { imaLinkEntry 11 }

imaLinkScramble OBJECT-TYPE
	SYNTAX        INTEGER{
			disable(0),
			 enable(1)
	}
	MAX-ACCESS read-write
	STATUS current
	DESCRIPTION
		"enable/disable the scramble status of the link"
::= { imaLinkEntry 12 }

-- The IMA Link Current Statistics subtree
-- The IMA Link Current Statistics subtree consists of a single table:
-- the IMA Link Current Table. This table contains various statistics
-- collected by each IMA link for the current 15 minute interval.
-- Implementation of IMA Link Current Table is optional.
--
imaLinkCurrentTable OBJECT-TYPE
	SYNTAX SEQUENCE OF ImaLinkCurrentEntry
	MAX-ACCESS not-accessible
	STATUS current
	DESCRIPTION
		"The IMA Link Current table."
::= { atmfImaLinkMibObjects 2 }

imaLinkCurrentEntry OBJECT-TYPE
	SYNTAX ImaLinkCurrentEntry
	MAX-ACCESS not-accessible
	STATUS current
	DESCRIPTION
		"An entry in the IMA Link Current table."
	INDEX { ifIndex }
::= { imaLinkCurrentTable 1 }

ImaLinkCurrentEntry ::= SEQUENCE {
		imaLinkCurrentImaViolations Gauge32,
		imaLinkCurrentOifAnomalies 	Gauge32,
    	imaLinkCurrentTxStuffs		Gauge32,
		imaLinkCurrentRxStuffs 		Gauge32,
		imaLinkCurrentTxUserCells  	Gauge32, 
		imaLinkCurrentRxUserCells  	Gauge32, 
		imaLinkCurrentFilteredCells Gauge32, 
		imaLinkCurrentDroppedCells 	Gauge32, 
		imaLinkCurrentIcpCells  	Gauge32, 
		imaLinkCurrentRxFillerCells Gauge32, 
		imaLinkCurrentHcsErrs 		Gauge32}

imaLinkCurrentImaViolations OBJECT-TYPE
	SYNTAX Gauge32
	MAX-ACCESS read-only
	STATUS current
	DESCRIPTION
		"ICP violations: count of errored, invalid or missing ICP cells,
	except during SES-IMA or UAS-IMA conditions, in the current
	15 minute interval."
	REFERENCE
		"ATM Forum IMA v1.1, (R-125) and (O-26) in Section 12.2.2.2
	on page 77"
::= { imaLinkCurrentEntry 1 }

imaLinkCurrentOifAnomalies OBJECT-TYPE
	SYNTAX Gauge32
	MAX-ACCESS read-only
	STATUS current
	DESCRIPTION
		"The number of OIF anomalies, except during SES-IMA or UAS-IMA
	conditions, at the near-end in the current 15 minute interval.
	This is an optional attribute."
	REFERENCE
		"ATM Forum IMA v1.1, (O-20) and (O-26) in Section 12.2.2.2
	on page 77"
::= { imaLinkCurrentEntry 2 }

imaLinkCurrentTxStuffs OBJECT-TYPE
	SYNTAX Gauge32
	MAX-ACCESS read-only
	STATUS current
	DESCRIPTION
		"Count of stuff events inserted in the transmit direction in
	the current 15 minute interval. This is an optional attribute."
	REFERENCE
		"ATM Forum IMA v1.1, (O-23) and (O-26) in Section 12.2.2.2
	on page 77"
::= { imaLinkCurrentEntry 3 }

imaLinkCurrentRxStuffs OBJECT-TYPE
	SYNTAX Gauge32
	MAX-ACCESS read-only
	STATUS current
	DESCRIPTION
		"Count of stuff events detected in the receive direction in
	the current 15 minute interval. This is an optional attribute."
	REFERENCE
		"ATM Forum IMA v1.1, (O-24) and (O-26) in Section 12.2.2.2
	on page 77"
::= { imaLinkCurrentEntry 4 }

imaLinkCurrentTxUserCells OBJECT-TYPE
	SYNTAX Gauge32
	MAX-ACCESS read-only
	STATUS current
	DESCRIPTION
		"Count of TxUserCells the current 15 minute interval."
	REFERENCE
		"ATM Forum IMA v1.1, (O-24) and (O-26) in Section 12.2.2.2
	on page 77"
::= { imaLinkCurrentEntry 5 }

imaLinkCurrentRxUserCells OBJECT-TYPE
	SYNTAX Gauge32
	MAX-ACCESS read-only
	STATUS current
	DESCRIPTION
		"Count of RxUserCells the current 15 minute interval"
	REFERENCE
		"ATM Forum IMA v1.1, (O-24) and (O-26) in Section 12.2.2.2
	on page 77"
::= { imaLinkCurrentEntry 6 }

imaLinkCurrentFilteredCells OBJECT-TYPE
	SYNTAX Gauge32
	MAX-ACCESS read-only
	STATUS current
	DESCRIPTION
		"Count of FileredCells the current 15 minute interval"
	REFERENCE
		"ATM Forum IMA v1.1, (O-24) and (O-26) in Section 12.2.2.2
	on page 77"
::= { imaLinkCurrentEntry 7 }

imaLinkCurrentDroppedCells OBJECT-TYPE
	SYNTAX Gauge32
	MAX-ACCESS read-only
	STATUS current
	DESCRIPTION
		"Count of DroppedCells the current 15 minute interval"
	REFERENCE
		"ATM Forum IMA v1.1, (O-24) and (O-26) in Section 12.2.2.2
	on page 77"
::= { imaLinkCurrentEntry 8 }

imaLinkCurrentIcpCells OBJECT-TYPE
	SYNTAX Gauge32
	MAX-ACCESS read-only
	STATUS current
	DESCRIPTION
		"Count of IcpCells the current 15 minute interval"
	REFERENCE
		"ATM Forum IMA v1.1, (O-24) and (O-26) in Section 12.2.2.2
	on page 77"
::= { imaLinkCurrentEntry 9 }

imaLinkCurrentRxFillerCells OBJECT-TYPE
	SYNTAX Gauge32
	MAX-ACCESS read-only
	STATUS current
	DESCRIPTION
		"Count of RxFillerCells the current 15 minute interval"
	REFERENCE
		"ATM Forum IMA v1.1, (O-24) and (O-26) in Section 12.2.2.2
	on page 77"
::= { imaLinkCurrentEntry 10 }


imaLinkCurrentHcsErrs OBJECT-TYPE
	SYNTAX Gauge32
	MAX-ACCESS read-only
	STATUS current
	DESCRIPTION
		"Count of HcsErrs the current 15 minute interval"
	REFERENCE
		"ATM Forum IMA v1.1, (O-24) and (O-26) in Section 12.2.2.2
	on page 77"
::= { imaLinkCurrentEntry 11 }

-- The IMA Link Interval Statistics subtree
-- The IMA Link Interval Statistics subtree consists of a single table:
-- the IMA Link Interval Table. This table contains various statistics
-- collected by each IMA link over the previous 24 hours of operation.
-- The past 24 hours are broken into 96 completed 15 minute intervals.
-- Implementation of IMA Link Interval Table is optional.

imaLinkIntervalTable OBJECT-TYPE
	SYNTAX SEQUENCE OF ImaLinkIntervalEntry
	MAX-ACCESS not-accessible
	STATUS current
	DESCRIPTION
		"The IMA Link Interval table."
::= { atmfImaLinkMibObjects 3 }

imaLinkIntervalEntry OBJECT-TYPE
	SYNTAX ImaLinkIntervalEntry
	MAX-ACCESS not-accessible
	STATUS current
	DESCRIPTION
		"An entry in the IMA Link Interval table."
	INDEX { ifIndex, imaLinkIntervalNumber }
::= { imaLinkIntervalTable 1 }

ImaLinkIntervalEntry ::= SEQUENCE {
		imaLinkIntervalNumber 		 	INTEGER,
	   	imaLinkIntervalImaViolations 	Gauge32,
   		imaLinkIntervalOifAnomalies 	Gauge32,
    	imaLinkIntervalTxStuffs 		Gauge32,
		imaLinkIntervalRxStuffs 		Gauge32,
   		imaLinkIntervalTxUserCells  	Gauge32, 
		imaLinkIntervalRxUserCells  	Gauge32, 
		imaLinkIntervalFilteredCells 	Gauge32, 
		imaLinkIntervalDroppedCells 	Gauge32, 
		imaLinkIntervalIcpCells  		Gauge32, 
		imaLinkIntervalRxFillerCells 	Gauge32, 
		imaLinkIntervalHcsErrs 			Gauge32}

imaLinkIntervalNumber OBJECT-TYPE
	SYNTAX INTEGER
	MAX-ACCESS not-accessible
	STATUS current
	DESCRIPTION
		"A number between 1 and 96, where 1 is the most
	recently completed 15 minute interval and 96 is the least
	recently completed 15 minutes interval (assuming that all
	96 intervals are valid)."
::= { imaLinkIntervalEntry 1 }

imaLinkIntervalImaViolations OBJECT-TYPE
	SYNTAX Gauge32
	MAX-ACCESS read-only
	STATUS current
	DESCRIPTION
		"ICP violations: count of errored, invalid or missing ICP cells,
	except during SES-IMA or UAS-IMA conditions, in one of the
	previous 96, individual 15 minute, intervals."
	REFERENCE
		"ATM Forum IMA v1.1, (R-125) and (O-26) in Section 12.2.2.2
	on page 77"
::= { imaLinkIntervalEntry 2 }

imaLinkIntervalOifAnomalies  OBJECT-TYPE
	SYNTAX Gauge32
	MAX-ACCESS read-only
	STATUS current
	DESCRIPTION
		"The number of times a far-end receive failure alarm condition
	has been entered on this link (i.e., Rx-Unusable-FE) in one of
	the previous 96, individual 15 minute, intervals. This is an
	optional attribute."
	REFERENCE
		"ATM Forum IMA v1.1, (O-22) and (O-26) in Section 12.2.2.2
	on page 77"
::= { imaLinkIntervalEntry 3 }

imaLinkIntervalTxStuffs OBJECT-TYPE
	SYNTAX Gauge32
	MAX-ACCESS read-only
	STATUS current
	DESCRIPTION
		"Count of stuff events inserted in the transmit direction in
	one of the previous 96, individual 15 minute, intervals. This
	is an optional attribute."
	REFERENCE
		"ATM Forum IMA v1.1, (O-23) and (O-26) in Section 12.2.2.2
	on page 77"
::= { imaLinkIntervalEntry 4 }

imaLinkIntervalRxStuffs OBJECT-TYPE
	SYNTAX Gauge32
	MAX-ACCESS read-only
	STATUS current
	DESCRIPTION
		"Count of stuff events detected in the receive direction in
	one of the previous 96, individual 15 minute, intervals. This
	is an optional attribute."
	REFERENCE
		"ATM Forum IMA v1.1, (O-24) and (O-26) in Section 12.2.2.2
	on page 77"
::= { imaLinkIntervalEntry 5}

imaLinkIntervalTxUserCells OBJECT-TYPE
	SYNTAX Gauge32
	MAX-ACCESS read-only
	STATUS current
	DESCRIPTION
		"Count of TxUserCells detected in the receive direction in
	one of the previous 96, individual 15 minute, intervals. This
	is an optional attribute."
	REFERENCE
		"ATM Forum IMA v1.1, (O-24) and (O-26) in Section 12.2.2.2
	on page 77"
::= { imaLinkIntervalEntry 6}

imaLinkIntervalRxUserCells OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 7}

imaLinkIntervalFilteredCells OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 8}

imaLinkIntervalDroppedCells OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 9}

imaLinkIntervalIcpCells OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 10}

imaLinkIntervalRxFillerCells OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 11}

imaLinkIntervalHcsErrs OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 12}

-- The IMA Link Total Statistics subtree
-- The IMA Link Total Statistics subtree consists of a single table:
-- the IMA Link Total Table. This table contains the cumulative sum
-- of the various statistics collected by each IMA link for the 24 hour
-- period preceding the current interval.
-- Implementation of IMA Link Total Table is optional.

imaLinkTotalTable OBJECT-TYPE
	SYNTAX SEQUENCE OF ImaLinkTotalEntry
	MAX-ACCESS not-accessible
	STATUS current
	DESCRIPTION
		"The IMA Link Total table."
::= { atmfImaLinkMibObjects 4 }

imaLinkTotalEntry OBJECT-TYPE
	SYNTAX ImaLinkTotalEntry
	MAX-ACCESS not-accessible
	STATUS current
	DESCRIPTION
		"An entry in the IMA Link Total table."
	INDEX { ifIndex }
::= { imaLinkTotalTable 1 }

ImaLinkTotalEntry ::= SEQUENCE {
		imaLinkTotalImaViolations Gauge32,
   		imaLinkTotalOifAnomalies Gauge32,
    	imaLinkTotalTxStuffs Gauge32,
		imaLinkTotalRxStuffs Gauge32,
   		imaLinkTotalTxUserCells  Gauge32, 
		imaLinkTotalRxUserCells  Gauge32, 
		imaLinkTotalFilteredCells Gauge32, 
		imaLinkTotalDroppedCells Gauge32, 
		imaLinkTotalIcpCells  Gauge32, 
		imaLinkTotalRxFillerCells Gauge32, 
		imaLinkTotalHcsErrs    Gauge32}
		
imaLinkTotalImaViolations OBJECT-TYPE
	SYNTAX Gauge32
	MAX-ACCESS read-only
	STATUS current
	DESCRIPTION
		"ICP violations: count of errored, invalid or missing ICP cells,
	except during SES-IMA or UAS-IMA conditions, in the previous 24
	hour interval. Invalid 15 minute intervals count as 0."
	REFERENCE
		"ATM Forum IMA v1.1, (R-125) and (O-27) in Section 12.2.2.2
	on page 77"
::= { imaLinkTotalEntry 1 }

imaLinkTotalOifAnomalies OBJECT-TYPE
	SYNTAX Gauge32
	MAX-ACCESS read-only
	STATUS current
	DESCRIPTION
		"The number of OIF anomalies, except during SES-IMA or UAS-IMA
	conditions, at the near-end in the previous 24 hour interval.
	Invalid 15 minute intervals count as 0. This is an optional
	attribute."
	REFERENCE
		"ATM Forum IMA v1.1, (O-20) and (O-27) in Section 12.2.2.2
	on page 77"
::= { imaLinkTotalEntry 2 }

imaLinkTotalTxStuffs OBJECT-TYPE
	SYNTAX Gauge32
	MAX-ACCESS read-only
	STATUS current
	DESCRIPTION
		"Count of stuff events inserted in the transmit direction in
	the previous 24 hour interval. Invalid 15 minute intervals
	count as 0. This is an optional attribute."
	REFERENCE
		"ATM Forum IMA v1.1, (O-23) and (O-27) in Section 12.2.2.2
	on page 77"
::= { imaLinkTotalEntry 3 }

imaLinkTotalRxStuffs OBJECT-TYPE
	SYNTAX Gauge32
	MAX-ACCESS read-only
	STATUS current
	DESCRIPTION
		"Count of stuff events detected in the receive direction in
	the previous 24 hour interval. Invalid 15 minute intervals
	count as 0. This is an optional attribute."
	REFERENCE
		"ATM Forum IMA v1.1, (O-24) and (O-27) in Section 12.2.2.2
	on page 77"
::= { imaLinkTotalEntry 4 }


imaLinkTotalTxUserCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 5 }

imaLinkTotalRxUserCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 6 }

imaLinkTotalFilteredCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 7}

imaLinkTotalDroppedCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 8}

imaLinkTotalIcpCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 9}

imaLinkTotalRxFillerCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 10}

imaLinkTotalHcsErrs OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 11}


-- Conformance Information
 imaLinkGroup OBJECT-GROUP
       OBJECTS{ 
       	imaLinkIfIndex   ,
	imaLinkRowStatus  ,
	imaLinkGroupIndex ,
	imaLinkNeTxState  ,
	imaLinkNeRxState  ,
	imaLinkFeTxState  ,
	imaLinkFeRxState  ,
	imaLinkTxLid ,
	imaLinkRxLid,
	imaLinkIcpOffset  ,
    imaLinkPhyLink  ,
	imaLinkScramble   }    
       STATUS          current
       DESCRIPTION
              " A set of objects providing configuration and status information for
              an IMA Link definition."
       ::=  {atmfImaLinkGroups 1 }


imaLinkCurrentGroup OBJECT-GROUP
   OBJECTS{	
   		imaLinkCurrentImaViolations ,
		imaLinkCurrentOifAnomalies 	,
    	imaLinkCurrentTxStuffs		,
		imaLinkCurrentRxStuffs 		,
		imaLinkCurrentTxUserCells  	, 
		imaLinkCurrentRxUserCells  	, 
		imaLinkCurrentFilteredCells , 
		imaLinkCurrentDroppedCells 	, 
		imaLinkCurrentIcpCells  	, 
		imaLinkCurrentRxFillerCells , 
		imaLinkCurrentHcsErrs }
		
        STATUS          current
        DESCRIPTION
              " Objects containing current statistics for an IMA Link."
           ::=  {atmfImaLinkGroups 2} 


   imaLinkIntervalGroup OBJECT-GROUP
      OBJECTS{
	   	imaLinkIntervalImaViolations 	,
   		imaLinkIntervalOifAnomalies 	,
    	imaLinkIntervalTxStuffs 		,
		imaLinkIntervalRxStuffs 	,
   		imaLinkIntervalTxUserCells  	, 
		imaLinkIntervalRxUserCells  	, 
		imaLinkIntervalFilteredCells 	, 
		imaLinkIntervalDroppedCells 	, 
		imaLinkIntervalIcpCells  		, 
		imaLinkIntervalRxFillerCells 	, 
		imaLinkIntervalHcsErrs 			 }       
        STATUS          current
        DESCRIPTION
              " Objects containing interval statistics for an IMA Link."
           ::=  {atmfImaLinkGroups 3}         
    
    imaLinkTotalGroup OBJECT-GROUP
          OBJECTS{
		imaLinkTotalImaViolations ,
   		imaLinkTotalOifAnomalies ,
    	imaLinkTotalTxStuffs ,
		imaLinkTotalRxStuffs ,
   		imaLinkTotalTxUserCells  , 
		imaLinkTotalRxUserCells  , 
		imaLinkTotalFilteredCells , 
		imaLinkTotalDroppedCells , 
		imaLinkTotalIcpCells  , 
		imaLinkTotalRxFillerCells , 
		imaLinkTotalHcsErrs}    
		   
        STATUS          current
        DESCRIPTION
              " Objects containing total statistics for an IMA Link."
           
           ::=  {atmfImaLinkGroups 4} 
           
--  compliance statements
    atmfImaMibCompliance MODULE-COMPLIANCE
    STATUS  current
    DESCRIPTION
           "The compliance statement."
    MODULE  -- this module
    MANDATORY-GROUPS{
            imaLinkGroup,
            imaLinkCurrentGroup,
            imaLinkIntervalGroup,
            imaLinkTotalGroup
            }
        ::= { atmfImaLinkCompliances 1 }
END


------------------------------------------------------------------------------
------------------------------------------------------------------------------
--
--  File         : lanMib.mib
--  Description  : ZTE lan MIB  
--
------------------------------------------------------------------------------
------------------------------------------------------------------------------

LAN-MIB DEFINITIONS ::= BEGIN

	IMPORTS
			MODULE-IDENTITY, OBJECT-TYPE,
			Integer32, enterprises					FROM SNMPv2-SMI

			MODULE-COMPLIANCE, OBJECT-GROUP			FROM SNMPv2-CONF

--			zxLan									FROM WRS-MASTER-MIB

			PortList, dot1qStaticMulticastEntry		FROM Q-BRIDGE-MIB;       

------------------------------------------------------------------------------
------------------------------------------------------------------------------

    zte MODULE-IDENTITY
        LAST-UPDATED    "0008290000Z"  -- August 29, 2000
        ORGANIZATION    "Wind River Systems, Inc."
        CONTACT-INFO    "Wind River Systems, Inc.
                         E-mail: support@windriver.com"

        DESCRIPTION     "WRS Master MIB OID defines and documentation."

        REVISION        "0008290000Z"  -- August 29, 2000
        DESCRIPTION     "Initial MIB creation."

        ::= { enterprises 3902 }
    
-- DSL Products
	zxDsl	OBJECT IDENTIFIER ::= { zte 1004 }
	zxDslam OBJECT IDENTIFIER ::= { zxDsl 1 }
	zxLan	OBJECT IDENTIFIER ::= { zxDslam 10 }
------------------------------------------------------------------------------
------------------------------------------------------------------------------

	lanCommon	OBJECT IDENTIFIER ::= { zxLan 2 }
--	lanBridge	OJBECT IDENTIFIER ::= { zxLan 5 }
------------------------------------------------------------------------------
------------------------------------------------------------------------------

    lanCleanFlash OBJECT-TYPE
        SYNTAX INTEGER {
               noop(1),            -- no operation
               clean(2),           -- clean the data in flash
               cleanInProgress(3)  -- read-only: flash clean in progress
        }
        MAX-ACCESS read-write
        STATUS current
        DESCRIPTION
            "When set to 'clean(2)', the data in flash are cleaned . This
             operations may be slow . Consequently, all or many updates 
             should be made before cleaning the flash.  Note that the SNMP
             set to 'clean(2)' returns immediately to the caller.  Gets on
             this object then return  'cleanInProgress(3)' until the clean
             operation completes, at which time 'noop(1)' is returned.  
             Consequently, a get operation always returns 'noop(1)' or 
             'cleanInProgress(3)' depending on the current state.
             
             The agent returns 'badValue' for SNMPv1 or 'inconsistentValue'
             for SNMPv2c/v3 for a set to 'clean(2)' while the current get
             state is 'cleanInProgress(3)'.
             
             Attempts to set this object to 'cleanInProgress(3)' returns
             'badValue' for SNMPv1 or 'wrongValue' for SNMPv2c/v3."
        ::= { lanCommon 1 }


    lanReset OBJECT-TYPE
        SYNTAX INTEGER {
               noop(1),           -- no operation
               reset(2),          -- reset unit
               resetToDefaults(3) -- reset to factory defaults/reset unit
        }
        MAX-ACCESS read-write
        STATUS current
        DESCRIPTION
            "Physically performs a hardware reset of the unit. 
             Use with care.  A 'reset(2)' resets the unit, a
             'resetToDefaults(3)' resets the NVM configuration
             to factory defaults and then resets the unit, and 'noop(1)'
             does nothing.  A value of 'noop(1)' is always returned for a
             GET operation."
        ::= { lanCommon 2 }

    lanVersionNumber OBJECT-TYPE
        SYNTAX OCTET STRING (SIZE (0..4))
        MAX-ACCESS read-only
        STATUS current
        DESCRIPTION
            "Get this MIB Major version number.  This number should 
             match the Major version given in the documentation header
             at the beginning text of this MIB.  Note that the '.c' file
             corresponding to this MIB has to be manually edited to
             change the version number if this file is modified and
             the version number is therefore changed."
        ::= { lanCommon 3 }


    lanSaveFlash OBJECT-TYPE
        SYNTAX INTEGER {
               noop(1),           -- no operation
               save(2),           -- save all configuration parameters to NVM
               saveInProgress(3)  -- read-only: NVM save in progress
        }
        MAX-ACCESS read-write
        STATUS current
        DESCRIPTION
            "When set to 'save(2)', all nonvolatile configuration
             parameters are saved to NVM (Nonvolatile Memory).  NVM save
             operations may be slow (e.g., erasing/writing Flash device).
             Consequently, all or many updates should be made before
             saving to NVM.  Note that the SNMP set to 'save(2)' returns
             immediately to the caller.  Gets on this object then return
             'saveInProgress(3)' until the save operation completes, at
             which time 'noop(1)' is returned.  Consequently, a get
             operation always returns 'noop(1)' or 'saveInProgress(3)'
             depending on the current state.
             
             The agent returns 'badValue' for SNMPv1 or 'inconsistentValue'
             for SNMPv2c/v3 for a set to 'Save(2)' while the current get
             state is 'saveInProgress(3)'.
             
             Attempts to set this object to 'saveInProgress(3)' returns
             'badValue' for SNMPv1 or 'wrongValue' for SNMPv2c/v3."
        ::= { lanCommon 4 }

END

------------------------------------------------------------------------------
------------------------------------------------------------------------------
--
--  File         : IMAB.mib
--  Description  : ZTE IMAB MIB  
--
------------------------------------------------------------------------------
------------------------------------------------------------------------------
IMAB-GROUP-MIB DEFINITIONS ::= BEGIN

IMPORTS
           MODULE-IDENTITY, OBJECT-TYPE, Integer32, Counter32, Gauge32,
           NOTIFICATION-TYPE, enterprises
              FROM SNMPv2-SMI
           MODULE-COMPLIANCE, OBJECT-GROUP, NOTIFICATION-GROUP
              FROM SNMPv2-CONF
           TEXTUAL-CONVENTION, DateAndTime, RowStatus
              FROM SNMPv2-TC
           InterfaceIndex, InterfaceIndexOrZero, ifIndex
              FROM IF-MIB;
              
zxImabGroupMib MODULE-IDENTITY
           LAST-UPDATED "9902111830Z"
           ORGANIZATION "The ATM Forum"
           CONTACT-INFO
              "ATM Forum
              World Headquarters
              2570 West El Camino Real
              Suite 304
              Mountain View, CA 94040-1313
              USA
              Phone: +1 415 949 6700
              Fax: +1 415 949 6705
              email: info@ atmforum. com"
           DESCRIPTION
              "The MIB module for managing ATM Forum Inverse Multiplexing
              for ATM (IMA) interfaces."
           REVISION          "9902111830Z"
           DESCRIPTION
              "Updated and repaired version of the IMA-MIB released with the
              IMA v1.1 specification (af-phy-0086.001)."
           REVISION          "9701092245Z"
           DESCRIPTION
              "Initial incomplete version of the IMA-MIB as published in the
              IMA v1.0 specification (af-phy-0086.000)."
           ::= { zxIma 5 }

zte OBJECT IDENTIFIER ::= { enterprises 3902 }
zxDsl OBJECT IDENTIFIER ::= { zte 1004 }
zxDslam OBJECT IDENTIFIER ::= { zxDsl 1 }
zxIma	OBJECT IDENTIFIER ::= { zxDslam 11 }

zxImabGroupMibObjects OBJECT IDENTIFIER ::= { zxImabGroupMib 1 }

zxImabGroupMibConformance OBJECT IDENTIFIER ::= { zxImabGroupMib 2 }
zxImabGroupMibGroups OBJECT IDENTIFIER ::= { zxImabGroupMibConformance 1 }
zxImabGroupMibCompliances OBJECT IDENTIFIER ::= { zxImabGroupMibConformance 2 }


--Textual conventions

MilliSeconds ::= TEXTUAL-CONVENTION
           STATUS           current
           DESCRIPTION
              "Time in milliseconds"
           SYNTAX           Integer32

ImaGroupState ::= TEXTUAL-CONVENTION
           STATUS           current
           DESCRIPTION
              "State of the IMA group."
           REFERENCE
              "ATM Forum IMA v1.1, Section 10.2.1 on page 55"
           SYNTAX            INTEGER {
              notConfigured(1),
              startUp(2),
              startUpAck(3),
              configAbortUnsupportedM(4),
              configAbortIncompatibleSymmetry(5),
              configAbortOther(6),
              insufficientLinks(7),
              blocked(8),
              operational(9),
              configAbortUnsupportedImaVersion(10) }

ImaGroupFailureStatus ::= TEXTUAL-CONVENTION
           STATUS           current
           DESCRIPTION
              "Failure reason of an IMA group."
           REFERENCE
              "ATM Forum IMA v1.1, Section 10.2.1, page 55"
           SYNTAX            INTEGER {
              noFailure( 1), --unit is up
              startUpNe( 2),
              startUpFe( 3),
              invalidMValueNe( 4),
              invalidMValueFe( 5),
              failedAssymetricNe( 6),
              failedAssymetricFe( 7),
              insufficientLinksNe( 8),
              insufficientLinksFe( 9),
              blockedNe( 10),
              blockedFe( 11),
              otherFailure( 12),
              invalidImaVersionNe( 13),
              invalidImaVersionFe( 14) }

ImaGroupTxClkMode ::= TEXTUAL-CONVENTION
           STATUS           current
           DESCRIPTION
              "Indicate the transmit clock mode of the IMA group.
              There are two possible modes: the Common Transmit
              Clock (CTC) and the Independent Transmit Clock (ITC).
              The CTC mode corresponds to the case when the transmit clock
              of all IMA links are derived from the same source.    The ITC
              configuration corresponds to the case where there is at least
              one IMA link whose transmit clock is derived from a source
              different than at least another link transmit clock."
           REFERENCE
              "ATM Forum IMA v1.1, Section 7 on page 38"
           SYNTAX            INTEGER {
              ctc( 1),
              itc( 2) }

ImaGroupSymmetry ::= TEXTUAL-CONVENTION
           STATUS           current
           DESCRIPTION
              "The group symmetry mode adjusted during the group start-up."
           REFERENCE
              "ATM Forum IMA v1.1, Section 5.2.2.7 on page 35"
           SYNTAX            INTEGER {
              symmetricOperation( 1),
              asymmetricOperation( 2),
              asymmetricConfiguration( 3) }

ImaFrameLength ::= TEXTUAL-CONVENTION
           STATUS           current
           DESCRIPTION
              "Length of the IMA frames."
           REFERENCE
              "ATM Forum IMA v1.1, Section 5.2.2.4.2 on page 34"
           SYNTAX            INTEGER {
              m32( 32),
              m64( 64),
              m128( 128),
              m256( 256) }

ImaTestProcStatus ::= TEXTUAL-CONVENTION
           STATUS           current
           DESCRIPTION
              "States of the Test Pattern Procedure."
           REFERENCE
              "ATM Forum IMA v1.1, Section 13 on page 81"
           SYNTAX            INTEGER {
              disabled( 1),
              operating( 2),
              linkFail( 3) }

--
--The IMA Group subtree
--
--The IMA Group subtree consists of the number of IMA groups and a
--table of IMA groups.    Each entry in the table of IMA groups contains
--information (configuration and status) specific to each group.
--

imabGroupNumber OBJECT-TYPE
           SYNTAX            INTEGER (0.. 2147483647)
           MAX-ACCESS    read-only
           STATUS           current
           DESCRIPTION
              "The number of active IMA groups configured on this system."
           ::= { zxImabGroupMibObjects 1 }

imabGroupTable OBJECT-TYPE
           SYNTAX           SEQUENCE OF ImabGroupEntry
           MAX-ACCESS    not-accessible
           STATUS           current
           DESCRIPTION
              "The IMA Group Configuration table."
           ::= { zxImabGroupMibObjects 2 }

imabGroupEntry OBJECT-TYPE
           SYNTAX           ImabGroupEntry
           MAX-ACCESS    not-accessible
           STATUS           current
           DESCRIPTION
              "An entry in the IMA Group table."
           INDEX             { imabGroupIndex }
           ::= { imabGroupTable 1 }

ImabGroupEntry ::= SEQUENCE {
           imabGroupIndex                            INTEGER (1..2147483647),
           imabGroupRowStatus                     RowStatus,
--           imabGroupIfIndex                        InterfaceIndex,
--           imabGroupNeState                        ImaGroupState,
--           imabGroupFeState                        ImaGroupState,
--           imabGroupFailureStatus             ImaGroupFailureStatus,
           imabGroupSymmetry                      ImaGroupSymmetry,
           imabGroupMinNumTxLinks             INTEGER (1.. 32),
           imabGroupMinNumRxLinks             INTEGER (1.. 32),
           imabGroupNeTxClkMode                 ImaGroupTxClkMode,
--           imabGroupFeTxClkMode                 ImaGroupTxClkMode,
--           imabGroupTxTimingRefLink          InterfaceIndexOrZero,
--           imabGroupRxTimingRefLink          InterfaceIndexOrZero,
--           imabGroupLastChange                   DateAndTime,
--           imabGroupTxImaId                        INTEGER (0.. 255),
--           imabGroupRxImaId                        INTEGER (0.. 255),
           imabGroupTxFrameLength             ImaFrameLength,
--           imabGroupRxFrameLength             ImaFrameLength,
           imabGroupDiffDelayMax               MilliSeconds,
--           imabGroupLeastDelayLink            InterfaceIndexOrZero,
--           imabGroupDiffDelayMaxObs          MilliSeconds,
           imabGroupAlphaValue                   INTEGER (1.. 2),
           imabGroupBetaValue                     INTEGER (1.. 5),
           imabGroupGammaValue                   INTEGER (1.. 5),
--           imabGroupRunningSecs                 Gauge32,
--           imabGroupUnavailSecs                 Counter32,
--           imabGroupNeNumFailures             Counter32,
--           imabGroupFeNumFailures             Counter32,
--           imabGroupTxAvailCellRate          Gauge32,
--           imabGroupRxAvailCellRate          Gauge32,
--           imabGroupNumTxCfgLinks             Gauge32,
--           imabGroupNumRxCfgLinks             Gauge32,
--           imabGroupNumTxActLinks             Gauge32,
--           imabGroupNumRxActLinks             Gauge32,
--           imabGroupTestLinkIfIndex          InterfaceIndexOrZero,
           imabGroupTestPattern                 INTEGER (-1.. 255),
           imabGroupTestProcStatus            ImaTestProcStatus,
--           imabGroupValidIntervals            INTEGER (0.. 96),
--           imabGroupInvalidIntervals        INTEGER (0.. 96),
--           imabGroupTimeElapsed                 INTEGER (0.. 899),
           imabGroupTxOamLabelValue          INTEGER (1.. 255),
--           imabGroupRxOamLabelValue          INTEGER (0.. 255),
	   imabGroupCLKMode		    INTEGER }

imabGroupIndex OBJECT-TYPE
           SYNTAX            INTEGER (1.. 2147483647)
           MAX-ACCESS    not-accessible
           STATUS           current
           DESCRIPTION
              "A unique value for the IMA Group."
           ::= { imabGroupEntry 1 }

imabGroupRowStatus OBJECT-TYPE
           SYNTAX           RowStatus
           MAX-ACCESS    read-create
           STATUS           current
           DESCRIPTION
              "The imaGroupRowStatus object allows create, change, and delete
              operations on imaGroupTable entries.

              To create a new conceptual row (or instance) of the imaGroupTable,
              imaGroupRowStatus must be set to 'createAndWait' or 'createAndGo'.
              If settable, a successful set of the following objects must be
              performed before the imaGroupRowStatus of a new conceptual row can
              be set to 'active':

                  imaGroupMinNumTxLinks
                  imaGroupMinNumRxLinks
                  imaGroupTxImaId

              Some objects in the imaGroupTable control settings which can only
              be established or changed at group start-up time.    These objects
              include:

                  imaGroupTxImaId
                  imaGroupSymmetry
                  imaGroupTxFrameLength

              To change (modify) the imaGroupTxImaId object, the manager must
              first set imaGroupRowStatus to 'notInService'.    However, changes
              to the following two objects can be optionally allowed while the
              imaGroupRowStatus is 'active':

                  imaGroupSymmetry
                  imaGroupTxFrameLength

              These two objects can be changed when the imaGroupRowStatus is
              'active' in order to allow the far-end to recover from its
              Config-Aborted state without having to force the near-end Group
              State machine to go to the 'Not Configured' state.    Changing
              these object values after group start-up has completed causes a
              restart of the IMA group.

              Alternatively, as noted above, the agent implementation may
              simply require the imaGroupRowStatus object to first be set to
              'notInService' before allowing changes to either of these two
              objects.

              To remove (delete) an imaGroupTable entry from this table, set
              imaGroupRowStatus to 'destroy'.

              Setting the imaGroupRowStatus to 'active' has the effect of
              activating the Group Startup Procedure.    The Group Startup
              Procedure uses provisioned links that have imaLinkRowStatus set
              to 'active' and imaLinkGroupIndex set to the imaGroupIndex in
              this conceptual row.

              When the imaGroupRowStatus is not in 'active' state, the Group
              State machine is in its 'Not Configured' state."
           ::= { imabGroupEntry 2 }

--imabGroupIfIndex OBJECT-TYPE
--           SYNTAX           InterfaceIndex
--           MAX-ACCESS    read-only
--           STATUS           current
--           DESCRIPTION
--              "This object identifies the logical interface number ('ifIndex')
--              assigned to this IMA group, and is used to identify corresponding
--              rows in the Interfaces MIB.
--
--              Note that re-initialization of the management agent may cause
--              a client's 'imaGroupIfIndex' to change."
--           ::= { imabGroupEntry 3 }

--imabGroupNeState OBJECT-TYPE
--           SYNTAX           ImaGroupState
--           MAX-ACCESS    read-only
--           STATUS           current
--           DESCRIPTION
--              "The current operational state of the near-end IMA Group State
--              Machine."
--           REFERENCE
--              "ATM Forum IMA v1.1, Section 10.2.1 on page 55"
--           ::= { imabGroupEntry 4 }

--imabGroupFeState OBJECT-TYPE
--           SYNTAX           ImaGroupState
--           MAX-ACCESS    read-only
--           STATUS           current
--           DESCRIPTION
--              "The current operational state of the far-end IMA Group State
--              Machine."
--           REFERENCE
--              "ATM Forum IMA v1.1, Section 10.2.1 on page 55"
--           ::= { imabGroupEntry 5 }

--imabGroupFailureStatus OBJECT-TYPE
--           SYNTAX           ImaGroupFailureStatus
--           MAX-ACCESS    read-only
--           STATUS           current
--           DESCRIPTION
--              "The current failure status of the IMA group (the reason why
--              the GTSM is in the down state)."
--           REFERENCE
--              "ATM Forum IMA v1.1, Section 10.2.1 on page 55"
--           ::= { imabGroupEntry 6 }

imabGroupSymmetry OBJECT-TYPE
           SYNTAX           ImaGroupSymmetry
           MAX-ACCESS    read-create
           STATUS           current
           DESCRIPTION
              "Symmetry of the IMA group."
           REFERENCE
              "ATM Forum IMA v1.1, Section 5.2.2.7 on page 35"
           DEFVAL { symmetricOperation }
           ::= { imabGroupEntry 7 }

imabGroupMinNumTxLinks OBJECT-TYPE
           SYNTAX            INTEGER (1.. 32)
           MAX-ACCESS    read-create
           STATUS           current
           DESCRIPTION
              "Minimum number of transmit links required to be Active for
              the IMA group to be in the Operational state."
           REFERENCE
              "ATM Forum IMA v1.1, Section 10.2.1.1 on page 55"
           ::= { imabGroupEntry 8 }

imabGroupMinNumRxLinks OBJECT-TYPE
           SYNTAX            INTEGER (1.. 32)
           MAX-ACCESS    read-create
           STATUS           current
           DESCRIPTION
              "Minimum number of receive links required to be Active for
              the IMA group to be in the Operational state."
           REFERENCE
              "ATM Forum IMA v1.1, Section 10.2.1.1 on page 55"
           ::= { imabGroupEntry 9 }

imabGroupNeTxClkMode OBJECT-TYPE
           SYNTAX           ImaGroupTxClkMode
           MAX-ACCESS    read-create
           STATUS           current
           DESCRIPTION
              "Transmit clocking mode used by the near-end IMA group."
           REFERENCE
              "ATM Forum IMA v1.1, Section 7 on page 38"
           DEFVAL { ctc }
           ::= { imabGroupEntry 10 }

--imabGroupFeTxClkMode OBJECT-TYPE
--           SYNTAX           ImaGroupTxClkMode
--           MAX-ACCESS    read-only
--           STATUS           current
--           DESCRIPTION
--              "Transmit clocking mode used by the far-end IMA group."
--           REFERENCE
--              "ATM Forum IMA v1.1, Section 7 on page 38"
--           ::= { imabGroupEntry 11 }

--imabGroupTxTimingRefLink OBJECT-TYPE
--           SYNTAX           InterfaceIndexOrZero
--           MAX-ACCESS    read-only
--           STATUS           current
--           DESCRIPTION
--              "The ifIndex of the transmit timing reference link to be
--              used by the near-end for IMA data cell clock recovery from
--              the ATM layer.    The distinguished value of zero may be used
--              if no link has been configured in the IMA group, or if the
--              transmit timing reference link has not yet been selected."
--           REFERENCE
--              "ATM Forum IMA v1.1, Section 8.1.1 on page 41"
--           ::= { imabGroupEntry 12 }

--imabGroupRxTimingRefLink OBJECT-TYPE
--           SYNTAX           InterfaceIndexOrZero
--           MAX-ACCESS    read-only
--           STATUS           current
--           DESCRIPTION
--              "The ifIndex of the receive timing reference link to be
--              used by near-end for IMA data cell clock recovery toward
--              the ATM layer.    The distinguished value of zero may be used
--              if no link has been configured in the IMA group, or if the
--              receive timing reference link has not yet been detected."
--           REFERENCE
--              "ATM Forum IMA v1.1, Section 8.1.1 on page 41"
--           ::= { imabGroupEntry 13 }

--imabGroupLastChange OBJECT-TYPE
--           SYNTAX           DateAndTime
--           MAX-ACCESS    read-only
--           STATUS           current
--           DESCRIPTION
--              "The time-of-day the IMA group last changed operational
--              state (i. e., value of imaGroupNeState changed)."
--           ::= { imabGroupEntry 14 }

--imabGroupTxImaId OBJECT-TYPE
--           SYNTAX           INTEGER (0.. 255)
--           MAX-ACCESS    read-only
--           STATUS           current
--           DESCRIPTION
--              "The IMA ID currently in use by the near-end IMA function."
--           REFERENCE
--              "ATM Forum IMA v1.1, Section 5.2.2.6 on page 35"
--           ::= { imabGroupEntry 15 }

--imabGroupRxImaId OBJECT-TYPE
--           SYNTAX           INTEGER (0.. 255)
--           MAX-ACCESS    read-only
--           STATUS           current
--           DESCRIPTION
--              "The IMA ID currently in use by the far-end IMA function."
--           REFERENCE
--              "ATM Forum IMA v1.1, Section 5.2.2.6 on page 35"
--           ::= { imabGroupEntry 16 }

imabGroupTxFrameLength OBJECT-TYPE
           SYNTAX           ImaFrameLength
           MAX-ACCESS    read-create
           STATUS           current
           DESCRIPTION
              "The frame length to be used by the IMA group in the transmit
              direction.    Can only be set when the IMA group is startup."
           REFERENCE
              "ATM Forum IMA v1.1, Section 5.2.2.4.2 on page 34"
           DEFVAL { m128 }
           ::= { imabGroupEntry 17 }

--imabGroupRxFrameLength OBJECT-TYPE
--           SYNTAX           ImaFrameLength
--           MAX-ACCESS    read-only
--           STATUS           current
--           DESCRIPTION
--              "Value of IMA frame length as received from remote IMA function."
--           REFERENCE
--              "ATM Forum IMA v1.1, Section 5.2.2.4.2 on page 34"
--           ::= { imabGroupEntry 18 }

imabGroupDiffDelayMax OBJECT-TYPE
           SYNTAX           MilliSeconds
           MAX-ACCESS    read-create
           STATUS           current
           DESCRIPTION
              "The maximum number of milliseconds of differential delay among
              the links that will be tolerated on this interface."
           REFERENCE
              "ATM Forum IMA v1.1, Section 9.2 on page 45"
           DEFVAL { 25 }
           ::= { imabGroupEntry 19 }

--imabGroupLeastDelayLink OBJECT-TYPE
--           SYNTAX           InterfaceIndexOrZero
--           MAX-ACCESS    read-only
--           STATUS           current
--           DESCRIPTION
--              "The ifIndex of the link configured in the IMA group which has
--              the smallest link propagation delay.    The distinguished value of
--              zero may be used if no link has been configured in the IMA group,
--              or if the link with the smallest link propagation delay has not
--              yet been determined."
--           REFERENCE
--              "ATM Forum IMA v1.1, Section 9.2 on page 45"
--           ::= { imabGroupEntry 20 }

--imabGroupDiffDelayMaxObs OBJECT-TYPE
--           SYNTAX           MilliSeconds
--           MAX-ACCESS    read-only
--           STATUS           current
--           DESCRIPTION
--              "The latest maximum differential delay observed (in milliseconds)
--              between the links having the least and most link propagation delay,
--              among the receive links that are currently configured in the IMA
--              group."
--           REFERENCE
--              "ATM Forum IMA v1.1, Section 9.2 on page 45"
--           ::= { imabGroupEntry 21 }

imabGroupAlphaValue OBJECT-TYPE
           SYNTAX           INTEGER (1.. 2)
           MAX-ACCESS    read-create
           STATUS           current
           DESCRIPTION
              "This indicates the 'alpha' value used to specify the number
              of consecutive invalid ICP cells to be detected before moving
              to the IMA Hunt state from the IMA Sync state."
           REFERENCE
              "ATM Forum IMA v1.1, Section 11 on page 68"
           DEFVAL { 2 }
           ::= { imabGroupEntry 22 }

imabGroupBetaValue OBJECT-TYPE
           SYNTAX           INTEGER (1.. 5)
           MAX-ACCESS    read-create
           STATUS           current
           DESCRIPTION
              "This indicates the 'beta' value used to specify the number
              of consecutive errored ICP cells to be detected before moving
              to the IMA Hunt state from the IMA Sync state."
           REFERENCE
              "ATM Forum IMA v1.1, Section 11 on page 68"
           DEFVAL { 2 }
           ::= { imabGroupEntry 23 }

imabGroupGammaValue OBJECT-TYPE
           SYNTAX           INTEGER (1.. 5)
           MAX-ACCESS    read-create
           STATUS           current
           DESCRIPTION
              "This indicates the 'gamma' value used to specify the number
              of consecutive valid ICP cells to be detected before moving
              to the IMA Sync state from the IMA PreSync state."
           REFERENCE
              "ATM Forum IMA v1.1, Section 11 on page 68"
           DEFVAL { 1 }
           ::= { imabGroupEntry 24 }

--imabGroupRunningSecs OBJECT-TYPE
--           SYNTAX           Gauge32
--           MAX-ACCESS    read-only
--           STATUS           current
--           DESCRIPTION
--              "The amount of time (in seconds) since this IMA group has
--              been in the Operational state."
--           REFERENCE
--              "ATM Forum IMA v1.1, Section 10.2.1 on page 55"
--           ::= { imabGroupEntry 25 }

--imabGroupUnavailSecs OBJECT-TYPE
--           SYNTAX           Counter32
--           MAX-ACCESS    read-only
--           STATUS           current
--           DESCRIPTION
--              "Count of one second intervals where the IMA Group Traffic
--              State Machine is Down."
--           REFERENCE
--              "ATM Forum IMA v1.1, Section 10.2.1 on page 55 and (R-136) in Section
--              12.2.2.2 on page 77"
--           ::= { imabGroupEntry 26 }

--imabGroupNeNumFailures OBJECT-TYPE
--           SYNTAX           Counter32
--           MAX-ACCESS    read-only
--           STATUS           current
--           DESCRIPTION
--              "The number of times a near-end group failure (Config-Aborted,
--              Insufficient-Links) has been reported since power-up or reboot."
--           REFERENCE
--              "ATM Forum IMA v1.1, (R-137) in Section 12.2.2.2 on page 77"
--           ::= { imabGroupEntry 27 }

--imabGroupFeNumFailures OBJECT-TYPE
--           SYNTAX           Counter32
--           MAX-ACCESS    read-only
--           STATUS           current
--           DESCRIPTION
--              "The number of times a far-end group failure (Config-Aborted-FE,
--              Insufficient-Links-FE, Blocked-FE) has been reported since
--              power-up or reboot.    This is an optional attribute."
--           REFERENCE
--              "ATM Forum IMA v1.1, (O-25) in Section 12.2.2.2 on page 77"
--           ::= { imabGroupEntry 28 }

--imabGroupTxAvailCellRate OBJECT-TYPE
--           SYNTAX           Gauge32
--           MAX-ACCESS    read-only
--           STATUS           current
--           DESCRIPTION
--              "The current cell rate (truncated value in cells per second)
--              provided by this IMA group in the transmit direction,
--              considering all the transmit links in the Active state."
--           ::= { imabGroupEntry 29 }

--imabGroupRxAvailCellRate OBJECT-TYPE
--           SYNTAX           Gauge32
--           MAX-ACCESS    read-only
--           STATUS           current
--           DESCRIPTION
--              "The current cell rate (truncated value in cells per second)
--              provided by this IMA group in the receive direction,
--              considering all the receive links in the Active state."
--           ::= { imabGroupEntry 30 }

--imaGroupNumTxCfgLinks is used by a network operator to tell how many
--links are configured for transmit in the IMA group.

--imabGroupNumTxCfgLinks OBJECT-TYPE
--           SYNTAX           Gauge32
--           MAX-ACCESS    read-only
--           STATUS           current
--           DESCRIPTION
--              "The number of links that are configured to transmit in this IMA
--              group. This attribute overwrites the value of the
--              imaGroupNumRxActLinks attribute when the IMA group is configured
--              in the Symmetrical Configuration group symmetry mode."
--           ::= { imabGroupEntry 31 }

--imaGroupNumRxCfgLinks is used by a network operator to tell how many
--links are configured for receive in the IMA group.

--imabGroupNumRxCfgLinks OBJECT-TYPE
--           SYNTAX           Gauge32
--           MAX-ACCESS    read-only
--           STATUS           current
--           DESCRIPTION
--              "The number of links that are configured to receive in this IMA
--              group. This attribute is overwritten by the value of the
--              imaGroupNumTxActLinks attribute when the IMA group is configured
--              in the Symmetrical Configuration group symmetry mode."
--           ::= { imabGroupEntry 32 }

--imaGroupNumTxActLinks is used by a network operator to tell how many
--links which are configured for transmit are also Active.

--imabGroupNumTxActLinks OBJECT-TYPE
--           SYNTAX           Gauge32
--           MAX-ACCESS    read-only
--           STATUS           current
--           DESCRIPTION
--              "The number of links which are configured to transmit and are
--              currently Active in this IMA group."
--           ::= { imabGroupEntry 33 }

--imaGroupNumRxActLinks is used by a network operator to tell how many
--links which are configured for receive are also Active.

--imabGroupNumRxActLinks OBJECT-TYPE
--           SYNTAX           Gauge32
--           MAX-ACCESS    read-only
--           STATUS           current
--           DESCRIPTION
--              "The number of links which are configured to receive and are
--              currently Active in this IMA group."
--           ::= { imabGroupEntry 34 }

--
--Test Pattern Procedure control objects.    These objects are implemented
--if the IMA implements the Test Pattern Procedure.    In this case all
--test pattern procedure related objects must be implemented.    Specifically,
--these objects are:
--
--     imaGroupTestLinkIfIndex
--     imaGroupTestPattern
--     imaGroupTestProcStatus
--     imaLinkRxTestPattern
--     imaLinkTestProcStatus
--

--imabGroupTestLinkIfIndex OBJECT-TYPE
--           SYNTAX           InterfaceIndexOrZero
--           MAX-ACCESS    read-create
--           STATUS           current
--           DESCRIPTION
--              "This object is used to designate an interface as the test link
--              for use in the Test Pattern Procedure.    The distinguished value of
--              zero specifies that the implementation may choose the Test Link,
--              in which case, the implementation may also choose the value of
--              'imaGroupTestPattern'.    The value zero may also be used if no link
--              has yet been added to the group.
--
--              Note that this value is NOT the same as the Tx LID value, but
--              instead either identifies the ifIndex value of the test link to be
--              used by the Test Pattern Procedure (i. e., the link whose LID value
--              is inserted in the Tx LID field of the transmitted ICP cells),
--              or identifies that the implementation may choose the test link (if
--              the value is zero)."
--           REFERENCE
--              "ATM Forum IMA v1.1, Section 13 on page 81"
--           DEFVAL { 0 }
--           ::= { imabGroupEntry 35 }

imabGroupTestPattern OBJECT-TYPE
           SYNTAX            INTEGER (-1.. 255)
           MAX-ACCESS    read-create
           STATUS           current
           DESCRIPTION
              "The value of this object is used to specify the Tx Test Pattern
              in an IMA group loopback operation.    A value in the range 0 to
              255 designates a specific pattern.    The distinguished value of
              -1 specifies that the implementation may choose the value.    In
              this case, the implementation may also choose the value of
              'imaGroupTestLinkIfIndex'.

              It is recommended that the specific value 255 not be used for
              testing, since by (R-137) the IMA interface is required to
              transmit 0xFF (i. e., 255) when the incoming test command is
              inactive or the test link is not detected, and thus it cannot
              be established for certain whether 255 was received due to an
              actual loopback operation or due to the normal operation of an
              IMA that is not performing (or else cannot perform) the test
              pattern procedure."
           REFERENCE
              "ATM Forum IMA v1.1, Section 13 on page 81"
           DEFVAL { -1 }
           ::= { imabGroupEntry 36 }

imabGroupTestProcStatus OBJECT-TYPE
           SYNTAX           ImaTestProcStatus
           MAX-ACCESS    read-create
           STATUS           current
           DESCRIPTION
              "This object is used to enable or disable the
              Test Pattern Procedure, and to note whether at least one
              link failed the test.

              The test is started by setting operating( 2) status.    If any
              link should fail the test, the IMA will set the status to
              linkFail( 3).    The linkFail( 3) state will persist until
              either the disabled( 1) state is set or until no instance
              of imaLinkTestProcStatus has the value linkFail( 3).

              Only the values disabled( 1) and operating( 2) may be written.
              Writing the operating( 2) value will not cause clearing of
              the linkFail( 3) state."
           REFERENCE
              "ATM Forum IMA v1.1, Section 13 on page 81"
           DEFVAL { disabled }
           ::= { imabGroupEntry 37 }

--
--Objects for use with the IMA Group Current Table, the IMA Group
--Interval Table, and the IMA Group Total Table.
--
--Implementation of these objects is optional, dependent on whether
--the tables mentioned above are implemented.
--

--imabGroupValidIntervals OBJECT-TYPE
--           SYNTAX            INTEGER (0.. 96)
--           MAX-ACCESS    read-only
--           STATUS           current
--           DESCRIPTION
--              "The number of previous 15 minute intervals for which valid data
--              was collected.    The value will be 96 unless the IMA group table
--              entry was created within the last 24 hours, in which case the value
--              will be the number of complete 15 minute intervals since the IMA
--              group table entry was created.    In the case where the agent is a
--              proxy, it is possible that some intervals are unavailable.    In this
--              case, this value is the maximum interval number for which valid
--              data is available.    This attribute is only mandatory when the IMA
--              Group Interval Statistics and/ or IMA Group Total Statistics objects
--              are implemented."
--           REFERENCE
--              "ATM Forum IMA v1.1, (O-26) in Section 12.2.2.2 on page 77"
--           ::= { imabGroupEntry 38 }
--
--imabGroupInvalidIntervals OBJECT-TYPE
--           SYNTAX            INTEGER (0.. 96)
--           MAX-ACCESS    read-only
--           STATUS           current
--           DESCRIPTION
--              "The number of intervals for which no valid data is available.
--              This attribute is only mandatory when the IMA Group Interval
--              Statistics and/ or IMA Group Total Statistics objects are
--              implemented."
--           REFERENCE
--              "ATM Forum IMA v1.1, (O-26) in Section 12.2.2.2 on page 77"
--           ::= { imabGroupEntry 39 }

--imabGroupTimeElapsed OBJECT-TYPE
--           SYNTAX           INTEGER (0.. 899)
--           MAX-ACCESS    read-only
--           STATUS           current
--           DESCRIPTION
--              "The number of seconds that have elapsed since the beginning of
--              the current measurement period.    This attribute is only mandatory
--              when the IMA Group Current Statistics are implemented."
--           REFERENCE
--              "ATM Forum IMA v1.1, (O-26) in Section 12.2.2.2 on page 77"
--           ::= { imabGroupEntry 40 }

--
--Objects to report the IMA OAM Label values transmitted and
--received by the IMA group.
--

imabGroupTxOamLabelValue OBJECT-TYPE
           SYNTAX           INTEGER (1.. 255)
           MAX-ACCESS    read-create
           STATUS           current
           DESCRIPTION
              "IMA OAM Label value transmitted by the NE IMA unit."
           REFERENCE
              "ATM Forum IMA v1.1, Section 5.2.2.3 on page 32"
           ::= { imabGroupEntry 41 }

--imabGroupRxOamLabelValue OBJECT-TYPE
--           SYNTAX           INTEGER (0.. 255)
--           MAX-ACCESS    read-only
--           STATUS           current
--           DESCRIPTION
--              "IMA OAM Label value transmitted by the FE IMA unit.    The value 0
--              likely means that the IMA unit has not received an OAM Label
--              from the FE IMA unit at this time."
--           REFERENCE
--              "ATM Forum IMA v1.1, Section 5.2.2.3 on page 32"
--           ::= { imabGroupEntry 42 }

imabGroupCLKMode   OBJECT-TYPE
	SYNTAX     INTEGER{
			master(0),
			 slave(1)
	}
	MAX-ACCESS read-create
	STATUS current
	DESCRIPTION
		"The clock mode of the Group "
	::= { imabGroupEntry 43 }


--
--The IMA Group Current Statistics subtree
--
--the IMA Group Current Table.    This table contains various statistics
--collected by each IMA group for the current 15 minute interval.
--
--Implementation of IMA Group Current Table is optional.
--

imabGroupCurrentTable OBJECT-TYPE
           SYNTAX           SEQUENCE OF imabGroupCurrentEntry
           MAX-ACCESS    not-accessible
           STATUS           current
           DESCRIPTION
              "The IMA Group Current table."
           ::= { zxImabGroupMibObjects 3 }

imabGroupCurrentEntry OBJECT-TYPE
           SYNTAX           imabGroupCurrentEntry
           MAX-ACCESS    not-accessible
           STATUS           current
           DESCRIPTION
              "An entry in the IMA Group Current table."
           INDEX             { imabGroupIndex }
           ::= { imabGroupCurrentTable 1 }

imabGroupCurrentEntry ::= SEQUENCE {
           imabGroupCurrentUnavailSecs          Gauge32,
           imabGroupCurrentNeNumFailures      Gauge32,
           imabGroupCurrentFeNumFailures      Gauge32 }

imabGroupCurrentUnavailSecs OBJECT-TYPE
           SYNTAX           Gauge32
           MAX-ACCESS    read-only
           STATUS           current
           DESCRIPTION
              "Count of one second intervals where the IMA Group Traffic
              State Machine is Down in the current 15 minutes interval."
           REFERENCE
              "ATM Forum IMA v1.1, Section 10.2.1 on page 55, (R-136) and
              (O-26) in Section 12.2.2.2 on page 77"
           ::= { imabGroupCurrentEntry 1 }

imabGroupCurrentNeNumFailures OBJECT-TYPE
           SYNTAX           Gauge32
           MAX-ACCESS    read-only
           STATUS           current
           DESCRIPTION
              "The number of times a near-end group failure (Config-Aborted,
              Insufficient-Links) has been reported in the current 15
              minutes interval."
           REFERENCE
              "ATM Forum IMA v1.1, (R-137) and (O-26) in Section 12.2.2.2
              on page 77"
           ::= { imabGroupCurrentEntry 2 }

imabGroupCurrentFeNumFailures OBJECT-TYPE
           SYNTAX           Gauge32
           MAX-ACCESS    read-only
           STATUS           current
           DESCRIPTION
              "The number of times a far-end group failure (Config-Aborted-FE,
              Insufficient-Links-FE, Blocked-FE) has been reported in the
              current 15 minutes interval.    This is an optional attribute."
           REFERENCE
              "ATM Forum IMA v1.1, (O-25) and (O-26) in Section 12.2.2.2
              on page 77"
           ::= { imabGroupCurrentEntry 3 }

--
--The IMA Group Interval Statistics subtree
--
--The IMA Group Interval Statistics subtree consists of a single table:
--the IMA Group Interval Table.    This table contains various statistics
--collected by each IMA group over the previous 24 hours of operation.
--The past 24 hours are broken into 96 completed 15 minute intervals.
--
--Implementation of IMA Group Interval Table is optional.
--

imabGroupIntervalTable OBJECT-TYPE
           SYNTAX           SEQUENCE OF imabGroupIntervalEntry
           MAX-ACCESS    not-accessible
           STATUS           current
           DESCRIPTION
              "The IMA Group Interval table."
           ::= { zxImabGroupMibObjects 4 }

imabGroupIntervalEntry OBJECT-TYPE
           SYNTAX           imabGroupIntervalEntry
           MAX-ACCESS    not-accessible
           STATUS           current
           DESCRIPTION
              "An entry in the IMA Group Interval table."
           INDEX             { imabGroupIndex, imabGroupIntervalNumber }
           ::= { imabGroupIntervalTable 1 }

imabGroupIntervalEntry ::= SEQUENCE {
           imabGroupIntervalNumber                   INTEGER (1.. 96),
           imabGroupIntervalUnavailSecs          Gauge32,
           imabGroupIntervalNeNumFailures      Gauge32,
           imabGroupIntervalFeNumFailures      Gauge32 }

imabGroupIntervalNumber OBJECT-TYPE
           SYNTAX            INTEGER (1.. 96)
           MAX-ACCESS    not-accessible
           STATUS           current
           DESCRIPTION
              "A number between 1 and 96, where 1 is the most
                recently completed 15 minute interval and 96 is the least
                recently completed 15 minutes interval (assuming that all
                96 intervals are valid)."
           ::= { imabGroupIntervalEntry 1 }

imabGroupIntervalUnavailSecs OBJECT-TYPE
           SYNTAX           Gauge32
           MAX-ACCESS    read-only
           STATUS           current
           DESCRIPTION
              "Count of one second intervals where the IMA Group Traffic
              State Machine is Down in one of the previous 96, individual 15
              minute, intervals."
           REFERENCE
              "ATM Forum IMA v1.1, Section 10.2.1 on page 55, (R-136) and
              (O-26) in Section 12.2.2.2 on page 77"
           ::= { imabGroupIntervalEntry 2 }

imabGroupIntervalNeNumFailures OBJECT-TYPE
           SYNTAX           Gauge32
           MAX-ACCESS    read-only
           STATUS           current
           DESCRIPTION
              "The number of times a near-end group failure (Config-Aborted,
              Insufficient-Links) has been reported in one of the previous
              96, individual 15 minute, intervals."
           REFERENCE
              "ATM Forum IMA v1.1, (R-137) and (O-26) in Section 12.2.2.2
              on page 77"
           ::= { imabGroupIntervalEntry 3 }

imabGroupIntervalFeNumFailures OBJECT-TYPE
           SYNTAX           Gauge32
           MAX-ACCESS    read-only
           STATUS           current
           DESCRIPTION
              "The number of times a far-end group failure (Config-Aborted-FE,
              Insufficient-Links-FE, Blocked-FE) has been reported in one of
              the previous 96, individual 15 minute, intervals.    This is an
              optional attribute."
           REFERENCE
              "ATM Forum IMA v1.1, (O-25) and (O-26) in Section 12.2.2.2
              on page 77"
           ::= { imabGroupIntervalEntry 4 }

--
--The IMA Group Total Statistics subtree
--
--The IMA Group Total Statistics subtree consists of a single table:
--the IMA Group Total Table.    This table contains the cumulative sum
--of the various statistics collected by each IMA group for the 24 hour
--period preceding the current interval.
--
--Implementation of IMA Group Total Table is optional.
--

imabGroupTotalTable OBJECT-TYPE
           SYNTAX           SEQUENCE OF imabGroupTotalEntry
           MAX-ACCESS    not-accessible
           STATUS           current
           DESCRIPTION
              "The IMA Group Total table."
           ::= { zxImabGroupMibObjects 5 }

imabGroupTotalEntry OBJECT-TYPE
           SYNTAX           imabGroupTotalEntry
           MAX-ACCESS    not-accessible
           STATUS           current
           DESCRIPTION
              "An entry in the IMA Group Total table."
           INDEX             { imabGroupIndex }
           ::= { imabGroupTotalTable 1 }

imabGroupTotalEntry ::= SEQUENCE {
           imabGroupTotalUnavailSecs          Gauge32,
           imabGroupTotalNeNumFailures      Gauge32,
           imabGroupTotalFeNumFailures      Gauge32 }

imabGroupTotalUnavailSecs OBJECT-TYPE
           SYNTAX           Gauge32
           MAX-ACCESS    read-only
           STATUS           current
           DESCRIPTION
              "Count of one second intervals where the IMA Group Traffic
              State Machine is Down in the previous 24 hour interval.
              Invalid 15 minute intervals count as 0."
           REFERENCE
              "ATM Forum IMA v1.1, Section 10.2.1 on page 55, (R-136) and
              (O-27) in Section 12.2.2.2 on page 77"
           ::= { imabGroupTotalEntry 1 }

imabGroupTotalNeNumFailures OBJECT-TYPE
           SYNTAX           Gauge32
           MAX-ACCESS    read-only
           STATUS           current
           DESCRIPTION
              "The number of times a near-end group failure (Config-Aborted,
              Insufficient-Links) has been reported in the previous 24 hour
              interval.    Invalid 15 minute intervals count as 0."
           REFERENCE
              "ATM Forum IMA v1.1, (R-137) and (O-27) in Section 12.2.2.2
              on page 77"
           ::= { imabGroupTotalEntry 2 }

imabGroupTotalFeNumFailures OBJECT-TYPE
           SYNTAX           Gauge32
           MAX-ACCESS    read-only
           STATUS           current
           DESCRIPTION
              "The number of times a far-end group failure (Config-Aborted-FE,
              Insufficient-Links-FE, Blocked-FE) has been reported in the
              previous 24 hour interval.    Invalid 15 minute intervals count
              as 0.    This is an optional attribute."
           REFERENCE
              "ATM Forum IMA v1.1, (O-25) and (O-27) in Section 12.2.2.2
              on page 77"
           ::= { imabGroupTotalEntry 3 }

--Conformance Information
--Compliance Statements


--Units of Conformance
imabGroupNumberGroup OBJECT-GROUP
  OBJECTS{
     imabGroupNumber
  }
 STATUS  current
 DESCRIPTION 
       "imabGroupNumber group"
 ::={zxImabGroupMibGroups 1}

imabGroupGroup OBJECT-GROUP
           OBJECTS {
           imabGroupIndex ,
           imabGroupRowStatus ,
           imabGroupIfIndex ,
           imabGroupNeState ,
           imabGroupFeState ,
           imabGroupFailureStatus ,
           imabGroupSymmetry ,
           imabGroupMinNumTxLinks ,
           imabGroupMinNumRxLinks ,
           imabGroupNeTxClkMode ,
           imabGroupFeTxClkMode ,
           imabGroupTxTimingRefLink ,
           imabGroupRxTimingRefLink ,
           imabGroupLastChange ,
           imabGroupTxImaId ,
           imabGroupRxImaId ,
           imabGroupTxFrameLength ,
           imabGroupRxFrameLength ,
           imabGroupDiffDelayMax ,
           imabGroupLeastDelayLink ,
           imabGroupDiffDelayMaxObs ,
           imabGroupAlphaValue ,
           imabGroupBetaValue ,
           imabGroupGammaValue ,
           imabGroupRunningSecs ,
           imabGroupUnavailSecs ,
           imabGroupNeNumFailures ,
           imabGroupFeNumFailures ,
           imabGroupTxAvailCellRate ,
           imabGroupRxAvailCellRate ,
           imabGroupNumTxCfgLinks ,
           imabGroupNumRxCfgLinks ,
           imabGroupNumTxActLinks ,
           imabGroupNumRxActLinks ,
           imabGroupTestLinkIfIndex ,
           imabGroupTestPattern ,
           imabGroupTestProcStatus ,
           imabGroupValidIntervals ,
           imabGroupInvalidIntervals ,
           imabGroupTimeElapsed ,
           imabGroupTxOamLabelValue ,
           imabGroupRxOamLabelValue ,
	   imabGroupCLKMode         }
           STATUS          current
           DESCRIPTION
              "A set of objects providing configuration and status information for
              an IMA group definition."
           ::= { zxImabGroupMibGroups 2 }

 imabGroupTestPatternGroup OBJECT-GROUP
           OBJECTS {
              imabGroupTestLinkIfIndex,
              imabGroupTestPattern,
              imabGroupTestProcStatus}
           STATUS          current
           DESCRIPTION
              "Objects in the imaGroupTable and imaLinkTable which control and
              report on the Test Pattern Procedure.    These objects must be
              implemented if the IMA Test Pattern Procedure is supported."
           ::= { zxImabGroupMibGroups 3 }


imabGroupIntervalGroup OBJECT-GROUP
           OBJECTS {
              imabGroupValidIntervals,
              imabGroupInvalidIntervals,
              imabGroupTimeElapsed,
              imabGroupCurrentUnavailSecs,
              imabGroupCurrentNeNumFailures,
              imabGroupCurrentFeNumFailures,
              imabGroupIntervalUnavailSecs,
              imabGroupIntervalNeNumFailures,
              imabGroupIntervalFeNumFailures,
              imabGroupTotalUnavailSecs,
              imabGroupTotalNeNumFailures,
              imabGroupTotalFeNumFailures }
           STATUS          current
           DESCRIPTION
              "Objects containing interval statistics for an IMA group."
           ::= { zxImabGroupMibGroups 4 }

zxImabGroupMibCompliance MODULE-COMPLIANCE
    STATUS  current
    DESCRIPTION
           "The compliance statement."
    MODULE  -- this module
    MANDATORY-GROUPS{
            imabGroupNumberGroup,
            imabGroupGroup,
            imabGroupTestPatternGroup,
            imabGroupIntervalGroup
            }
        ::= { zxImabGroupMibCompliances 1 }

END

IMAB-LINK-MIB DEFINITIONS ::= BEGIN

IMPORTS
           MODULE-IDENTITY, OBJECT-TYPE, Integer32, Counter32, Gauge32,
           NOTIFICATION-TYPE, enterprises
              FROM SNMPv2-SMI
           MODULE-COMPLIANCE, OBJECT-GROUP, NOTIFICATION-GROUP
              FROM SNMPv2-CONF
           TEXTUAL-CONVENTION, DateAndTime, RowStatus
              FROM SNMPv2-TC
           InterfaceIndex, InterfaceIndexOrZero, ifIndex
              FROM IF-MIB;
              
zxImabLinkMib MODULE-IDENTITY
           LAST-UPDATED "9902111830Z"
           ORGANIZATION "The ATM Forum"
           CONTACT-INFO
              "ATM Forum
              World Headquarters
              2570 West El Camino Real
              Suite 304
              Mountain View, CA 94040-1313
              USA
              Phone: +1 415 949 6700
              Fax: +1 415 949 6705
              email: info@ atmforum. com"
           DESCRIPTION
              "The MIB module for managing ATM Forum Inverse Multiplexing
              for ATM (IMA) interfaces."
           REVISION          "9902111830Z"
           DESCRIPTION
              "Updated and repaired version of the IMA-MIB released with the
              IMA v1.1 specification (af-phy-0086.001)."
           REVISION          "9701092245Z"
           DESCRIPTION
              "Initial incomplete version of the IMA-MIB as published in the
              IMA v1.0 specification (af-phy-0086.000)."
           ::= { zxIma 6 }

zte OBJECT IDENTIFIER ::= { enterprises 3902 }
zxDsl OBJECT IDENTIFIER ::= { zte 1004 }
zxDslam OBJECT IDENTIFIER ::= { zxDsl 1 }
zxIma	OBJECT IDENTIFIER ::= { zxDslam 11 }

zxImabLinkMibObjects OBJECT IDENTIFIER ::= { zxImabLinkMib 1 }

zxImabLinkMibConformance OBJECT IDENTIFIER ::= { zxImabLinkMib 2 }
zxImabLinkMibGroups OBJECT IDENTIFIER ::= { zxImabLinkMibConformance 1 }
zxImabLinkMibCompliances OBJECT IDENTIFIER ::= { zxImabLinkMibConformance 2 }


--Textual conventions

MilliSeconds ::= TEXTUAL-CONVENTION
           STATUS           current
           DESCRIPTION
              "Time in milliseconds"
           SYNTAX           Integer32

ImaLinkState ::= TEXTUAL-CONVENTION
           STATUS           current
           DESCRIPTION
              "State of a link belonging to an IMA group."
           REFERENCE
              "ATM Forum IMA v1.1, Section 10.1.2 on page 48"
           SYNTAX            INTEGER {
              notInGroup( 1),
              unusableNoGivenReason( 2),
              unusableFault( 3),
              unusableMisconnected( 4),
              unusableInhibited( 5),
              unusableFailed( 6),
              usable( 7),
              active( 8) }

ImaLinkFailureStatus ::= TEXTUAL-CONVENTION
           STATUS           current
           DESCRIPTION
              "Local failure status of a link belonging to an IMA group."
           REFERENCE
              "ATM Forum IMA v1.1, Section 10.1.2 on page 48"
           SYNTAX            INTEGER {
              noFailure( 1),
              imaLinkFailure( 2),
              lifFailure( 3),
              lodsFailure( 4),
              misConnected( 5),
              blocked( 6),
              fault( 7),
              farEndTxLinkUnusable( 8),
              farEndRxLinkUnusable( 9) }

ImaTestProcStatus ::= TEXTUAL-CONVENTION
           STATUS           current
           DESCRIPTION
              "States of the Test Pattern Procedure."
           REFERENCE
              "ATM Forum IMA v1.1, Section 13 on page 81"
           SYNTAX            INTEGER {
              disabled( 1),
              operating( 2),
              linkFail( 3) }

--
--The IMA Link subtree
--
--The IMA Link subtree consists of a table of IMA links.    Each entry
--in the table contains status information about a link which is part
--of an IMA group, and also contains a configuration object to select
--to which IMA group the link belongs.
--

imabLinkTable OBJECT-TYPE
           SYNTAX           SEQUENCE OF ImabLinkEntry
           MAX-ACCESS    not-accessible
           STATUS           current
           DESCRIPTION
              "The IMA group Link Status and Configuration table."
           ::= { zxImabLinkMibObjects 1 }

imabLinkEntry OBJECT-TYPE
           SYNTAX           ImabLinkEntry
           MAX-ACCESS    not-accessible
           STATUS           current
           DESCRIPTION
              "An entry in the IMA Group Link table."
           INDEX             { imabLinkIfIndex }
           ::= { imabLinkTable 1 }

ImabLinkEntry ::= SEQUENCE {
           imabLinkIfIndex                          InterfaceIndex,
           imabLinkRowStatus                      RowStatus,
           imabLinkGroupIndex                     Integer32,
--           imabLinkNeTxState                      ImaLinkState,
--           imabLinkNeRxState                      ImaLinkState,
--           imabLinkFeTxState                      ImaLinkState,
--           imabLinkFeRxState                      ImaLinkState,
--           imabLinkNeRxFailureStatus        ImaLinkFailureStatus,
--           imabLinkFeRxFailureStatus        ImaLinkFailureStatus,
--           imabLinkTxLid                              INTEGER (0.. 31),
--           imabLinkRxLid                              INTEGER (0.. 31),
--           imabLinkRelDelay                        MilliSeconds,
--           imabLinkImaViolations               Counter32,
--           imabLinkOifAnomalies                 Counter32,
--           imabLinkNeSevErroredSecs          Counter32,
--           imabLinkFeSevErroredSecs          Counter32,
--           imabLinkNeUnavailSecs               Counter32,
--           imabLinkFeUnavailSecs               Counter32,
--           imabLinkNeTxUnusableSecs          Counter32,
--           imabLinkNeRxUnusableSecs          Counter32,
--           imabLinkFeTxUnusableSecs          Counter32,
--           imabLinkFeRxUnusableSecs          Counter32,
--           imabLinkNeTxNumFailures            Counter32,
--           imabLinkNeRxNumFailures            Counter32,
--           imabLinkFeTxNumFailures            Counter32,
--           imabLinkFeRxNumFailures            Counter32,
--           imabLinkTxStuffs                        Counter32,
--           imabLinkRxStuffs                        Counter32,
--           imabLinkRxTestPattern               INTEGER (0.. 255),
--           imabLinkTestProcStatus             ImaTestProcStatus,
--           imabLinkValidIntervals             INTEGER (0.. 96),
--           imabLinkInvalidIntervals          INTEGER (0.. 96),
--           imabLinkTimeElapsed                   INTEGER (0.. 899),
	   imabLinkScramble			 INTEGER}

imabLinkIfIndex OBJECT-TYPE
           SYNTAX           InterfaceIndex
           MAX-ACCESS    not-accessible
           STATUS           current
           DESCRIPTION
              "This corresponds to the 'ifIndex' of the MIB-II interface
              on which this link is established.    This object also
              corresponds to the logical number ('ifIndex') assigned to
              this IMA link."
           ::= { imabLinkEntry 1 }

imabLinkRowStatus OBJECT-TYPE
           SYNTAX           RowStatus
           MAX-ACCESS    read-create
           STATUS           current
           DESCRIPTION
              "The imaLinkRowStatus object allows create, change, and delete
              operations on imaLinkTable entries.

              To create a new conceptual row (or instance) of the imaLinkTable,
              imaLinkRowStatus must be set to 'createAndWait' or 'createAndGo'.
              A successful set of the imaLinkGroupIndex object must be performed
              before the imaLinkRowStatus of a new conceptual row can be set to
              'active'.

              To change (modify) the imaLinkGroupIndex in an imaLinkTable entry,
              the imaLinkRowStatus object must first be set to 'notInService'.
              Only then can this object in the conceptual row be modified.
              This is due to the fact that the imaLinkGroupIndex object provides
              the association between a physical IMA link and the IMA group to
              which it belongs, and setting the imaLinkGroupIndex object to a
              different value has the effect of changing the association between
              a physical IMA link and an IMA group.    To place the link 'in group',
              the imaLinkRowStatus object is set to 'active'.    While the row is
              not in 'active' state, both the Transmit and Receive IMA link state
              machines are in the 'Not In Group' state.

              To remove (delete) an imaLinkTable entry from this table, set
              this object to 'destroy'."
           ::= { imabLinkEntry 2 }

imabLinkGroupIndex OBJECT-TYPE
           SYNTAX           Integer32
           MAX-ACCESS    read-create
           STATUS           current
           DESCRIPTION
              "The value which identifies the IMA group (imaGroupIndex)
              of which this link is a member."
           ::= { imabLinkEntry 3 }

--imabLinkNeTxState OBJECT-TYPE
--           SYNTAX           ImaLinkState
--           MAX-ACCESS    read-only
--           STATUS           current
--           DESCRIPTION
--              "The current state of the near-end transmit link."
--           REFERENCE
--              "ATM Forum IMA v1.1, Section 10.1.2 on page 48"
--           ::= { imabLinkEntry 4 }

--imabLinkNeRxState OBJECT-TYPE
--           SYNTAX           ImaLinkState
--           MAX-ACCESS    read-only
--           STATUS           current
--           DESCRIPTION
--              "The current state of the near-end receive link."
--           REFERENCE
--              "ATM Forum IMA v1.1, Section 10.1.2 on page 48"
--           ::= { imabLinkEntry 5 }

--imabLinkFeTxState OBJECT-TYPE
--           SYNTAX           ImaLinkState
--           MAX-ACCESS    read-only
--           STATUS           current
--           DESCRIPTION
--              "The current state of the far-end transmit link as reported
--              via ICP cells."
--           REFERENCE
--              "ATM Forum IMA v1.1, Section 10.1.2 on page 48"
--           ::= { imabLinkEntry 6 }

--imabLinkFeRxState OBJECT-TYPE
--           SYNTAX           ImaLinkState
--           MAX-ACCESS    read-only
--           STATUS           current
--           DESCRIPTION
--              "The current state of the far-end receive link as reported
--              via ICP cells."
--           REFERENCE
--              "ATM Forum IMA v1.1, Section 10.1.2 on page 48"
--           ::= { imabLinkEntry 7 }

--imabLinkNeRxFailureStatus OBJECT-TYPE
--           SYNTAX           ImaLinkFailureStatus
--           MAX-ACCESS    read-only
--           STATUS           current
--           DESCRIPTION
--              "The current link failure status of the near-end receive link."
--           REFERENCE
--              "ATM Forum IMA v1.1, Section 10.1.2 on page 48"
--           ::= { imabLinkEntry 8 }

--imabLinkFeRxFailureStatus OBJECT-TYPE
--           SYNTAX           ImaLinkFailureStatus
--           MAX-ACCESS    read-only
--           STATUS           current
--           DESCRIPTION
--              "The current link failure status of the far-end receive link
--              as reported via ICP cells."
--           REFERENCE
--              "ATM Forum IMA v1.1, Section 10.1.2 on page 48"
--           ::= { imabLinkEntry 9 }

--imabLinkTxLid OBJECT-TYPE
--           SYNTAX            INTEGER (0.. 31)
--           MAX-ACCESS    read-only
--           STATUS           current
--           DESCRIPTION
--              "The outgoing LID used currently on the link by the local end.
--              This value has meaning only if the link belongs to an IMA group."
--           REFERENCE
--              "ATM Forum IMA v1.1, Section 5.2.2.1 on page 26"
--           ::= { imabLinkEntry 10 }
--
--imabLinkRxLid OBJECT-TYPE
--           SYNTAX            INTEGER (0.. 31)
--           MAX-ACCESS    read-only
--           STATUS           current
--           DESCRIPTION
--              "The incoming LID used currently on the link by the remote
--              end as reported via ICP cells.    This value has meaning only
--              if the link belongs to an IMA group."
--           REFERENCE
--              "ATM Forum IMA v1.1, Section 5.2.2.1 on page 26"
--           ::= { imabLinkEntry 11 }
--
--imabLinkRelDelay OBJECT-TYPE
--           SYNTAX           MilliSeconds
--           MAX-ACCESS    read-only
--           STATUS           current
--           DESCRIPTION
--              "The latest measured delay on this link relative to the link, in
--              the same IMA group, with the least delay."
--           REFERENCE
--              "ATM Forum IMA v1.1, Section 9.2 on page 45"
--           ::= { imabLinkEntry 12 }
--
--imabLinkImaViolations OBJECT-TYPE
--           SYNTAX           Counter32
--           MAX-ACCESS    read-only
--           STATUS           current
--           DESCRIPTION
--              "ICP violations: count of errored, invalid or missing ICP cells,
--              except during SES-IMA or UAS-IMA conditions."
--           REFERENCE
--              "ATM Forum IMA v1.1, (R-125) in Section 12.2.2.2 on page 77"
--           ::= { imabLinkEntry 13 }
--
--imabLinkOifAnomalies OBJECT-TYPE
--           SYNTAX           Counter32
--           MAX-ACCESS    read-only
--           STATUS           current
--           DESCRIPTION
--              "The number of OIF anomalies, except during SES-IMA or UAS-IMA
--              conditions, at the near-end.    This is an optional attribute."
--           REFERENCE
--              "ATM Forum IMA v1.1, (O-20) in Section 12.2.2.2 on page 77"
--           ::= { imabLinkEntry 14 }
--
--imabLinkNeSevErroredSecs OBJECT-TYPE
--           SYNTAX           Counter32
--           MAX-ACCESS    read-only
--           STATUS           current
--           DESCRIPTION
--              "Count of one second intervals containing >= 30% of the ICP cells
--              counted as IV-IMAs, or one or more link defects (e. g., LOS, OOF/ LOF,
--              AIS, or LCD), LIF defects, or LODS defects, except during UAS-IMA
--              condition."
--           REFERENCE
--              "ATM Forum IMA v1.1, (R-126) in Section 12.2.2.2 on page 77"
--           ::= { imabLinkEntry 15 }
--
--imabLinkFeSevErroredSecs OBJECT-TYPE
--           SYNTAX           Counter32
--           MAX-ACCESS    read-only
--           STATUS           current
--           DESCRIPTION
--              "Count of one second intervals containing one or more RDI-IMA
--              defects, except during UAS-IMA-FE condition."
--           REFERENCE
--              "ATM Forum IMA v1.1, (R-127) in Section 12.2.2.2 on page 77"
--           ::= { imabLinkEntry 16 }
--
--imabLinkNeUnavailSecs OBJECT-TYPE
--           SYNTAX           Counter32
--           MAX-ACCESS    read-only
--           STATUS           current
--           DESCRIPTION
--              "Count of unavailable seconds at near-end: unavailability begins
--              at the onset of 10 contiguous SES-IMA and ends at the onset
--              of 10 contiguous seconds with no SES-IMA."
--           REFERENCE
--              "ATM Forum IMA v1.1, (R-128) in Section 12.2.2.2 on page 77"
--           ::= { imabLinkEntry 17 }
--
--imabLinkFeUnavailSecs OBJECT-TYPE
--           SYNTAX           Counter32
--           MAX-ACCESS    read-only
--           STATUS           current
--           DESCRIPTION
--              "Count of unavailable seconds at far-end: unavailability begins
--              at the onset of 10 contiguous SES-IMA-FE and ends at the onset of
--              10 contiguous seconds with no SES-IMA-FE."
--           REFERENCE
--              "ATM Forum IMA v1.1, (R-129) in Section 12.2.2.2 on page 77"
--           ::= { imabLinkEntry 18 }
--
--imabLinkNeTxUnusableSecs OBJECT-TYPE
--           SYNTAX           Counter32
--           MAX-ACCESS    read-only
--           STATUS           current
--           DESCRIPTION
--              "Tx Unusable seconds: count of Tx Unusable seconds at the near-end
--              Tx LSM."
--           REFERENCE
--              "ATM Forum IMA v1.1, (R-130) in Section 12.2.2.2 on page 77"
--           ::= { imabLinkEntry 19 }
--
--imabLinkNeRxUnusableSecs OBJECT-TYPE
--           SYNTAX           Counter32
--           MAX-ACCESS    read-only
--           STATUS           current
--           DESCRIPTION
--              "Rx Unusable seconds: count of Rx Unusable seconds at the near-end
--              Rx LSM."
--           REFERENCE
--              "ATM Forum IMA v1.1, (R-131) in Section 12.2.2.2 on page 77"
--           ::= { imabLinkEntry 20 }
--
--imabLinkFeTxUnusableSecs OBJECT-TYPE
--           SYNTAX           Counter32
--           MAX-ACCESS    read-only
--           STATUS           current
--           DESCRIPTION
--              "Tx Unusable seconds at far-end: count of seconds with Tx Unusable
--              indications from the far-end Tx LSM."
--           REFERENCE
--              "ATM Forum IMA v1.1, (R-132) in Section 12.2.2.2 on page 77"
--           ::= { imabLinkEntry 21 }
--
--imabLinkFeRxUnusableSecs OBJECT-TYPE
--           SYNTAX           Counter32
--           MAX-ACCESS    read-only
--           STATUS           current
--           DESCRIPTION
--              "Rx Unusable seconds at far-end: count of seconds with Rx Unusable
--              indications from the far-end Rx LSM."
--           REFERENCE
--              "ATM Forum IMA v1.1, (R-133) in Section 12.2.2.2 on page 77"
--           ::= { imabLinkEntry 22 }
--
--imabLinkNeTxNumFailures OBJECT-TYPE
--           SYNTAX           Counter32
--           MAX-ACCESS    read-only
--           STATUS           current
--           DESCRIPTION
--              "The number of times a near-end transmit failure alarm condition
--              has been entered on this link (i. e., some form of implementation
--              specific transmit fault)."
--           REFERENCE
--              "ATM Forum IMA v1.1, (R-134) in Section 12.2.2.2 on page 77"
--           ::= { imabLinkEntry 23 }
--
--imabLinkNeRxNumFailures OBJECT-TYPE
--           SYNTAX           Counter32
--           MAX-ACCESS    read-only
--           STATUS           current
--           DESCRIPTION
--              "The number of times a near-end receive failure alarm condition
--              has been entered on this link (i. e., LIF, LODS,
--              RFI-IMA, Mis-Connected or some form of implementation specific receive
--              fault)."
--           REFERENCE
--              "ATM Forum IMA v1.1, (R-135) in Section 12.2.2.2 on page 77"
--           ::= { imabLinkEntry 24 }
--
--imabLinkFeTxNumFailures OBJECT-TYPE
--           SYNTAX           Counter32
--           MAX-ACCESS    read-only
--           STATUS           current
--           DESCRIPTION
--              "The number of times a far-end transmit failure alarm condition
--              has been entered on this link (i. e., Tx-Unusable-FE).    This is an
--              optional attribute."
--           REFERENCE
--              "ATM Forum IMA v1.1, (O-21) in Section 12.2.2.2 on page 77"
--           ::= { imabLinkEntry 25 }
--
--imabLinkFeRxNumFailures OBJECT-TYPE
--           SYNTAX           Counter32
--           MAX-ACCESS    read-only
--           STATUS           current
--           DESCRIPTION
--              "The number of times a far-end receive failure alarm condition
--              has been entered on this link (i. e., Rx-Unusable-FE).    This is an
--              optional attribute."
--           REFERENCE
--              "ATM Forum IMA v1.1, (O-22) in Section 12.2.2.2 on page 77"
--           ::= { imabLinkEntry 26 }
--
--imabLinkTxStuffs OBJECT-TYPE
--           SYNTAX           Counter32
--           MAX-ACCESS    read-only
--           STATUS           current
--           DESCRIPTION
--              "Count of stuff events inserted in the transmit direction.
--              This is an optional attribute."
--           REFERENCE
--              "ATM Forum IMA v1.1, (O-23) in Section 12.2.2.2 on page 77"
--           ::= { imabLinkEntry 27 }
--
--imabLinkRxStuffs OBJECT-TYPE
--           SYNTAX           Counter32
--           MAX-ACCESS    read-only
--           STATUS           current
--           DESCRIPTION
--              "Count of stuff events detected in the receive direction.
--              This is an optional attribute."
--           REFERENCE
--              "ATM Forum IMA v1.1, (O-24) in Section 12.2.2.2 on page 77"
--           ::= { imabLinkEntry 28 }
--

--Test Pattern Procedure control objects.    These objects are implemented
--if the IMA implements the Test Pattern Procedure.    In this case all
--test pattern procedure related objects must be implemented.    Specifically,
--these objects are:
--
--     imaGroupTestLinkIfIndex
--     imaGroupTestPattern
--     imaGroupTestProcStatus
--     imaLinkRxTestPattern
--     imaLinkTestProcStatus
--

--imabLinkRxTestPattern OBJECT-TYPE
--           SYNTAX           INTEGER (0.. 255)
--           MAX-ACCESS    read-only
--           STATUS           current
--           DESCRIPTION
--              "This object identifies the test pattern received in the
--              ICP Cell (octet 17) on the link during the IMA Test Pattern
--              Procedure.    This value may then be compared to the transmitted
--              test pattern."
--           ::= { imabLinkEntry 29 }
--
--imabLinkTestProcStatus OBJECT-TYPE
--           SYNTAX           ImaTestProcStatus
--           MAX-ACCESS    read-only
--           STATUS           current
--           DESCRIPTION
--              "This value indicates the current state of the Test Pattern
--              Procedure.    If the value is disabled( 1), the test is not
--              running.    A value of operating( 2) means the test is running
--              and no error has been found on this interface.    A value of
--              linkFail( 3) means an error has been detected on this link
--              during the test.
--
--              Once an error is detected, the linkFail( 3) value is latched until
--              either this object is read or until the imaGroupTestProcStatus
--              is moved to disabled( 1).    Once read, if the error no longer
--              persists, a subsequent read will report the value operating( 2)."
--           ::= { imabLinkEntry 30 }

--
--Objects for use with the IMA Link Current Table, the IMA Link
--Interval Table, and the IMA Link Total Table.
--
--Implementation of these objects is optional, dependent on whether
--the tables mentioned above are implemented.
--

--imabLinkValidIntervals OBJECT-TYPE
--           SYNTAX            INTEGER (0.. 96)
--           MAX-ACCESS    read-only
--           STATUS           current
--           DESCRIPTION
--              "The number of previous 15 minute intervals for which valid data
--              was collected.    The value will be 96 unless the IMA group table
--              entry was created within the last 24 hours, in which case the value
--              will be the number of complete 15 minute intervals since the IMA
--              group table entry was created.    In the case where the agent is a
--              proxy, it is possible that some intervals are unavailable.    In this
--              case, this value is the maximum interval number for which valid
--              data is available.    This attribute is only mandatory when the IMA
--              Link Interval Statistics and/ or IMA Link Total Statistics objects
--              are implemented."
--           REFERENCE
--              "ATM Forum IMA v1.1, (O-26) in Section 12.2.2.2 on page 77"
--           ::= { imabLinkEntry 31 }
--
--imabLinkInvalidIntervals OBJECT-TYPE
--           SYNTAX            INTEGER (0.. 96)
--           MAX-ACCESS    read-only
--           STATUS           current
--           DESCRIPTION
--              "The number of intervals for which no valid data is available.
--              This attribute is only mandatory when the IMA Link Interval
--              Statistics and/ or IMA Link Total Statistics objects are
--              implemented."
--           REFERENCE
--              "ATM Forum IMA v1.1, (O-26) in Section 12.2.2.2
--                on page 77"
--           ::= { imabLinkEntry 32 }
--
--imabLinkTimeElapsed OBJECT-TYPE
--           SYNTAX           INTEGER (0.. 899)
--           MAX-ACCESS    read-only
--           STATUS           current
--           DESCRIPTION
--              "The number of seconds that have elapsed since the beginning of
--              the current measurement period.    This attribute is only mandatory
--              when the IMA Link Current Statistics are implemented."
--           REFERENCE
--              "ATM Forum IMA v1.1, (O-26) in Section 12.2.2.2
--                on page 77"
--           ::= { imabLinkEntry 33 }

imabLinkScramble OBJECT-TYPE
	SYNTAX        INTEGER{
			disable(0),
			 enable(1)
	}
	MAX-ACCESS read-create
	STATUS current
	DESCRIPTION
		"enable/disable the scramble status of the link"
	::= { imabLinkEntry 34 }

--
--The IMA Link Current Statistics subtree
--
--The IMA Link Current Statistics subtree consists of a single table:
--the IMA Link Current Table.    This table contains various statistics
--collected by each IMA link for the current 15 minute interval.
--
--Implementation of IMA Link Current Table is optional.
--

imabLinkCurrentTable OBJECT-TYPE
           SYNTAX           SEQUENCE OF ImabLinkCurrentEntry
           MAX-ACCESS    not-accessible
           STATUS           current
           DESCRIPTION
              "The IMA Link Current table."
           ::= { zxImabLinkMibObjects 2 }

imabLinkCurrentEntry OBJECT-TYPE
           SYNTAX           ImabLinkCurrentEntry
           MAX-ACCESS    not-accessible
           STATUS           current
           DESCRIPTION
              "An entry in the IMA Link Current table."
           INDEX             { ifIndex }
           ::= { imabLinkCurrentTable 1 }

ImabLinkCurrentEntry ::= SEQUENCE {
           imabLinkCurrentImaViolations          Gauge32,
           imabLinkCurrentOifAnomalies            Gauge32,
           imabLinkCurrentNeSevErroredSecs    Gauge32,
           imabLinkCurrentFeSevErroredSecs    Gauge32,
           imabLinkCurrentNeUnavailSecs          Gauge32,
           imabLinkCurrentFeUnavailSecs          Gauge32,
           imabLinkCurrentNeTxUnusableSecs    Gauge32,
           imabLinkCurrentNeRxUnusableSecs    Gauge32,
           imabLinkCurrentFeTxUnusableSecs    Gauge32,
           imabLinkCurrentFeRxUnusableSecs    Gauge32,
           imabLinkCurrentNeTxNumFailures      Gauge32,
           imabLinkCurrentNeRxNumFailures      Gauge32,
           imabLinkCurrentFeTxNumFailures      Gauge32,
           imabLinkCurrentFeRxNumFailures      Gauge32,
           imabLinkCurrentTxStuffs                   Gauge32,
           imabLinkCurrentRxStuffs                   Gauge32 }

imabLinkCurrentImaViolations OBJECT-TYPE
           SYNTAX           Gauge32
           MAX-ACCESS    read-only
           STATUS           current
           DESCRIPTION
              "ICP violations: count of errored, invalid or missing ICP cells,
              except during SES-IMA or UAS-IMA conditions, in the current
              15 minute interval."
           REFERENCE
              "ATM Forum IMA v1.1, (R-125) and (O-26) in Section 12.2.2.2
              on page 77"
           ::= { imabLinkCurrentEntry 1 }

imabLinkCurrentOifAnomalies OBJECT-TYPE
           SYNTAX           Gauge32
           MAX-ACCESS    read-only
           STATUS           current
           DESCRIPTION
              "The number of OIF anomalies, except during SES-IMA or UAS-IMA
              conditions, at the near-end in the current 15 minute interval.
              This is an optional attribute."
           REFERENCE
              "ATM Forum IMA v1.1, (O-20) and (O-26) in Section 12.2.2.2
              on page 77"
           ::= { imabLinkCurrentEntry 2 }

imabLinkCurrentNeSevErroredSecs OBJECT-TYPE
           SYNTAX           Gauge32
           MAX-ACCESS    read-only
           STATUS           current
           DESCRIPTION
              "Count of one second intervals containing >= 30% of the ICP cells
              counted as IV-IMAs, or one or more link defects (e. g., LOS, OOF/ LOF,
              AIS, or LCD), LIF defects, or LODS defects, except during UAS-IMA
              condition, in the current 15 minute interval."
           REFERENCE
              "ATM Forum IMA v1.1, (R-126) and (O-26) in Section 12.2.2.2
              on page 77"
           ::= { imabLinkCurrentEntry 3 }

imabLinkCurrentFeSevErroredSecs OBJECT-TYPE
           SYNTAX           Gauge32
           MAX-ACCESS    read-only
           STATUS           current
           DESCRIPTION
              "Count of one second intervals containing one or more RDI-IMA
              defects, except during UAS-IMA-FE condition, in the current 15
              minute interval."
           REFERENCE
              "ATM Forum IMA v1.1, (R-127) and (O-26) in Section 12.2.2.2
              on page 77"
           ::= { imabLinkCurrentEntry 4 }

imabLinkCurrentNeUnavailSecs OBJECT-TYPE
           SYNTAX           Gauge32
           MAX-ACCESS    read-only
           STATUS           current
           DESCRIPTION
              "Count of unavailable seconds at near-end in the current 15 minute
              interval: unavailability begins at the onset of 10 contiguous
              SES-IMA and ends at the onset of 10 contiguous seconds with no
              SES-IMA."
           REFERENCE
              "ATM Forum IMA v1.1, (R-128) and (O-26) in Section 12.2.2.2
              on page 77"
           ::= { imabLinkCurrentEntry 5 }

imabLinkCurrentFeUnavailSecs OBJECT-TYPE
           SYNTAX           Gauge32
           MAX-ACCESS    read-only
           STATUS           current
           DESCRIPTION
              "Count of unavailable seconds at far-end in the current 15 minute
              interval: unavailability begins at the onset of 10 contiguous
              SES-IMA-FE and ends at the onset of 10 contiguous seconds with no
              SES-IMA-FE."
           REFERENCE
              "ATM Forum IMA v1.1, (R-129) and (O-26) in Section 12.2.2.2
              on page 77"
           ::= { imabLinkCurrentEntry 6 }

imabLinkCurrentNeTxUnusableSecs OBJECT-TYPE
           SYNTAX           Gauge32
           MAX-ACCESS    read-only
           STATUS           current
           DESCRIPTION
              "Tx Unusable seconds: count of Unusable seconds at the near-end
              Tx LSM in the current 15 minute interval."
           REFERENCE
              "ATM Forum IMA v1.1, (R-130) and (O-26) in Section 12.2.2.2
              on page 77"
           ::= { imabLinkCurrentEntry 7 }

imabLinkCurrentNeRxUnusableSecs OBJECT-TYPE
           SYNTAX           Gauge32
           MAX-ACCESS    read-only
           STATUS           current
           DESCRIPTION
              "Rx Unusable seconds: count of Unusable seconds at the near-end
              Rx LSM in the current 15 minute interval."
           REFERENCE
              "ATM Forum IMA v1.1, (R-131) and (O-26) in Section 12.2.2.2
              on page 77"
           ::= { imabLinkCurrentEntry 8 }

imabLinkCurrentFeTxUnusableSecs OBJECT-TYPE
           SYNTAX           Gauge32
           MAX-ACCESS    read-only
           STATUS           current
           DESCRIPTION
              "Tx Unusable seconds at far-end: count of seconds with Tx Unusable
              indications from the far-end Tx LSM in the current 15 minute
              interval."
           REFERENCE
              "ATM Forum IMA v1.1, (R-132) and (O-26) in Section 12.2.2.2
              on page 77"
           ::= { imabLinkCurrentEntry 9 }

imabLinkCurrentFeRxUnusableSecs OBJECT-TYPE
           SYNTAX           Gauge32
           MAX-ACCESS    read-only
           STATUS           current
           DESCRIPTION
              "Rx Unusable seconds at far-end: count of seconds with Rx Unusable
              indications from the far-end Rx LSM in the current 15 minute
              interval."
           REFERENCE
              "ATM Forum IMA v1.1, (R-133) and (O-26) in Section 12.2.2.2
              on page 77"
           ::= { imabLinkCurrentEntry 10 }

imabLinkCurrentNeTxNumFailures OBJECT-TYPE
           SYNTAX           Gauge32
           MAX-ACCESS    read-only
           STATUS           current
           DESCRIPTION
              "The number of times a near-end transmit failure alarm condition
              has been entered on this link (i. e., some form of implementation
              specific transmit fault) in the current 15 minute interval."
           REFERENCE
              "ATM Forum IMA v1.1, (R-134) and (O-26) in Section 12.2.2.2
              on page 77"
           ::= { imabLinkCurrentEntry 11 }

imabLinkCurrentNeRxNumFailures OBJECT-TYPE
           SYNTAX           Gauge32
           MAX-ACCESS    read-only
           STATUS           current
           DESCRIPTION
              "The number of times a near-end receive failure alarm condition
              has been entered on this link (i. e., LIF, LODS, RFI-IMA, Mis-Connected,
              or some form of implementation specific receive fault)
              in the current 15 minute interval."
           REFERENCE
              "ATM Forum IMA v1.1, (R-135) and (O-26) in Section 12.2.2.2
              on page 77"
           ::= { imabLinkCurrentEntry 12 }

imabLinkCurrentFeTxNumFailures OBJECT-TYPE
           SYNTAX           Gauge32
           MAX-ACCESS    read-only
           STATUS           current
           DESCRIPTION
              "The number of times a far-end transmit failure alarm condition
              has been entered on this link (i. e., Tx-Unusable-FE) in the
              current 15 minute interval.    This is an optional attribute."
           REFERENCE
              "ATM Forum IMA v1.1, (O-21) and (O-26) in Section 12.2.2.2
              on page 77"
           ::= { imabLinkCurrentEntry 13 }

imabLinkCurrentFeRxNumFailures OBJECT-TYPE
           SYNTAX           Gauge32
           MAX-ACCESS    read-only
           STATUS           current
           DESCRIPTION
              "The number of times a far-end receive failure alarm condition
              has been entered on this link (i. e., Rx-Unusable-FE) in the
              current 15 minute interval.    This is an optional attribute."
           REFERENCE
              "ATM Forum IMA v1.1, (O-22) and (O-26) in Section 12.2.2.2
              on page 77"
           ::= { imabLinkCurrentEntry 14 }

imabLinkCurrentTxStuffs OBJECT-TYPE
           SYNTAX           Gauge32
           MAX-ACCESS    read-only
           STATUS           current
           DESCRIPTION
              "Count of stuff events inserted in the transmit direction in
              the current 15 minute interval.    This is an optional attribute."
           REFERENCE
              "ATM Forum IMA v1.1, (O-23) and (O-26) in Section 12.2.2.2
              on page 77"
           ::= { imabLinkCurrentEntry 15 }

imabLinkCurrentRxStuffs OBJECT-TYPE
           SYNTAX           Gauge32
           MAX-ACCESS    read-only
           STATUS           current
           DESCRIPTION
              "Count of stuff events detected in the receive direction in
              the current 15 minute interval.    This is an optional attribute."
           REFERENCE
              "ATM Forum IMA v1.1, (O-24) and (O-26) in Section 12.2.2.2
              on page 77"
           ::= { imabLinkCurrentEntry 16 }

--
--The IMA Link Interval Statistics subtree
--
--The IMA Link Interval Statistics subtree consists of a single table:
--the IMA Link Interval Table.    This table contains various statistics
--collected by each IMA link over the previous 24 hours of operation.
--The past 24 hours are broken into 96 completed 15 minute intervals.
--
--Implementation of IMA Link Interval Table is optional.
--

imabLinkIntervalTable OBJECT-TYPE
           SYNTAX           SEQUENCE OF ImabLinkIntervalEntry
           MAX-ACCESS    not-accessible
           STATUS           current
           DESCRIPTION
              "The IMA Link Interval table."
           ::= { zxImabLinkMibObjects 3 }

imabLinkIntervalEntry OBJECT-TYPE
           SYNTAX           ImabLinkIntervalEntry
           MAX-ACCESS    not-accessible
           STATUS           current
           DESCRIPTION
              "An entry in the IMA Link Interval table."
           INDEX             { ifIndex, imabLinkIntervalNumber }
           ::= { imabLinkIntervalTable 1 }

ImabLinkIntervalEntry ::= SEQUENCE {
           imabLinkIntervalNumber                      INTEGER (1.. 96),
           imabLinkIntervalImaViolations          Gauge32,
           imabLinkIntervalOifAnomalies            Gauge32,
           imabLinkIntervalNeSevErroredSecs    Gauge32,
           imabLinkIntervalFeSevErroredSecs    Gauge32,
           imabLinkIntervalNeUnavailSecs          Gauge32,
           imabLinkIntervalFeUnavailSecs          Gauge32,
           imabLinkIntervalNeTxUnusableSecs    Gauge32,
           imabLinkIntervalNeRxUnusableSecs    Gauge32,
           imabLinkIntervalFeTxUnusableSecs    Gauge32,
           imabLinkIntervalFeRxUnusableSecs    Gauge32,
           imabLinkIntervalNeTxNumFailures      Gauge32,
           imabLinkIntervalNeRxNumFailures      Gauge32,
           imabLinkIntervalFeTxNumFailures      Gauge32,
           imabLinkIntervalFeRxNumFailures      Gauge32,
           imabLinkIntervalTxStuffs                   Gauge32,
           imabLinkIntervalRxStuffs                   Gauge32 }

imabLinkIntervalNumber OBJECT-TYPE
           SYNTAX            INTEGER (1.. 96)
           MAX-ACCESS    not-accessible
           STATUS           current
           DESCRIPTION
              "A number between 1 and 96, where 1 is the most
                recently completed 15 minute interval and 96 is the least
                recently completed 15 minutes interval (assuming that all
                96 intervals are valid)."
           ::= { imabLinkIntervalEntry 1 }

imabLinkIntervalImaViolations OBJECT-TYPE
           SYNTAX           Gauge32
           MAX-ACCESS    read-only
           STATUS           current
           DESCRIPTION
              "ICP violations: count of errored, invalid or missing ICP cells,
              except during SES-IMA or UAS-IMA conditions, in one of the
              previous 96, individual 15 minute, intervals."
           REFERENCE
              "ATM Forum IMA v1.1, (R-125) and (O-26) in Section 12.2.2.2
              on page 77"
           ::= { imabLinkIntervalEntry 2 }

imabLinkIntervalOifAnomalies OBJECT-TYPE
           SYNTAX           Gauge32
           MAX-ACCESS    read-only
           STATUS           current
           DESCRIPTION
              "The number of OIF anomalies, except during SES-IMA or UAS-IMA
              conditions, at the near-end in one of the previous 96, individual
              15 minute, intervals.    This is an optional attribute."
           REFERENCE
              "ATM Forum IMA v1.1, (O-20) and (O-26) in Section 12.2.2.2
              on page 77"
           ::= { imabLinkIntervalEntry 3 }

imabLinkIntervalNeSevErroredSecs OBJECT-TYPE
           SYNTAX           Gauge32
           MAX-ACCESS    read-only
           STATUS           current
           DESCRIPTION
              "Count of one second intervals containing >= 30% of the ICP cells
              counted as IV-IMAs, or one or more link defects (e. g., LOS, OOF/ LOF,
              AIS, or LCD), LIF defects, or LODS defects, except during UAS-IMA
              condition, in one of the previous 96, individual 15 minute,
              intervals."
           REFERENCE
              "ATM Forum IMA v1.1, (R-126) and (O-26) in Section 12.2.2.2
              on page 77"
           ::= { imabLinkIntervalEntry 4 }

imabLinkIntervalFeSevErroredSecs OBJECT-TYPE
           SYNTAX           Gauge32
           MAX-ACCESS    read-only
           STATUS           current
           DESCRIPTION
              "Count of one second intervals containing one or more RDI-IMA
              defects, except during UAS-IMA-FE condition, in one of the previous
              96, individual 15 minute, intervals."
           REFERENCE
              "ATM Forum IMA v1.1, (R-127) and (O-26) in Section 12.2.2.2
              on page 77"
           ::= { imabLinkIntervalEntry 5 }

imabLinkIntervalNeUnavailSecs OBJECT-TYPE
           SYNTAX           Gauge32
           MAX-ACCESS    read-only
           STATUS           current
           DESCRIPTION
              "Count of unavailable seconds at near-end in one of the previous
              96, individual 15 minute, intervals: unavailability begins at the
              onset of 10 contiguous SES-IMA and ends at the onset of 10
              contiguous seconds with no SES-IMA."
           REFERENCE
              "ATM Forum IMA v1.1, (R-128) and (O-26) in Section 12.2.2.2
              on page 77"
           ::= { imabLinkIntervalEntry 6 }

imabLinkIntervalFeUnavailSecs OBJECT-TYPE
           SYNTAX           Gauge32
           MAX-ACCESS    read-only
           STATUS           current
           DESCRIPTION
              "Count of unavailable seconds at far-end in one of the previous
              96, individual 15 minute, intervals: unavailability begins at the
              onset of 10 contiguous SES-IMA-FE and ends at the onset of 10
              contiguous seconds with no SES-IMA-FE."
           REFERENCE
              "ATM Forum IMA v1.1, (R-129) and (O-26) in Section 12.2.2.2
              on page 77"
           ::= { imabLinkIntervalEntry 7 }

imabLinkIntervalNeTxUnusableSecs OBJECT-TYPE
           SYNTAX           Gauge32
           MAX-ACCESS    read-only
           STATUS           current
           DESCRIPTION
              "Tx Unusable seconds: count of Unusable seconds at the near-end
              Tx LSM in one of the previous 96, individual 15 minute, intervals."
           REFERENCE
              "ATM Forum IMA v1.1, (R-130) and (O-26) in Section 12.2.2.2
              on page 77"
           ::= { imabLinkIntervalEntry 8 }

imabLinkIntervalNeRxUnusableSecs OBJECT-TYPE
           SYNTAX           Gauge32
           MAX-ACCESS    read-only
           STATUS           current
           DESCRIPTION
              "Rx Unusable seconds: count of Unusable seconds at the near-end
              Rx LSM in one of the previous 96, individual 15 minute, intervals."
           REFERENCE
              "ATM Forum IMA v1.1, (R-131) and (O-26) in Section 12.2.2.2
              on page 77"
           ::= { imabLinkIntervalEntry 9 }

imabLinkIntervalFeTxUnusableSecs OBJECT-TYPE
           SYNTAX           Gauge32
           MAX-ACCESS    read-only
           STATUS           current
           DESCRIPTION
              "Tx Unusable seconds at far-end: count of seconds with Tx Unusable
              indications from the far-end Tx LSM in one of the previous 96,
              individual 15 minute, intervals."
           REFERENCE
              "ATM Forum IMA v1.1, (R-132) and (O-26) in Section 12.2.2.2
              on page 77"
           ::= { imabLinkIntervalEntry 10 }

imabLinkIntervalFeRxUnusableSecs OBJECT-TYPE
           SYNTAX           Gauge32
           MAX-ACCESS    read-only
           STATUS           current
           DESCRIPTION
              "Rx Unusable seconds at far-end: count of seconds with Rx Unusable
              indications from the far-end Rx LSM in one of the previous 96,
              individual 15 minute, intervals."
           REFERENCE
              "ATM Forum IMA v1.1, (R-133) and (O-26) in Section 12.2.2.2
              on page 77"
           ::= { imabLinkIntervalEntry 11 }

imabLinkIntervalNeTxNumFailures OBJECT-TYPE
           SYNTAX           Gauge32
           MAX-ACCESS    read-only
           STATUS           current
           DESCRIPTION
              "The number of times a near-end transmit failure alarm condition
              has been entered on this link (i. e., some form of implementation
              specific transmit fault) in one of the previous 96, individual
              15 minute, intervals."
           REFERENCE
              "ATM Forum IMA v1.1, (R-134) and (O-26) in Section 12.2.2.2
              on page 77"
           ::= { imabLinkIntervalEntry 12 }

imabLinkIntervalNeRxNumFailures OBJECT-TYPE
           SYNTAX           Gauge32
           MAX-ACCESS    read-only
           STATUS           current
           DESCRIPTION
              "The number of times a near-end receive failure alarm condition
              has been entered on this link (i. e., LIF, LODS, RFI-IMA,
              Mis-Connected, or some form of implementation specific
              receive fault) in one of the previous 96, individual 15 minute,
              intervals."
           REFERENCE
              "ATM Forum IMA v1.1, (R-135) and (O-26) in Section 12.2.2.2
              on page 77"
           ::= { imabLinkIntervalEntry 13 }

imabLinkIntervalFeTxNumFailures OBJECT-TYPE
           SYNTAX           Gauge32
           MAX-ACCESS    read-only
           STATUS           current
           DESCRIPTION
              "The number of times a far-end transmit failure alarm condition
              has been entered on this link (i. e., Tx-Unusable-FE) in one of the
              previous 96, individual 15 minute, intervals.    This is an optional
              attribute."
           REFERENCE
              "ATM Forum IMA v1.1, (O-21) and (O-26) in Section 12.2.2.2
              on page 77"
           ::= { imabLinkIntervalEntry 14 }

imabLinkIntervalFeRxNumFailures OBJECT-TYPE
           SYNTAX           Gauge32
           MAX-ACCESS    read-only
           STATUS           current
           DESCRIPTION
              "The number of times a far-end receive failure alarm condition
              has been entered on this link (i. e., Rx-Unusable-FE) in one of
              the previous 96, individual 15 minute, intervals.    This is an
              optional attribute."
           REFERENCE
              "ATM Forum IMA v1.1, (O-22) and (O-26) in Section 12.2.2.2
              on page 77"
           ::= { imabLinkIntervalEntry 15 }

imabLinkIntervalTxStuffs OBJECT-TYPE
           SYNTAX           Gauge32
           MAX-ACCESS    read-only
           STATUS           current
           DESCRIPTION
              "Count of stuff events inserted in the transmit direction in
              one of the previous 96, individual 15 minute, intervals.    This
              is an optional attribute."
           REFERENCE
              "ATM Forum IMA v1.1, (O-23) and (O-26) in Section 12.2.2.2
              on page 77"
           ::= { imabLinkIntervalEntry 16 }

imabLinkIntervalRxStuffs OBJECT-TYPE
           SYNTAX           Gauge32
           MAX-ACCESS    read-only
           STATUS           current
           DESCRIPTION
              "Count of stuff events detected in the receive direction in
              one of the previous 96, individual 15 minute, intervals.    This
              is an optional attribute."
           REFERENCE
              "ATM Forum IMA v1.1, (O-24) and (O-26) in Section 12.2.2.2
              on page 77"
           ::= { imabLinkIntervalEntry 17 }

--
--The IMA Link Total Statistics subtree
--
--The IMA Link Total Statistics subtree consists of a single table:
--the IMA Link Total Table.    This table contains the cumulative sum
--of the various statistics collected by each IMA link for the 24 hour
--period preceding the current interval.
--
--Implementation of IMA Link Total Table is optional.
--

imabLinkTotalTable OBJECT-TYPE
           SYNTAX           SEQUENCE OF ImabLinkTotalEntry
           MAX-ACCESS    not-accessible
           STATUS           current
           DESCRIPTION
              "The IMA Link Total table."
           ::= { zxImabLinkMibObjects 4 }

imabLinkTotalEntry OBJECT-TYPE
           SYNTAX           ImabLinkTotalEntry
           MAX-ACCESS    not-accessible
           STATUS           current
           DESCRIPTION
              "An entry in the IMA Link Total table."
           INDEX             { ifIndex }
           ::= { imabLinkTotalTable 1 }

ImabLinkTotalEntry ::= SEQUENCE {
           imabLinkTotalImaViolations          Gauge32,
           imabLinkTotalOifAnomalies            Gauge32,
           imabLinkTotalNeSevErroredSecs    Gauge32,
           imabLinkTotalFeSevErroredSecs    Gauge32,
           imabLinkTotalNeUnavailSecs          Gauge32,
           imabLinkTotalFeUnavailSecs          Gauge32,
           imabLinkTotalNeTxUnusableSecs    Gauge32,
           imabLinkTotalNeRxUnusableSecs    Gauge32,
           imabLinkTotalFeTxUnusableSecs    Gauge32,
           imabLinkTotalFeRxUnusableSecs    Gauge32,
           imabLinkTotalNeTxNumFailures      Gauge32,
           imabLinkTotalNeRxNumFailures      Gauge32,
           imabLinkTotalFeTxNumFailures      Gauge32,
           imabLinkTotalFeRxNumFailures      Gauge32,
           imabLinkTotalTxStuffs                   Gauge32,
           imabLinkTotalRxStuffs                   Gauge32 }

imabLinkTotalImaViolations OBJECT-TYPE
           SYNTAX           Gauge32
           MAX-ACCESS    read-only
           STATUS           current
           DESCRIPTION
              "ICP violations: count of errored, invalid or missing ICP cells,
              except during SES-IMA or UAS-IMA conditions, in the previous 24
              hour interval.    Invalid 15 minute intervals count as 0."
           REFERENCE
              "ATM Forum IMA v1.1, (R-125) and (O-27) in Section 12.2.2.2
              on page 77"
           ::= { imabLinkTotalEntry 1 }

imabLinkTotalOifAnomalies OBJECT-TYPE
           SYNTAX           Gauge32
           MAX-ACCESS    read-only
           STATUS           current
           DESCRIPTION
              "The number of OIF anomalies, except during SES-IMA or UAS-IMA
              conditions, at the near-end in the previous 24 hour interval.
              Invalid 15 minute intervals count as 0.    This is an optional
              attribute."
           REFERENCE
              "ATM Forum IMA v1.1, (O-20) and (O-27) in Section 12.2.2.2
              on page 77"
           ::= { imabLinkTotalEntry 2 }

imabLinkTotalNeSevErroredSecs OBJECT-TYPE
           SYNTAX           Gauge32
           MAX-ACCESS    read-only
           STATUS           current
           DESCRIPTION
              "Count of one second intervals containing >= 30% of the ICP cells
              counted as IV-IMAs, or one or more link defects (e. g., LOS, OOF/ LOF,
              AIS, or LCD), LIF defects, or LODS defects, except during UAS-IMA
              condition, in the previous 24 hour interval.    Invalid 15 minute
              intervals count as 0."
           REFERENCE
              "ATM Forum IMA v1.1, (R-126) and (O-27) in Section 12.2.2.2
              on page 77"
           ::= { imabLinkTotalEntry 3 }

imabLinkTotalFeSevErroredSecs OBJECT-TYPE
           SYNTAX           Gauge32
           MAX-ACCESS    read-only
           STATUS           current
           DESCRIPTION
              "Count of one second intervals containing one or more RDI-IMA
              defects, except during UAS-IMA-FE condition, in the previous 24
              hour interval.    Invalid 15 minute intervals count as 0."
           REFERENCE
              "ATM Forum IMA v1.1, (R-127) and (O-27) in Section 12.2.2.2
              on page 77"
           ::= { imabLinkTotalEntry 4 }

imabLinkTotalNeUnavailSecs OBJECT-TYPE
           SYNTAX           Gauge32
           MAX-ACCESS    read-only
           STATUS           current
           DESCRIPTION
              "Count of unavailable seconds at near-end in the previous 24 hour
              interval: unavailability begins at the onset of 10 contiguous
              SES-IMA and ends at the onset of 10 contiguous seconds with no
              SES-IMA.    Invalid 15 minute intervals count as 0."
           REFERENCE
              "ATM Forum IMA v1.1, (R-128) and (O-27) in Section 12.2.2.2
              on page 77"
           ::= { imabLinkTotalEntry 5 }

imabLinkTotalFeUnavailSecs OBJECT-TYPE
           SYNTAX           Gauge32
           MAX-ACCESS    read-only
           STATUS           current
           DESCRIPTION
              "Count of unavailable seconds at far-end in the previous 24 hour
              interval: unavailability begins at the onset of 10 contiguous
              SES-IMA-FE and ends at the onset of 10 contiguous seconds with no
              SES-IMA-FE.    Invalid 15 minute intervals count as 0."
           REFERENCE
              "ATM Forum IMA v1.1, (R-129) and (O-27) in Section 12.2.2.2
              on page 77"
           ::= { imabLinkTotalEntry 6 }

imabLinkTotalNeTxUnusableSecs OBJECT-TYPE
           SYNTAX           Gauge32
           MAX-ACCESS    read-only
           STATUS           current
           DESCRIPTION
              "Tx Unusable seconds: count of Unusable seconds at the near-end
              Tx LSM in the previous 24 hour interval.    Invalid 15 minute
              intervals count as 0."
           REFERENCE
              "ATM Forum IMA v1.1, (R-130) and (O-27) in Section 12.2.2.2
              on page 77"
           ::= { imabLinkTotalEntry 7 }

imabLinkTotalNeRxUnusableSecs OBJECT-TYPE
           SYNTAX           Gauge32
           MAX-ACCESS    read-only
           STATUS           current
           DESCRIPTION
              "Rx Unusable seconds: count of Unusable seconds at the near-end
              Rx LSM in the previous 24 hour interval.    Invalid 15 minute
              intervals count as 0."
           REFERENCE
              "ATM Forum IMA v1.1, (R-131) and (O-27) in Section 12.2.2.2
              on page 77"
           ::= { imabLinkTotalEntry 8 }

imabLinkTotalFeTxUnusableSecs OBJECT-TYPE
           SYNTAX           Gauge32
           MAX-ACCESS    read-only
           STATUS           current
           DESCRIPTION
              "Tx Unusable seconds at far-end: count of seconds with Tx Unusable
              indications from the far-end Tx LSM in the previous 24 hour
              interval.    Invalid 15 minute intervals count as 0."
           REFERENCE
              "ATM Forum IMA v1.1, (R-132) and (O-27) in Section 12.2.2.2
              on page 77"
           ::= { imabLinkTotalEntry 9 }

imabLinkTotalFeRxUnusableSecs OBJECT-TYPE
           SYNTAX           Gauge32
           MAX-ACCESS    read-only
           STATUS           current
           DESCRIPTION
              "Rx Unusable seconds at far-end: count of seconds with Rx Unusable
              indications from the far-end Rx LSM in the previous 24 hour
              interval.    Invalid 15 minute intervals count as 0."
           REFERENCE
              "ATM Forum IMA v1.1, (R-133) and (O-27) in Section 12.2.2.2
              on page 77"
           ::= { imabLinkTotalEntry 10 }

imabLinkTotalNeTxNumFailures OBJECT-TYPE
           SYNTAX           Gauge32
           MAX-ACCESS    read-only
           STATUS           current
           DESCRIPTION
              "The number of times a near-end transmit failure alarm condition
              has been entered on this link (i. e., some form of implementation
              specific transmit fault) in the previous 24 hour interval.
              Invalid 15 minute intervals count as 0."
           REFERENCE
              "ATM Forum IMA v1.1, (R-134) and (O-27) in Section 12.2.2.2
              on page 77"
           ::= { imabLinkTotalEntry 11 }

imabLinkTotalNeRxNumFailures OBJECT-TYPE
           SYNTAX           Gauge32
           MAX-ACCESS    read-only
           STATUS           current
           DESCRIPTION
              "The number of times a near-end receive failure alarm condition
              has been entered on this link (i. e., LIF, LODS, RFI-IMA,
              Mis-Connected, or some form of implementation specific receive fault)
              in the previous 24 hour interval. Invalid 15 minute intervals
              count as 0."
           REFERENCE
              "ATM Forum IMA v1.1, (R-135) and (O-27) in Section 12.2.2.2
              on page 77"
           ::= { imabLinkTotalEntry 12 }

imabLinkTotalFeTxNumFailures OBJECT-TYPE
           SYNTAX           Gauge32
           MAX-ACCESS    read-only
           STATUS           current
           DESCRIPTION
              "The number of times a far-end transmit failure alarm condition
              has been entered on this link (i. e., Tx-Unusable-FE) in the
              previous 24 hour interval.    Invalid 15 minute intervals count
              as 0.    This is an optional attribute."
           REFERENCE
              "ATM Forum IMA v1.1, (O-21) and (O-27) in Section 12.2.2.2
              on page 77"
           ::= { imabLinkTotalEntry 13 }

imabLinkTotalFeRxNumFailures OBJECT-TYPE
           SYNTAX           Gauge32
           MAX-ACCESS    read-only
           STATUS           current
           DESCRIPTION
              "The number of times a far-end receive failure alarm condition
              has been entered on this link (i. e., Rx-Unusable-FE) in the
              previous 24 hour interval.    Invalid 15 minute intervals count
              as 0.    This is an optional attribute."
           REFERENCE
              "ATM Forum IMA v1.1, (O-22) and (O-27) in Section 12.2.2.2
              on page 77"
           ::= { imabLinkTotalEntry 14 }

imabLinkTotalTxStuffs OBJECT-TYPE
           SYNTAX           Gauge32
           MAX-ACCESS    read-only
           STATUS           current
           DESCRIPTION
              "Count of stuff events inserted in the transmit direction in
              the previous 24 hour interval.    Invalid 15 minute intervals
              count as 0.    This is an optional attribute."
           REFERENCE
              "ATM Forum IMA v1.1, (O-23) and (O-27) in Section 12.2.2.2
              on page 77"
           ::= { imabLinkTotalEntry 15 }

imabLinkTotalRxStuffs OBJECT-TYPE
           SYNTAX           Gauge32
           MAX-ACCESS    read-only
           STATUS           current
           DESCRIPTION
              "Count of stuff events detected in the receive direction in
              the previous 24 hour interval.    Invalid 15 minute intervals
              count as 0.    This is an optional attribute."
           REFERENCE
              "ATM Forum IMA v1.1, (O-24) and (O-27) in Section 12.2.2.2
              on page 77"
           ::= { imabLinkTotalEntry 16 }

--Conformance Information
--Compliance Statements

imabLinkGroup OBJECT-GROUP
           OBJECTS {
              imabLinkRowStatus,
              imabLinkGroupIndex,
              imabLinkNeTxState,
              imabLinkNeRxState,
              imabLinkFeTxState,
              imabLinkFeRxState,
              imabLinkNeRxFailureStatus,
              imabLinkFeRxFailureStatus,
              imabLinkTxLid,
              imabLinkRxLid,
              imabLinkRelDelay,
              imabLinkImaViolations,
              imabLinkOifAnomalies,
              imabLinkNeSevErroredSecs,
              imabLinkFeSevErroredSecs,
              imabLinkNeUnavailSecs,
              imabLinkFeUnavailSecs,
              imabLinkNeTxUnusableSecs,
              imabLinkNeRxUnusableSecs,
              imabLinkFeTxUnusableSecs,
              imabLinkFeRxUnusableSecs,
              imabLinkNeTxNumFailures,
              imabLinkNeRxNumFailures,
              imabLinkFeTxNumFailures,
              imabLinkFeRxNumFailures,
              imabLinkTxStuffs,
              imabLinkRxStuffs,
	      imabLinkScramble }
           STATUS          current
           DESCRIPTION
              "A set of objects providing status information for an IMA link."
           ::= { zxImabLinkMibGroups 1 }

 imabLinkTestPatternGroup OBJECT-GROUP
           OBJECTS {
              imabLinkRxTestPattern,
              imabLinkTestProcStatus }
           STATUS          current
           DESCRIPTION
              "Objects in the imaGroupTable and imaLinkTable which control and
              report on the Test Pattern Procedure.    These objects must be
              implemented if the IMA Test Pattern Procedure is supported."
           ::= { zxImabLinkMibGroups 2 }

imabLinkIntervalGroup OBJECT-GROUP
           OBJECTS {
              imabLinkValidIntervals,
              imabLinkInvalidIntervals,
              imabLinkTimeElapsed,
              imabLinkCurrentImaViolations,
              imabLinkCurrentOifAnomalies,
              imabLinkCurrentNeSevErroredSecs,
              imabLinkCurrentFeSevErroredSecs,
              imabLinkCurrentNeUnavailSecs,
              imabLinkCurrentFeUnavailSecs,
              imabLinkCurrentNeTxUnusableSecs,
              imabLinkCurrentNeRxUnusableSecs,
              imabLinkCurrentFeTxUnusableSecs,
              imabLinkCurrentFeRxUnusableSecs,
              imabLinkCurrentNeTxNumFailures,
              imabLinkCurrentNeRxNumFailures,
              imabLinkCurrentFeTxNumFailures,
              imabLinkCurrentFeRxNumFailures,
              imabLinkCurrentTxStuffs,
              imabLinkCurrentRxStuffs,
              imabLinkIntervalImaViolations,
              imabLinkIntervalOifAnomalies,
              imabLinkIntervalNeSevErroredSecs,
              imabLinkIntervalFeSevErroredSecs,
              imabLinkIntervalNeUnavailSecs,
              imabLinkIntervalFeUnavailSecs,
              imabLinkIntervalNeTxUnusableSecs,
              imabLinkIntervalNeRxUnusableSecs,
              imabLinkIntervalFeTxUnusableSecs,
              imabLinkIntervalFeRxUnusableSecs,
              imabLinkIntervalNeTxNumFailures,
              imabLinkIntervalNeRxNumFailures,
              imabLinkIntervalFeTxNumFailures,
              imabLinkIntervalFeRxNumFailures,
              imabLinkIntervalTxStuffs,
              imabLinkIntervalRxStuffs,
              imabLinkTotalimaViolations,
              imabLinkTotalOifAnomalies,
              imabLinkTotalNeSevErroredSecs,
              imabLinkTotalFeSevErroredSecs,
              imabLinkTotalNeUnavailSecs,
              imabLinkTotalFeUnavailSecs,
              imabLinkTotalNeTxUnusableSecs,
              imabLinkTotalNeRxUnusableSecs,
              imabLinkTotalFeTxUnusableSecs,
              imabLinkTotalFeRxUnusableSecs,
              imabLinkTotalNeTxNumFailures,
              imabLinkTotalNeRxNumFailures,
              imabLinkTotalFeTxNumFailures,
              imabLinkTotalFeRxNumFailures,
              imabLinkTotalTxStuffs,
              imabLinkTotalRxStuffs }
           STATUS          current
           DESCRIPTION
              "Objects containing interval statistics for an IMA link."
           ::= { zxImabLinkMibGroups 3 }

zxImabLinkMibCompliance MODULE-COMPLIANCE
    STATUS  current
    DESCRIPTION
           "The compliance statement."
    MODULE  -- this module
    MANDATORY-GROUPS{
            imabLinkGroup,
            imabLinkTestPatternGroup,
            imabLinkIntervalGroup
            }
        ::= { zxImabLinkMibCompliances 1 }

END
IMAB-SYS-MIB DEFINITIONS ::= BEGIN

IMPORTS
           MODULE-IDENTITY, OBJECT-TYPE, Integer32, Counter32, Gauge32,
           NOTIFICATION-TYPE, enterprises
              FROM SNMPv2-SMI
           MODULE-COMPLIANCE, OBJECT-GROUP, NOTIFICATION-GROUP
              FROM SNMPv2-CONF
           TEXTUAL-CONVENTION, DateAndTime, RowStatus
              FROM SNMPv2-TC
           InterfaceIndex, InterfaceIndexOrZero, ifIndex
              FROM IF-MIB;
              
zxImabSysMib MODULE-IDENTITY
           LAST-UPDATED "9902111830Z"
           ORGANIZATION "The ATM Forum"
           CONTACT-INFO
              "ATM Forum
              World Headquarters
              2570 West El Camino Real
              Suite 304
              Mountain View, CA 94040-1313
              USA
              Phone: +1 415 949 6700
              Fax: +1 415 949 6705
              email: info@ atmforum. com"
           DESCRIPTION
              "The MIB module for managing ATM Forum Inverse Multiplexing
              for ATM (IMA) interfaces."
           REVISION          "9902111830Z"
           DESCRIPTION
              "Updated and repaired version of the IMA-MIB released with the
              IMA v1.1 specification (af-phy-0086.001)."
           REVISION          "9701092245Z"
           DESCRIPTION
              "Initial incomplete version of the IMA-MIB as published in the
              IMA v1.0 specification (af-phy-0086.000)."
           ::= { zxIma 4 }

zte OBJECT IDENTIFIER ::= { enterprises 3902 }
zxDsl OBJECT IDENTIFIER ::= { zte 1004 }
zxDslam OBJECT IDENTIFIER ::= { zxDsl 1 }
zxIma	OBJECT IDENTIFIER ::= { zxDslam 11 }

zxImabSysMibObjects OBJECT IDENTIFIER ::= { zxImabSysMib 1 }
zxImabTrap          OBJECT IDENTIFIER ::= { zxImabSysMib 2 }
zxImabSysMibConformance OBJECT IDENTIFIER ::= { zxImabSysMib 3 }
zxImabSysMibTrapPrefix OBJECT IDENTIFIER ::= { zxImabTrap 0 }

zxImabSysMibGroups OBJECT IDENTIFIER ::= { zxImabSysMibConformance 1 }
zxImabSysMibCompliances OBJECT IDENTIFIER ::= { zxImabSysMibConformance 2 }

---IMA common definition.

imabVersionNumber OBJECT-TYPE
	SYNTAX INTEGER
	MAX-ACCESS read-only
	STATUS current
	DESCRIPTION
		"the ima version ,which is from version head structure of 'ver.bin' "
::= { zxImabSysMibObjects 1 }

imabMaxSupportedGroupNumber OBJECT-TYPE
	SYNTAX Integer32
	MAX-ACCESS read-only
	STATUS current
	DESCRIPTION
		"The max number of IMA groups supported in this system
	the default value:16 "
::= { zxImabSysMibObjects 2 }

imabMaxSupportedLinkNumber OBJECT-TYPE
	SYNTAX Integer32
	MAX-ACCESS read-only
	STATUS current
	DESCRIPTION
		"The max number of IMA Links supported in this system
	the default value:16 "
::= { zxImabSysMibObjects 3 }

imabDataManagementCmd OBJECT-TYPE
        SYNTAX INTEGER {
               noop(1),           -- no operation
               save(2),           -- save all configuration parameters to NVM
               saveInProgress(3),  -- read-only: NVM save in progress
               clear(4),		 --  clear all configuration parameters in NVM
               clearInProgress(5),   -- read-only: clear NVM is in progressing
               reset(6)
        }
        MAX-ACCESS read-write
        STATUS current
        DESCRIPTION
            "When set to 'save(2)', all nonvolatile configuration
             parameters are saved to NVM (Nonvolatile Memory).  NVM save
             operations may be slow (e.g., erasing/writing Flash device).
             Consequently, all or many updates should be made before
             saving to NVM.  Note that the SNMP set to 'save(2)' returns
             immediately to the caller.  Gets on this object then return
             'saveInProgress(3)' until the save operation completes, at
             which time 'noop(1)' is returned.  Consequently, a get
             operation always returns 'noop(1)' or 'saveInProgress(3)'
             depending on the current state.

             When set to 'clear(4)', all configuration parameters in NVM will cleared,
             system data return back to 'no config' state. when clear NVM data, this scalar 
             is set to 'clearInProgress(5)' to forbid 'save' or 'clear' command by others.
             
             The agent returns 'badValue' for SNMPv1 or 'inconsistentValue'
             for SNMPv2c/v3 for a set to 'Save(2)' while the current get
             state is 'saveInProgress(3)'.
             
             Attempts to set this object to 'saveInProgress(3)' returns
             'badValue' for SNMPv1 or 'wrongValue' for SNMPv2c/v3. "
             
        ::= { zxImabSysMibObjects 4 }
        
imabSlotID OBJECT-TYPE
	SYNTAX Integer32
	MAX-ACCESS read-only
	STATUS current
	DESCRIPTION
		"the slot id of ima in the dislam  "
::= { zxImabSysMibObjects 5 }

imabAlarmStatus OBJECT-TYPE
	SYNTAX  INTEGER {
		cleared(1),
		declared(2) }
	MAX-ACCESS accessible-for-notify
	STATUS current
	DESCRIPTION
		"Status of the IMA alarm."
::= { zxImabSysMibObjects 6 }

imabAlarmType OBJECT-TYPE
           SYNTAX        INTEGER {
                   ima_EVT_LNK_LIF(1),
  								 ima_EVT_LNK_LODS(2),
  								 ima_EVT_LNK_RFI(3),
  								 ima_EVT_LNK_TX_MISC(4),
  								 ima_EVT_LNK_FAULT(7),
  								 ima_EVT_LNK_TX_UUS_FE(8),
  								 ima_EVT_LNK_RX_UUS_FE(9)  
           }
           MAX-ACCESS    accessible-for-notify
           STATUS        current
           DESCRIPTION
              "The Type of IMA alarm declared or cleared.    The value of
              ImaAlarmType identifies the type of alarm according to the
              definitions in the IMA specification."
           REFERENCE
              "ATM Forum IMA v1.1, Section 12.2.3 on page 79"
            ::= { zxImabSysMibObjects 7 }

imabFailureAlarm NOTIFICATION-TYPE
           OBJECTS {
              ifIndex,
              imaAlarmStatus,
              imaAlarmType }
           STATUS           current
           DESCRIPTION
              "The imaFailureAlarm provides a method for an agent implementing IMA
              to notify an NMS of an alarm condition."
           REFERENCE
              "ATM Forum IMA v1.1, Section 12.2.3 on page 79"
           ::= { zxImabSysMibTrapPrefix 1 }

--Conformance Information
imabCommonGroup OBJECT-GROUP
           OBJECTS {
	      imabVersionNumber,
              imabMaxSupportedGroupNumber,
              imabMaxSupportedLinkNumber,
              imabDataManagementCmd,
              imabSlotID,
              imabAlarmStatus,
              imabAlarmType,
              imabFailureAlarm
              }
           STATUS          current
           DESCRIPTION
              "Objects used in System Cotrol and common information group."
           ::= { zxImabSysMibGroups 1 }

 zxImabSysMibCompliance MODULE-COMPLIANCE
    STATUS  current
    DESCRIPTION
           "The compliance statement."
    MODULE  -- this module
    MANDATORY-GROUPS{
            imabCommonGroup
            }
        ::= { zxImabSysMibCompliances 1 }

END

------------------------------------------------------------------------------

--  IMAB END
------------------------------------------------------------------------------


------------------------------------------------------------------------------
--
--  File         : wandCommMib.mib
--  Description  : ZTE WAND MIB  
--
------------------------------------------------------------------------------
WAND-COMM-MIB DEFINITIONS ::= BEGIN

	IMPORTS
			MODULE-IDENTITY, OBJECT-TYPE,
			enterprises					FROM SNMPv2-SMI
			MODULE-COMPLIANCE, OBJECT-GROUP			FROM SNMPv2-CONF		
			MacAddress                           FROM SNMPv2-TC
			wandCommMib                          FROM WRS-MASTER-MIB
			PortList, dot1qStaticMulticastEntry		FROM Q-BRIDGE-MIB;       

    wandCleanFlash OBJECT-TYPE
        SYNTAX INTEGER {
               noop(1),            -- no operation
               clean(2),           -- clean the data in flash
               cleanInProgress(3)  -- read-only: flash clean in progress
        }
        MAX-ACCESS read-write
        STATUS current
        DESCRIPTION
            "When set to 'clean(2)', the data in flash are cleaned . This
             operations may be slow . Consequently, all or many updates 
             should be made before cleaning the flash.  Note that the SNMP
             set to 'clean(2)' returns immediately to the caller.  Gets on
             this object then return  'cleanInProgress(3)' until the clean
             operation completes, at which time 'noop(1)' is returned.  
             Consequently, a get operation always returns 'noop(1)' or 
             'cleanInProgress(3)' depending on the current state.
            
             The agent returns 'badValue' for SNMPv1 or 'inconsistentValue'
             for SNMPv2c/v3 for a set to 'clean(2)' while the current get
             state is 'cleanInProgress(3)'.
             
             Attempts to set this object to 'cleanInProgress(3)' returns
             'badValue' for SNMPv1 or 'wrongValue' for SNMPv2c/v3."
        ::= { wandCommMib 1 }

    wandReset OBJECT-TYPE
        SYNTAX INTEGER {
               noop(1),           -- no operation
               reset(2),          -- reset unit
               resetToDefaults(3) -- reset to factory defaults/reset unit
        }
        MAX-ACCESS read-write
        STATUS current
        DESCRIPTION
            "Physically performs a hardware reset of the unit. 
             Use with care.  A 'reset(2)' resets the unit, a
             'resetToDefaults(3)' resets the NVM configuration
             to factory defaults and then resets the unit, and 'noop(1)'
             does nothing.  A value of 'noop(1)' is always returned for a
             GET operation."
        ::= { wandCommMib 2 }

    wandVersionNumber OBJECT-TYPE
        SYNTAX OCTET STRING (SIZE (0..4))
        MAX-ACCESS read-only
        STATUS current
        DESCRIPTION
            "Get this MIB Major version number.  This number should 
             match the Major version given in the documentation header
             at the beginning text of this MIB.  Note that the '.c' file
             corresponding to this MIB has to be manually edited to
             change the version number if this file is modified and
             the version number is therefore changed."
        ::= { wandCommMib 3 }


    wandSaveFlash OBJECT-TYPE
        SYNTAX INTEGER {
               noop(1),           -- no operation
               save(2),           -- save all configuration parameters to NVM
               saveInProgress(3)  -- read-only: NVM save in progress
        }
        MAX-ACCESS read-write
        STATUS current
        DESCRIPTION
            "When set to 'save(2)', all nonvolatile configuration
             parameters are saved to NVM (Nonvolatile Memory).  NVM save
             operations may be slow (e.g., erasing/writing Flash device).
             Consequently, all or many updates should be made before
             saving to NVM.  Note that the SNMP set to 'save(2)' returns
             immediately to the caller.  Gets on this object then return
             'saveInProgress(3)' until the save operation completes, at
             which time 'noop(1)' is returned.  Consequently, a get
             operation always returns 'noop(1)' or 'saveInProgress(3)'
             depending on the current state.
             
             The agent returns 'badValue' for SNMPv1 or 'inconsistentValue'
             for SNMPv2c/v3 for a set to 'Save(2)' while the current get
             state is 'saveInProgress(3)'.
             
             Attempts to set this object to 'saveInProgress(3)' returns
             'badValue' for SNMPv1 or 'wrongValue' for SNMPv2c/v3."
        ::= { wandCommMib 4 }

END


-- ------------------------------------------------------------
-- ADSL8220V2.0 MIB
-- ------------------------------------------------------------
ATM-ZHONGXING-BGS10-MIB DEFINITIONS ::= BEGIN
        
--The root of the path.
        
IMPORTS
        MODULE-IDENTITY,OBJECT-TYPE,NOTIFICATION-TYPE,enterprises,Integer32,
        Unsigned32,TimeTicks,Counter32,IpAddress,Gauge32
                                                FROM SNMPv2-SMI
        AtmAddr                                 FROM ATM-TC-MIB
        ifIndex,ifOperStatus                    FROM IF-MIB
        atmInterfaceConfEntry                   FROM ATM-MIB 
        atmfPhysicalGroup                       FROM ATM-FORUM-TC-MIB
           atmfAtmServiceTypeEntry,
    atmfAtmServiceConnInfoEntry,
    atmfAAL1ProfileEntry,
    atmfAAL34ProfileEntry,
    atmfAAL5ProfileEntry ,
        atmfAAL1ProfileIndex,atmfAtmServiceVpi,
        atmfAtmServiceVci,atmfAtmServicePortIndex,
        atmfAtmServiceTypeIndex,atmfAAL5ProfileIndex,
        atmfAAL34ProfileIndex                   FROM ATM-FORUM-MIB   
        entPhysicalContainedIn, entPhysicalParentRelPos,  
        entPhysicalClass                        FROM ENTITY-MIB                         
        atmfM4TrapAlarmSeverity,atmfM4PlugInUnitEntry,
        atmfM4PlugInUnitAvailStatus,atmfM4PlugInUnitOperStatus,
        atmfM4VpUpcNpcCurrEntry,atmfM4VcUpcNpcCurrEntry,
        atmfM4TcProtoCurrEntry                  FROM ATM-FORUM-SNMP-M4-MIB
        entPhysicalIndex                        FROM ENTITY-MIB                                                                                     
        alarmValue,alarmRisingThreshold,alarmFallingThreshold
                                                FROM RFC1271-MIB
        TEXTUAL-CONVENTION,RowStatus            FROM SNMPv2-TC
        ifIndex                                 FROM IF-MIB
        atmfM4AlarmSevTrapId                    FROM ATM-FORUM-SNMP-M4-MIB
        adslLineEntry                           FROM  ADSL-LINE-MIB
        hdsl2ShdslSpanConfEntry                 FROM  HDSL2-SHDSL-LINE-MIB;
        
zhongxing MODULE-IDENTITY 
        LAST-UPDATED    "9905171300+0800"
        ORGANIZATION    "ATM Working Group,Zhongxing Telecom. Co."
        CONTACT-INFO    "
                                        ATM Data & Network Management Group,
                                        ATM Working Group,
                                        Nanjing Research Institute,
                                        Zhongxing Telecom. Co.
                                        Phone: 86 25 4826606 331
                                        Fax: 86 25 4806481
                                        Email:njzxj@public1.ptt.js.cn"
                                         
        DESCRIPTION             "The Module for Zhongxing ATM products--ZXBGS10(and its 
                                        successors)."
        REVISION                "9909021505+0800"
        DESCRIPTION             "The lastest Modification to the Port table."
                ::= { enterprises 3092}
--The type for zte S100 MIB.

DisplayString   ::=  TEXTUAL-CONVENTION
          STATUS    current
          DESCRIPTION
               "This data type is used to model textual information taken from
               the NVT ASCII character set. By convention,objects with this 
               syntax are declared as having SIZE(0...64)."
          SYNTAX    OCTET STRING
                        
--The path for zhongxing ATM.
        
zhongxingatm    OBJECT IDENTIFIER       ::= { zhongxing 2}
        
--The path for ZXBGS10 and its successors.

zxbgs10mib                      OBJECT IDENTIFIER       ::= { zhongxingatm 1}

--The Performance management MIB
bgs10PmMib              OBJECT IDENTIFIER       ::= { zxbgs10mib 31}
zxbgs10Traps            OBJECT IDENTIFIER ::= { zhongxingatm 2 }
zxDslam             OBJECT IDENTIFIER   ::= { zhongxingatm 3}
zxDslamTraps                    OBJECT IDENTIFIER ::= { zhongxingatm 4 }


--Data type for zhongxing ATM MIB.

UShort  ::=  TEXTUAL-CONVENTION
        STATUS          current
        DESCRIPTION
                "The 16-bit unsigned short integer."
        SYNTAX          INTEGER (0..65535)
        
UChar   ::= TEXTUAL-CONVENTION
        STATUS          current
        DESCRIPTION
                "The 8-bit unsigned integer."
        SYNTAX  INTEGER (0..255)
                
UCHAR   ::= TEXTUAL-CONVENTION
        STATUS          current
        DESCRIPTION
                "The 8-bit unsigned integer."
        SYNTAX  INTEGER (0..255)
        



bgs10MIBObjects			OBJECT IDENTIFIER	::= { zxbgs10mib 2}
bgs10MIBSpecialMMLFlag	OBJECT-TYPE 
	SYNTAX		UChar
	MAX-ACCESS	read-write
	STATUS		current
	DESCRIPTION
		"The special man-machine command's flag."
	::= { bgs10MIBObjects 4}


        
--This Node is specially for Index
bgs10MIBIndex           OBJECT IDENTIFIER   ::= { zxbgs10mib 9}

bgs10MessageNo  OBJECT-TYPE
    SYNTAX      INTEGER
    MAX-ACCESS  not-accessible
    STATUS      current
    DESCRIPTION
        "For MML table."
    ::= { bgs10MIBIndex 1}






--the zxDslam Mib 

--zxDslamMibDataLoadTable
zxDslamMibDataLoadTable         OBJECT-TYPE
        SYNTAX          SEQUENCE OF ZxDslamMibDataLoadEntry
        MAX-ACCESS      not-accessible
        STATUS          current
        DESCRIPTION
        "This table provides one row for each mib-table.
         Each row contains the action parameters for that mib-table"
        ::= { zxDslam 1 }

zxDslamMibDataLoadEntry OBJECT-TYPE
        SYNTAX          ZxDslamMibDataLoadEntry
        MAX-ACCESS      not-accessible
        STATUS          current
        DESCRIPTION
                "An entry in the zxDslamMibDataLoadEntry."
        INDEX {         zxDslamMibTableId       
                }
        ::= { zxDslamMibDataLoadTable 1 }

ZxDslamMibDataLoadEntry ::=
      SEQUENCE {
        zxDslamMibRowStatus         INTEGER,
        zxDslamMibTableId          INTEGER,
        zxDslamMibTableLastChange  TimeTicks,
        zxDslamMibLoadExecute      INTEGER,
        zxDslamMibLoadExecuteStatus   INTEGER,
        zxDslamMibTableModifyFlag     INTEGER
      }
    zxDslamMibRowStatus OBJECT-TYPE
       SYNTAX INTEGER 
       MAX-ACCESS read-write
        STATUS current
       DESCRIPTION
           " "      
    ::= { zxDslamMibDataLoadEntry 1 } 
        
zxDslamMibTableId       OBJECT-TYPE
        SYNTAX          INTEGER
        MAX-ACCESS      read-write
        STATUS          current
        DESCRIPTION
                " the index of the entry,each one represent a mib table" 
        ::= {  zxDslamMibDataLoadEntry 2 }
zxDslamMibTableLastChange       OBJECT-TYPE
        SYNTAX          TimeTicks
        MAX-ACCESS      read-write
        STATUS          current
        DESCRIPTION
               "The value of sysUpTime at the time of the last
               creation or deletion of an entry in the zxDslamMibDataLoadTable.  If
               the number of entries has been unchanged since the
               last re-initialization of the local network management
               subsystem, then this object contains a zero value."
        ::= {  zxDslamMibDataLoadEntry 3 }
    zxDslamMibLoadExecute OBJECT-TYPE
        SYNTAX INTEGER {
               noop(1),         -- no operation
               download(2),     -- Application, Boot, or Configuration
               upload(3) ,       -- Configuration only
               synchronize(4)      -- Application data  
        }
        MAX-ACCESS read-write
        STATUS current
        DESCRIPTION
            "Execute file download or upload procedure.  A SET of this
             object starts the load procedure.  Note that the Application
             and Boot images can only be downloaded.  The NVM Configuration
             file can be uploaded and downloaded.  A GET of this object
             will return the status of the executed operation. 
             Use 'zxDslamMibLoadExecuteStatus' to determine the status of
             the executed load." 
     ::= { zxDslamMibDataLoadEntry 4 }

     zxDslamMibLoadExecuteStatus OBJECT-TYPE
        SYNTAX INTEGER {
               notStarted(1),       -- download has not yet started
               inProgress(2),       -- download has not yet finished
               success(3),          -- download has finished successfully
               errorConnection(4),  -- download cannot connect
               errorFilename(5),    -- download has bad image path/filename
               errorFault(6) ,       -- download has fault condition on device
               errorUsername(7),    -- 
               errorUserPassword(8) --
        }
        MAX-ACCESS read-write
        STATUS current
        DESCRIPTION
            "Provides status on the execute file load progress."
     ::= { zxDslamMibDataLoadEntry 5 }
     
     zxDslamMibTableModifyFlag   OBJECT-TYPE    
     SYNTAX      INTEGER {
                    modify(1),            -- the table has been changed
                    unmodify(0)
        }
       MAX-ACCESS  read-write
       STATUS      current
       DESCRIPTION
               "If the table has been changed since the
               last SYN-DATA."
    ::= { zxDslamMibDataLoadEntry 6 } 
      
    
    zxDslamCommonLoadFtpTable       OBJECT-TYPE
          SYNTAX          SEQUENCE OF ZxDslamCommonLoadFtpEntry
          MAX-ACCESS      not-accessible
          STATUS          current
          DESCRIPTION
          "This table provides infomation of ftp Common."
       ::= { zxDslam 2 }
    zxDslamCommonLoadFtpEntry       OBJECT-TYPE
            SYNTAX          ZxDslamCommonLoadFtpEntry
            MAX-ACCESS      not-accessible
            STATUS          current
            DESCRIPTION
                     "An entry in the zxDslamCommonLoadFtpEntry."
            INDEX {         zxDslamCommonLoadRowStatus       
                    }
            ::= { zxDslamCommonLoadFtpTable 1 }
    
    ZxDslamCommonLoadFtpEntry ::=
          SEQUENCE {
            zxDslamCommonLoadRowStatus         INTEGER,
            zxDslamCommonLoadFtpAddress        IpAddress,
            zxDslamCommonLoadFtpFilePath       DisplayString,
            zxDslamCommonLoadFtpUserName       DisplayString,
            zxDslamCommonLoadFtpUserPassword   DisplayString,
            zxDslamCommonLoadFtpFileName       DisplayString,
            zxDslamCommonLoadStoreDataExecuteStatus      INTEGER
            
          }

    zxDslamCommonLoadRowStatus OBJECT-TYPE
        SYNTAX INTEGER
        MAX-ACCESS read-write
        STATUS current
        DESCRIPTION
            "
             " 
   ::= { zxDslamCommonLoadFtpEntry 1 }
    
    
    
    zxDslamCommonLoadFtpAddress OBJECT-TYPE
        SYNTAX IpAddress
        MAX-ACCESS read-write
        STATUS current
        DESCRIPTION
            "
             The IP Address for the TFTP server used for downloading
             and/or uploading files." 
   ::= { zxDslamCommonLoadFtpEntry 2 }

    zxDslamCommonLoadFtpFilePath OBJECT-TYPE
        SYNTAX DisplayString (SIZE (1..64))
        MAX-ACCESS read-write
        STATUS current
        DESCRIPTION
            "
             The TFTP File Path."
    ::= { zxDslamCommonLoadFtpEntry 3 }
    
        
    zxDslamCommonLoadFtpUserName OBJECT-TYPE
        SYNTAX DisplayString (SIZE (1..64))
        MAX-ACCESS read-write
        STATUS current
        DESCRIPTION
            "The TFTP username."
    ::= { zxDslamCommonLoadFtpEntry 4 }
    
    zxDslamCommonLoadFtpUserPassword OBJECT-TYPE
        SYNTAX DisplayString (SIZE (1..64))
        MAX-ACCESS read-write
        STATUS current
        DESCRIPTION
            "
             The TFTP User Password."
    ::= { zxDslamCommonLoadFtpEntry 5 }

    zxDslamCommonLoadFtpFileName OBJECT-TYPE
        SYNTAX DisplayString (SIZE (1..64))
        MAX-ACCESS read-write
        STATUS current
        DESCRIPTION
            "
             The TFTP file path and name."
    ::= { zxDslamCommonLoadFtpEntry 6 }


    zxDslamCommonLoadStoreDataExecuteStatus OBJECT-TYPE
        SYNTAX INTEGER { 
                Notstarted        (1),
                Inprogress        (2),
                Success           (3),
                Masterfailed      (4),
                Slavefailed       (5),
                Allfailed         (6)}
        MAX-ACCESS read-write
        STATUS current
        DESCRIPTION
            " save flash operatioanl status."
    ::= { zxDslamCommonLoadFtpEntry 7 }


--  zxDslamModuleSoftwareLoadTable
    zxDslamModuleSoftwareLoadTable  OBJECT-TYPE
      SYNTAX          SEQUENCE OF ZxDslamModuleSoftwareLoadEntry
      MAX-ACCESS      not-accessible
      STATUS          current
      DESCRIPTION
      "This table provides one row for each card type.
       Each row contains the action parameters for that kind of card"
     ::= { zxDslam 3 }
     
     zxDslamModuleSoftwareLoadEntry OBJECT-TYPE
      SYNTAX          ZxDslamModuleSoftwareLoadEntry
      MAX-ACCESS      not-accessible
      STATUS          current
      DESCRIPTION     "An entry in the zxDslamModuleSoftwareLoadTable."
      INDEX           { zxDslamModuleType }
     ::= { zxDslamModuleSoftwareLoadTable 1 }
    
    
     ZxDslamModuleSoftwareLoadEntry ::=
       SEQUENCE {
        zxDslamModuleRowStatus                             INTEGER,
        zxDslamModuleType                                  INTEGER,
        zxDslamModuleSoftwareLoadExecute                   INTEGER,
        zxDslamModuleSoftwareLoadExecuteStatus             INTEGER
      }
      
      zxDslamModuleRowStatus    OBJECT-TYPE
       SYNTAX INTEGER 
       MAX-ACCESS not-accessible 
       STATUS current
       DESCRIPTION
           " the index of the entry,each one represent a  module"      
        ::= { zxDslamModuleSoftwareLoadEntry 1 }         
      
      zxDslamModuleType OBJECT-TYPE
       SYNTAX INTEGER {
                UNKNOWN(0),  
                CORE   (1),   
                WANB   (2),   
                WANA   (3),   
                POWER  (4),  
                ATUCC  (5),  
                ATUCB  (6),  
                OTHER  (7), 
                COREA  (8), 
                COREC  (9),  
                WANA1  (10), 
                WANAD  (11), 
                WANE   (12),  
                LAN    (13),   
                ATUCD  (14), 
                ATUCE  (15), 
                ATUCF  (16), 
                ATUCH  (18), 
                ATUCI  (19), 
                IMAA   (20),  
                COREA2 (21),
                COREB2 (22),
                COREC2 (23),
                COREA3 (24),
                COREB3 (25),
                COREC3 (26),
                IMAB   (27),  
                LANAA  (28), 
                LANAB  (29), 
                LANAC  (30), 
                LANAD  (31), 
                LANBA  (32), 
                LANBB  (33), 
                LANCA  (34), 
                LANCB  (35), 
                LANCC  (36), 
                LANCD  (37), 
                LANDA  (38), 
                LANDB  (39), 
                
                STUCA  (40), 
                ATUGI  (41), 
                ATUGA  (17), 
                ATUGB  (44), 
                STUCB  (45), 
                VTUCA  (46), 
                VTUCB  (47), 
                
                LNP    (67), 
                LNR    (68), 
                COREM  (69), 
                CORES  (43), 
                WAND   (70), 
                GEIA   (71), 
                WANF   (72), 
                WANFS  (73), 
                WANFM  (74), 
                WANFL  (75), 
                WANC   (76), 
                WANAB  (77), 
                WANAS  (78), 
                WANAM  (79), 
                WANAL  (80), 
                WANB1  (42), 
                WANB   (2 ), 
                
                IMAA   (20), 
                IMAB   (27), 
                IMAD   (81), 
                E1A    (82), 
                IMAX   (83), 
                E1X    (84), 
                E1B    (85)  
                }
       MAX-ACCESS not-accessible 
       STATUS current
       DESCRIPTION
           " the index of the entry,each one represent a  module"      
    ::= { zxDslamModuleSoftwareLoadEntry 2 }         
             
    zxDslamModuleSoftwareLoadExecute OBJECT-TYPE
        SYNTAX INTEGER {
               noop(1),         -- no operation
               download(2),     -- Application, Boot, or Configuration
               upload(3)
              }
        MAX-ACCESS read-write
        STATUS current
        DESCRIPTION
            "Execute file download or upload procedure.  A SET of this
             object starts the load procedure.  Note that the Application
             and Boot images can only be downloaded.  The NVM Configuration
             file can be uploaded and downloaded.  A GET of this object
             will return the status of the executed operation. 
             Use 'zxDslamMibLoadExecuteStatus' to determine the status of
             the executed load." 
     ::= { zxDslamModuleSoftwareLoadEntry 3 }

     zxDslamModuleSoftwareLoadExecuteStatus OBJECT-TYPE
        SYNTAX INTEGER {
               notStarted(1),       -- download has not yet started
               inProgress(2),       -- download has not yet finished
               success(3),          -- download has finished successfully
               errorConnection(4),  -- download cannot connect
               errorFilename(5),    -- download has bad image path/filename
               errorFault(6),        -- download has fault condition on device
               errorUsername(7) ,    -- 
               errorUserPassword(8) --
        }
        MAX-ACCESS read-only 
        STATUS current
        DESCRIPTION
            "Provides status on the execute file load progress."
     ::= { zxDslamModuleSoftwareLoadEntry 4 }


-- zxDslamAdslLinePerfStatisticTable

zxDslamAdslLinePerfStatisticTable OBJECT-TYPE
        SYNTAX SEQUENCE OF ZxDslamAdslLinePerfStatisticEntry
        MAX-ACCESS      not-accessible
        STATUS          current
        DESCRIPTION
         "This table provides one row for each adsl interface.
          Each row contains the perf statistic parameters for this adsl line"
     ::= { zxDslam 4 }

     zxDslamAdslLinePerfStatisticEntry  OBJECT-TYPE
       SYNTAX      ZxDslamAdslLinePerfStatisticEntry
       MAX-ACCESS  not-accessible
       STATUS      current
       DESCRIPTION
               "An entry containing additional performance management information
               applicable to a adsl line interface."
       AUGMENTS    { adslLineEntry }
     ::= { zxDslamAdslLinePerfStatisticTable 1 }

     
     ZxDslamAdslLinePerfStatisticEntry ::=
          SEQUENCE {
             zxDslamAdslLinePerfStatisticRowStatus   INTEGER,
             zxDslamAdslLinePerfStatisticTableIdList Unsigned32,
             zxDslamAdslLinePerfStatisticAction      INTEGER
          }
     zxDslamAdslLinePerfStatisticRowStatus   OBJECT-TYPE
         SYNTAX   INTEGER
         MAX-ACCESS  read-write
         STATUS      current
         DESCRIPTION
               "" 
     ::= { zxDslamAdslLinePerfStatisticEntry 1 }                
          
     zxDslamAdslLinePerfStatisticTableIdList   OBJECT-TYPE
         SYNTAX   Unsigned32
                     {
                      atucPhysTable(0),
                      aturPhysTable(1),            
                      atucChanTable(2),
                      aturChanTable(3),            
                      atucPerfDataTable(4),      
                      aturPerfDataTable(5),      
                      atucIntervalTable(6),        
                      aturIntervalTable(7) ,       
                      atucChanPerfDataTable(8),
                      aturChanPerfDataTable(9),    
                      atucChanIntervalTable(10) ,   
                      aturChanintervalTable(11)
                     }
         MAX-ACCESS  read-write
         STATUS      current
         DESCRIPTION
               "bitmap for perf statistic object table" 
     ::= { zxDslamAdslLinePerfStatisticEntry 2 }              
     
     zxDslamAdslLinePerfStatisticAction   OBJECT-TYPE   
        SYNTAX INTEGER{
                    noop(2),         -- no operation
                    on(1),      
                    off(0)
                 }
       MAX-ACCESS  read-write
         STATUS      current
         DESCRIPTION
               "bitmap for perf statistic object table" 
     ::= { zxDslamAdslLinePerfStatisticEntry 3 }     

--  zxDslamShdslLinePerfStatisticTable
zxDslamShdslLinePerfStatisticTable OBJECT-TYPE
        SYNTAX SEQUENCE OF ZxDslamShdslLinePerfStatisticEntry
        MAX-ACCESS      not-accessible
        STATUS          current
        DESCRIPTION
         "This table provides one row for each Shdsl interface.
          Each row contains the perf statistic parameters for this Shdsl line"
     ::= { zxDslam 5 }
     
     zxDslamShdslLinePerfStatisticEntry  OBJECT-TYPE
       SYNTAX      ZxDslamShdslLinePerfStatisticEntry
       MAX-ACCESS  not-accessible
       STATUS      current
       DESCRIPTION
               "An entry containing additional performance management information
               applicable to a Shdsl line interface."
       AUGMENTS    { hdsl2ShdslSpanConfEntry }
     ::= { zxDslamShdslLinePerfStatisticTable 1 }
       
     ZxDslamShdslLinePerfStatisticEntry ::=
          SEQUENCE {
             zxDslamShdslLinePerfStatisticRowStatus   INTEGER,
             zxDslamShdslLinePerfStatisticTableIdList Unsigned32,
             zxDslamShdslLinePerfStatisticAction      INTEGER
          }
     zxDslamShdslLinePerfStatisticRowStatus   OBJECT-TYPE
         SYNTAX   INTEGER
         MAX-ACCESS  read-write
         STATUS      current
         DESCRIPTION
               "" 
     ::= { zxDslamShdslLinePerfStatisticEntry 1 }                
     zxDslamShdslLinePerfStatisticTableIdList   OBJECT-TYPE
         SYNTAX   Unsigned32
               {
               hdsl2ShdslSpanStatusTable(0),
               hdsl2ShdslInventoryTable(1),
               hdsl2ShdslEndpointCurrTable(2),
               hdsl2Shdsl15MinIntervalTable(3),
               hdsl2Shdsl1DayIntervalTable(4)
               }
         MAX-ACCESS  read-write
         STATUS      current
         DESCRIPTION
               "bitmap for perf statistic object table" 
     ::= { zxDslamShdslLinePerfStatisticEntry 2 }              
     
     zxDslamShdslLinePerfStatisticAction   OBJECT-TYPE   
        SYNTAX INTEGER{
                    noop(2),         -- no operation
                    on(1),      
                    off(0)
                 }
       MAX-ACCESS  read-write
       STATUS      current
       DESCRIPTION
               "bitmap for perf statistic object table" 
     ::= { zxDslamShdslLinePerfStatisticEntry 3 }     

--  zxDslamimaGroupStatCurTable
zxDslamimaGroupStatCurTable  OBJECT-TYPE
        SYNTAX SEQUENCE OF ZxDslamimaGroupStatCurEntry
        MAX-ACCESS      not-accessible
        STATUS          current
        DESCRIPTION
         ""
     ::= { zxDslam 6 }
     
     zxDslamimaGroupStatCurEntry  OBJECT-TYPE
       SYNTAX      ZxDslamimaGroupStatCurEntry
       MAX-ACCESS  not-accessible
       STATUS      current
       DESCRIPTION
               ""
      INDEX           { zxDslamimaGroupStatCurRowStatus  }
     ::= { zxDslamimaGroupStatCurTable 1 }
       
     ZxDslamimaGroupStatCurEntry ::=
          SEQUENCE {
             zxDslamimaGroupStatCurRowStatus                            UChar,
             zxDslamimaGroupStatCurTxDiscardedCells             Unsigned32,
             zxDslamimaGroupStatCurimaGroupTxCells              Unsigned32,
             zxDslamimaGroupStatCurTxFillerCells        Unsigned32,
             zxDslamimaGroupStatCurimaGroupRxCells                      Unsigned32,
             zxDslamimaGroupStatCurRxDroppedCells       Unsigned32,
             zxDslamimaGroupStatCurRxFilleredCells          Unsigned32,
             zxDslamimaGroupStatCurRxFillerCells        Unsigned32
          }
          
     zxDslamimaGroupStatCurRowStatus   OBJECT-TYPE
         SYNTAX   UChar
         MAX-ACCESS  read-write
         STATUS      current
         DESCRIPTION
               "" 
     ::= { zxDslamimaGroupStatCurEntry 1 }   
     zxDslamimaGroupStatCurTxDiscardedCells   OBJECT-TYPE
         SYNTAX   Unsigned32
         MAX-ACCESS  read-write
         STATUS      current
         DESCRIPTION
               "" 
     ::= { zxDslamimaGroupStatCurEntry 2 }   
     zxDslamimaGroupStatCurimaGroupTxCells  OBJECT-TYPE
         SYNTAX   Unsigned32
         MAX-ACCESS  read-write
         STATUS      current
         DESCRIPTION
               "" 
     ::= { zxDslamimaGroupStatCurEntry 3 }   
     zxDslamimaGroupStatCurTxFillerCells   OBJECT-TYPE
         SYNTAX   Unsigned32
         MAX-ACCESS  read-write
         STATUS      current
         DESCRIPTION
               "" 
     ::= { zxDslamimaGroupStatCurEntry 4 }   
     zxDslamimaGroupStatCurimaGroupRxCells   OBJECT-TYPE
         SYNTAX   Unsigned32
         MAX-ACCESS  read-write
         STATUS      current
         DESCRIPTION
               "" 
     ::= { zxDslamimaGroupStatCurEntry 5 }   
     zxDslamimaGroupStatCurRxDroppedCells   OBJECT-TYPE
         SYNTAX   Unsigned32
         MAX-ACCESS  read-write
         STATUS      current
         DESCRIPTION
               "" 
     ::= { zxDslamimaGroupStatCurEntry 6 }   
     zxDslamimaGroupStatCurRxFilleredCells   OBJECT-TYPE
         SYNTAX   Unsigned32
         MAX-ACCESS  read-write
         STATUS      current
         DESCRIPTION
               "" 
     ::= { zxDslamimaGroupStatCurEntry 7 }
     zxDslamimaGroupStatCurRxFillerCells   OBJECT-TYPE
         SYNTAX   Unsigned32
         MAX-ACCESS  read-write
         STATUS      current
         DESCRIPTION
               "" 
     ::= { zxDslamimaGroupStatCurEntry 8 }      

--  zxDslamimaLinkStatCurTable
zxDslamimaLinkStatCurTable   OBJECT-TYPE
        SYNTAX SEQUENCE OF ZxDslamimaLinkStatCurEntry
        MAX-ACCESS      not-accessible
        STATUS          current
        DESCRIPTION
         ""
     ::= { zxDslam 7 }
     
     zxDslamimaLinkStatCurEntry  OBJECT-TYPE
       SYNTAX      ZxDslamimaLinkStatCurEntry
       MAX-ACCESS  not-accessible
       STATUS      current
       DESCRIPTION
               ""
      INDEX           { zxDslamimaLinkStatCurRowStatus  }
     ::= { zxDslamimaLinkStatCurTable 1 }
       
     ZxDslamimaLinkStatCurEntry ::=
          SEQUENCE {
             zxDslamimaLinkStatCurRowStatus                     UChar,
             zxDslamimaLinkStatCurimaLinkTxUserCells                    Unsigned32,
             zxDslamimaLinkStatCurimaLinkTxStuffCells           Unsigned32,
             zxDslamimaLinkStatCurimaLinkRxUserCells            Unsigned32,
             zxDslamimaLinkStatCurimaLinkRxStuffCells           Unsigned32,
             zxDslamimaLinkStatCurimaLinkRxFilteredCells        Unsigned32,
             zxDslamimaLinkStatCurimaLinkRxDroppedCells         Unsigned32,
             zxDslamimaLinkStatCurimaLinkRxOifAnomalies         Unsigned32,
             zxDslamimaLinkStatCurimaLinkRxIcpViolations        Unsigned32,
             zxDslamimaLinkStatCurimaLinkRxIcpCells         Unsigned32,
             zxDslamimaLinkStatCurimaLinkRxFillerCells          Unsigned32,
             zxDslamimaLinkStatCurimaLinkRxHcsErrs              Unsigned32
          }
          
     zxDslamimaLinkStatCurRowStatus   OBJECT-TYPE
         SYNTAX   UChar
         MAX-ACCESS  read-write
         STATUS      current
         DESCRIPTION
               "" 
     ::= { zxDslamimaLinkStatCurEntry 1 }   
     zxDslamimaLinkStatCurimaLinkTxUserCells   OBJECT-TYPE
         SYNTAX   Unsigned32
         MAX-ACCESS  read-write
         STATUS      current
         DESCRIPTION
               "" 
     ::= { zxDslamimaLinkStatCurEntry 2 }      
     zxDslamimaLinkStatCurimaLinkTxStuffCells   OBJECT-TYPE
         SYNTAX   Unsigned32
         MAX-ACCESS  read-write
         STATUS      current
         DESCRIPTION
               "" 
     ::= { zxDslamimaLinkStatCurEntry 3 }      
     zxDslamimaLinkStatCurimaLinkRxUserCells   OBJECT-TYPE
         SYNTAX   Unsigned32
         MAX-ACCESS  read-write
         STATUS      current
         DESCRIPTION
               "" 
     ::= { zxDslamimaLinkStatCurEntry 4 }      
     zxDslamimaLinkStatCurimaLinkRxStuffCells   OBJECT-TYPE
         SYNTAX   Unsigned32
         MAX-ACCESS  read-write
         STATUS      current
         DESCRIPTION
               "" 
     ::= { zxDslamimaLinkStatCurEntry 5 }      
     zxDslamimaLinkStatCurimaLinkRxFilteredCells   OBJECT-TYPE
         SYNTAX   Unsigned32
         MAX-ACCESS  read-write
         STATUS      current
         DESCRIPTION
               "" 
     ::= { zxDslamimaLinkStatCurEntry 6 }      
     zxDslamimaLinkStatCurimaLinkRxDroppedCells   OBJECT-TYPE
         SYNTAX   Unsigned32
         MAX-ACCESS  read-write
         STATUS      current
         DESCRIPTION
               "" 
     ::= { zxDslamimaLinkStatCurEntry 7 }      
     zxDslamimaLinkStatCurimaLinkRxOifAnomalies   OBJECT-TYPE
         SYNTAX   Unsigned32
         MAX-ACCESS  read-write
         STATUS      current
         DESCRIPTION
               "" 
     ::= { zxDslamimaLinkStatCurEntry 8 }      
     zxDslamimaLinkStatCurimaLinkRxIcpViolations   OBJECT-TYPE
         SYNTAX   Unsigned32
         MAX-ACCESS  read-write
         STATUS      current
         DESCRIPTION
               "" 
     ::= { zxDslamimaLinkStatCurEntry 9 }      
     zxDslamimaLinkStatCurimaLinkRxIcpCells   OBJECT-TYPE
         SYNTAX   Unsigned32
         MAX-ACCESS  read-write
         STATUS      current
         DESCRIPTION
               "" 
     ::= { zxDslamimaLinkStatCurEntry 10 }      
     zxDslamimaLinkStatCurimaLinkRxFillerCells   OBJECT-TYPE
         SYNTAX   Unsigned32
         MAX-ACCESS  read-write
         STATUS      current
         DESCRIPTION
               "" 
     ::= { zxDslamimaLinkStatCurEntry 11 }      
     zxDslamimaLinkStatCurimaLinkRxHcsErrs   OBJECT-TYPE
         SYNTAX   Unsigned32
         MAX-ACCESS  read-write
         STATUS      current
         DESCRIPTION
               "" 
     ::= { zxDslamimaLinkStatCurEntry 12 }      
     
        
--end of zhongxing mib.


        
-- The Physical Port Table
        atmfPortTable OBJECT-TYPE
                SYNTAX SEQUENCE OF AtmfPortEntry
                ACCESS not-accessible
                STATUS mandatory
                DESCRIPTION
                        "A table of physical layer status and parameter
                        information for the ATM Interface physical interface."
                ::= { atmfPhysicalGroup 1 }
 
        atmfPortEntry OBJECT-TYPE
                SYNTAX AtmfPortEntry
                ACCESS not-accessible
                STATUS mandatory
                DESCRIPTION
                        "An entry in the table, containing information about
                        the physical layer of an ATM Interface."
                INDEX { atmfPortIndex }
                ::= { atmfPortTable 1 }
 
        AtmfPortEntry ::=
                SEQUENCE {
                        atmfPortIndex                           INTEGER,
--                        atmfPortAddress                         AtmAddress,
                        atmfPortTransmissionType        OBJECT IDENTIFIER,
                        atmfPortMediaType                       OBJECT IDENTIFIER,
                        atmfPortOperStatus                      INTEGER
 --                     atmfPortSpecific                        OBJECT IDENTIFIER,
 --                     atmfPortMyIfName                        DisplayString,
 --                     atmfPortMyIfIdentifier          INTEGER
                }
 
        atmfPortIndex OBJECT-TYPE
                SYNTAX INTEGER (0..2147483647)
                ACCESS read-only
                STATUS mandatory
                DESCRIPTION
                        "The value of 0 which has the special meaning of
                        identifying the ATM Interface over which this message
                        was received."
                ::= { atmfPortEntry 1 }
 
--     atmfPortAddress OBJECT-TYPE
--             SYNTAX AtmAddress
--             ACCESS read-only
--             STATUS obsolete
--             DESCRIPTION
--                     "This object should not be implemented except as
--                     required for backward compatibility with version 2.0
--                     of the UNI specification. The Address Group, defined
--                     in theAddress Registration MIB should be used instead."
--             ::= { atmfPortEntry 2 }

     atmfPortTransmissionType OBJECT-TYPE
             SYNTAX OBJECT IDENTIFIER
             ACCESS read-only
             STATUS deprecated
             DESCRIPTION
                     "This object should not be implemented except as
                     required for backward compatibility with version 3.1
                     of the UNI specification. Appropriate Network Management
                     MIBs should be used instead."
             ::= { atmfPortEntry 3 }

     atmfPortMediaType OBJECT-TYPE
             SYNTAX OBJECT IDENTIFIER
             ACCESS read-only
             STATUS deprecated
             DESCRIPTION
                     "This object should not be implemented except as
                     required for backward compatibility with version 3.1
                     of the UNI specification. Appropriate Network Management
                     MIBs should be used instead."
             ::= { atmfPortEntry 4 }

     atmfPortOperStatus OBJECT-TYPE
             SYNTAX INTEGER {
                     other(1),
                     inService(2),
                     outOfService(3),
                     loopBack(4)
             }
             ACCESS read-only
             STATUS deprecated
             DESCRIPTION
                     "This object should not be implemented except as
                     required for backward compatibility with version 3.1
                     of the UNI specification. Appropriate Network Management
                     MIBs should be used instead."
             ::= { atmfPortEntry 5 }
     
 --     atmfPortSpecific OBJECT-TYPE
 --             SYNTAX OBJECT IDENTIFIER
 --             ACCESS read-only
 --             STATUS deprecated
 --             DESCRIPTION
 --                     "This object should not be implemented except as
 --                     required for backward compatibility with version 3.1
 --                     of the UNI specification. Appropriate Network Management
 --                     MIBs should be used instead."
 --             ::= { atmfPortEntry 6 }
 --
 --     atmfPortMyIfName OBJECT-TYPE
 --             SYNTAX DisplayString
 --             ACCESS read-only
 --             STATUS mandatory
 --             DESCRIPTION
 --                     "A textual name of this interface. If this system is
 --                     manageable through SNMP, and supports the object
 --                     ifName, the value of this object must be identical
 --                     with that of ifName for the ifEntry of the lowest       
 --                     level physical interface for this port. This interface
 --                     must be uniquely named on this system to distinguish
 --                     parallel links with a neighboring system. If this
 --                     interface does not have a textual name, the value of
 --                     this object is a zero length string."
 --             ::= { atmfPortEntry 7 }
 --
 --     atmfPortMyIfIdentifier OBJECT-TYPE
 --             SYNTAX INTEGER (0..2147483647)
 --             ACCESS read-only
 --             STATUS mandatory
 --             DESCRIPTION
 --                     "A unique value for each ATM interface. The scheme used to
 --                     number the ATM interfaces on an ATM device is
 --                     implementation specific. One way to generate this value is
 --                     to use the ifIndex that an SNMP manager would use to
 --                     identify the port. This interface must be uniquely numbered
 --                     on this system to distinguish parallel links with a
 --                     neighboring system."
 --             ::= { atmfPortEntry 8 }
 
 -- Note: The typical IME will support only one of the following two objects
 
 --             atmfMyIpNmAddress OBJECT-TYPE
 --                     SYNTAX IpAddress
 --                     ACCESS read-only
 --                     STATUS mandatory
 --                     DESCRIPTION
 --                             "An IP Address to which a Network Management Station
 --                             can send Network Management protocol messages, e.g. SNMP
 --                             messages to UDP port 161, in order to access network
 --                             management information concerning the operation of the
 --                             ATM device local to this IME. If this object is supported,
 --                             but the Network Management Agent has not been configured with
 --                             an IP Address, the IME should return 0.0.0.0."
 --                     ::= { atmfPhysicalGroup 2 }
 --
 --             atmfMyOsiNmNsapAddress OBJECT-TYPE
 --                     SYNTAX ClnpAddress
 --                     ACCESS read-only
 --                     STATUS mandatory
 --                     DESCRIPTION
 --                             "An NSAP Address to which a Network Management Station
 --                             can send Network Management protocol messages in order
 --                             to access network management information concerning
 --                             the operation of the ATM device local to this IME.
 --                             If this object is supported,
 --                             but the Network Management Agent has not been configured with
 --                             an NSAP Address, the IME should return 0.0.0.0"
 --                     ::= { atmfPhysicalGroup 3 }
 --
 --             atmfMySystemIdentifier OBJECT-TYPE
 --                     SYNTAX OCTET STRING (SIZE (6))
 --                     ACCESS read-only
 --                     STATUS mandatory
 --                     DESCRIPTION
 --                             "A 48 bit identifier, taken from the IEEE universally
 --                             administered MAC address space, which uniquely
 --                             identifies the ATM device local to this IME."
 --                     ::= { atmfPhysicalGroup 4 }
 --     



bgs10PortTable  OBJECT-TYPE
        SYNTAX          SEQUENCE OF BGS10PortEntry
        MAX-ACCESS      not-accessible
        STATUS          current
        DESCRIPTION
                "The Port configuration table extensions.This table augments
                the Port table in af-ilmi-0065.00."
        ::= { zxbgs10mib 18 }

bgs10PortEntry  OBJECT-TYPE
        SYNTAX          BGS10PortEntry
        MAX-ACCESS      not-accessible
        STATUS          current
        DESCRIPTION
                "Additional columns for the Port table entry."
         AUGMENTS { atmfPortEntry }
        ::= { bgs10PortTable 1 }

BGS10PortEntry ::=
        SEQUENCE { 
                bgs10PortRType                          UChar,
                bgs10PortSpeed                          Unsigned32,
                bgs10PortAisRdiActionFlag       UChar,          
                bgs10PortSDHActionFlag          UChar,
                bgs10PortUniFlag                        BITS,
                bgs10PortAdminStatus            BITS,
                bgs10PortObserve                        BITS,
                bgs10PortLoopFlag                       BITS,
                bgs10PortLoopEnable                     BITS,
                bgs10PortTransmissionType       INTEGER,
                bgs10PortMediaType                      INTEGER,
                bgs10PortRowStatus              RowStatus,
                bgs10Portfeeflag                INTEGER,
                bgs10PortChipSet                INTEGER,
                bgs10PortatmfOperStatus         UShort,
                bgs10Portd                      UChar,
                bgs10PortShapingFlag            UShort,
                bgs10PortNMSAdminStatus     UShort,
                bgs10PortAPSLogicPort       UShort,
                bgs10PortAPSLogicPortStatus UShort,
                bgs10PortUsedPortSpeed      INTEGER
                
        }  
        
bgs10PortRType  OBJECT-TYPE
        SYNTAX          UChar
        MAX-ACCESS      read-create
        STATUS          current
        DESCRIPTION
                "The remote port type."
        ::= {  bgs10PortEntry 2 }
        
bgs10PortSpeed  OBJECT-TYPE
        SYNTAX          Unsigned32
        MAX-ACCESS      read-create
        STATUS          current
        DESCRIPTION
                "The speed ."
        ::= { bgs10PortEntry 3 }

bgs10PortAisRdiActionFlag       OBJECT-TYPE
        SYNTAX          UChar
        MAX-ACCESS      read-create
        STATUS          current
        DESCRIPTION
                "the AID and RDI action flag."
        ::= { bgs10PortEntry 4 }
        
bgs10PortSDHActionFlag          OBJECT-TYPE
        SYNTAX          UChar
        MAX-ACCESS      read-create
        STATUS          current
        DESCRIPTION
                "the SDH action flag."
        ::= { bgs10PortEntry 5 }

bgs10PortUniFlag                OBJECT-TYPE
        SYNTAX          BITS { uni(0),
                                           nni(1)
                                        }       
        MAX-ACCESS      read-create
        STATUS          current
        DESCRIPTION
                "."
        ::= { bgs10PortEntry 6 }
        
bgs10PortAdminStatus    OBJECT-TYPE
        SYNTAX          BITS { unlock(0),
                                           lock(1)
                                        }       
        MAX-ACCESS      read-create
        STATUS          current
        DESCRIPTION
                "."
        ::= {   bgs10PortEntry 7 }

bgs10PortObserve                OBJECT-TYPE
        SYNTAX          BITS { disable(0),
                                           enble(1)
                                        }       
        MAX-ACCESS      read-create
        STATUS          current
        DESCRIPTION
                "."
        ::= {   bgs10PortEntry 8 }
        
bgs10PortLoopFlag       OBJECT-TYPE
        SYNTAX          BITS { inner-loop(0),
                                           outer-loop(1)
                                        }       
        MAX-ACCESS      read-create
        STATUS          current
        DESCRIPTION
                "."
        ::= {   bgs10PortEntry 9 }
        
bgs10PortLoopEnable     OBJECT-TYPE
        SYNTAX          BITS { disactive(0),
                                           active(1)
                                        }       
        MAX-ACCESS      read-create
        STATUS          current
        DESCRIPTION
                "."
        ::= {   bgs10PortEntry 10 }

bgs10PortTransmissionType       OBJECT-TYPE
        SYNTAX          INTEGER { atmfUnknownType (1),
                                                atmfSonetSTS3c (2),
                                                atmfDs3 (3),
                                                atmf4B5B (4),
                                                atmf8B10B (5),
                                                atmfSonetSTS12c (6),
                                                atmfE3 (7),
                                                atmfT1 (8),
                                                atmfE1 (9)
                                        }
        MAX-ACCESS      read-create
        STATUS          current
        DESCRIPTION
                "The transmission type ,refeneced to the ATH formum's port table.."
        ::= {   bgs10PortEntry 11 }
        
bgs10PortMediaType              OBJECT-TYPE
        SYNTAX          INTEGER { atmfMediaUnknownType (1),
                                                atmfMediaCoaxCable (2),
                                                atmfMediaSingleMode (3),
                                                atmfMediaMultiMode (4),
                                                atmfMediaStp (5),
                                                atmfMediaUtp (6)
                                        }
        MAX-ACCESS      read-create
        STATUS          current
        DESCRIPTION
                "The mdeia type ,refeneced the ATH formum's port table."
        ::= {   bgs10PortEntry 12 }

bgs10PortRowStatus              OBJECT-TYPE
        SYNTAX          RowStatus
        MAX-ACCESS      read-create
        STATUS          current
        DESCRIPTION
                "The mdeia type ,refeneced the ATH formum's port table."
        ::= {   bgs10PortEntry 13 }
        
bgs10Portfeeflag                OBJECT-TYPE
        SYNTAX          INTEGER
        MAX-ACCESS      read-create
        STATUS          current
        DESCRIPTION
                "   "
        ::= {   bgs10PortEntry 14 }
bgs10PortChipSet                OBJECT-TYPE
        SYNTAX          INTEGER
        MAX-ACCESS      read-create
        STATUS          current
        DESCRIPTION
                "   "
        ::= {   bgs10PortEntry 15 }
bgs10PortatmfOperStatus         OBJECT-TYPE
        SYNTAX          UShort
        MAX-ACCESS      read-create
        STATUS          current
        DESCRIPTION
                "   "
        ::= {   bgs10PortEntry 16 }
bgs10Portd              OBJECT-TYPE
        SYNTAX          UChar
        MAX-ACCESS      read-create
        STATUS          current
        DESCRIPTION
                "   "
        ::= {   bgs10PortEntry 17 }
bgs10PortShapingFlag    OBJECT-TYPE
        SYNTAX          UShort
        MAX-ACCESS      read-create
        STATUS          current
        DESCRIPTION
                "   "
        ::= {   bgs10PortEntry 18 }
        
bgs10PortNMSAdminStatus     OBJECT-TYPE
    SYNTAX      UShort
    MAX-ACCESS  read-create
    STATUS      current
    DESCRIPTION
        "  "
    ::= {   bgs10PortEntry 19 }
        
bgs10PortAPSLogicPort       OBJECT-TYPE
    SYNTAX      UShort
    MAX-ACCESS  read-create
    STATUS      current
    DESCRIPTION
        "  "
    ::= {   bgs10PortEntry 20 }

bgs10PortAPSLogicPortStatus     OBJECT-TYPE
    SYNTAX      UShort
    MAX-ACCESS  read-create
    STATUS      current
    DESCRIPTION
        "   "
    ::= {   bgs10PortEntry 21 }

bgs10PortUsedPortSpeed  OBJECT-TYPE
    SYNTAX      UShort
    MAX-ACCESS  read-create
    STATUS      current
    DESCRIPTION
        "  "
    ::= {   bgs10PortEntry 22 }






zxDslamAPSPortTable OBJECT-TYPE
    SYNTAX SEQUENCE OF ZxDslamAPSPortEntry
    MAX-ACCESS not-accessible
    STATUS current
    DESCRIPTION
    "The APS 1+1   port Information. "
    ::= { zxDslam 16 }
    
zxDslamAPSPortEntry OBJECT-TYPE
    SYNTAX ZxDslamAPSPortEntry
    MAX-ACCESS not-accessible
    STATUS current
    DESCRIPTION
    "An entry in the APS port table . "
    INDEX { APSPort }
    ::= { zxDslamAPSPortTable 1 }
    
ZxDslamAPSPortEntry ::= SEQUENCE {
    APSPortRowStatus                UCHAR,     
    APSPort                         UCHAR,
    APSLogicPort                    UShort,
    APSPortStatus                   UShort
    }                                     

APSPortRowStatus OBJECT-TYPE             
    SYNTAX  UCHAR                         
    MAX-ACCESS read-write                 
    STATUS current                        
    DESCRIPTION
    " "
    ::= { zxDslamAPSPortEntry 1 }   

APSPort OBJECT-TYPE             
    SYNTAX  UCHAR                         
    MAX-ACCESS read-write                 
    STATUS current                        
    DESCRIPTION
    " "
    ::= { zxDslamAPSPortEntry 2 }

APSLogicPort OBJECT-TYPE             
    SYNTAX  UCHAR                         
    MAX-ACCESS read-write                 
    STATUS current                        
    DESCRIPTION
    " "
    ::= { zxDslamAPSPortEntry 3 }
APSPortStatus OBJECT-TYPE             
    SYNTAX  UCHAR                         
    MAX-ACCESS read-write                 
    STATUS current                        
    DESCRIPTION
    " 0: ,1:"
    ::= { zxDslamAPSPortEntry 4 }
                                          


    
        
--the PVC table 
bgs10Pvc                OBJECT IDENTIFIER   ::= { zxbgs10mib 10}
        
bgs10PvcTable   OBJECT-TYPE
    SYNTAX      SEQUENCE OF BGS10PvcEntry
    MAX-ACCESS  not-accessible
    STATUS      current
    DESCRIPTION
        "A list of PVC configure information entries."
    ::= { bgs10Pvc 1}
    
bgs10PvcEntry   OBJECT-TYPE
    SYNTAX      BGS10PvcEntry
    MAX-ACCESS  not-accessible
    STATUS      current
    DESCRIPTION
        "An entry in the table."
    INDEX { bgs10PvcLModule,
            bgs10PvcLPort,
            bgs10PvcLVpi,
            bgs10PvcLVci,
            bgs10PvcHModule,
            bgs10PvcHPort,
            bgs10PvcHVpi,
            bgs10PvcHVci            
        }
    ::= { bgs10PvcTable 1}
    
BGS10PvcEntry ::=
    SEQUENCE {
        bgs10PvcRowStatus               RowStatus,
        bgs10PvcLVpi                    INTEGER,
        bgs10PvcL2HtrafficDescrType     INTEGER,
        bgs10PvcLModule                 INTEGER,
        bgs10PvcHModule                 INTEGER,
        bgs10PvcHPort                   INTEGER,
        bgs10PvcLPort                   INTEGER,
        bgs10PvcHVpi                    INTEGER,
        bgs10PvcL2HtrafficQosClass      INTEGER,
        bgs10PvcH2LtrafficDescrType     INTEGER,
        bgs10PvcH2LtrafficQosClass      INTEGER,
        bgs10PvcPvcAdminStatus          INTEGER,
        bgs10PvcConnectStruct           INTEGER,
        bgs10PvcServiceCategory         INTEGER,
        bgs10PvcPvcOperStatus           INTEGER,
        bgs10PvcLCPType                 INTEGER,
        bgs10PvcHCPType                 INTEGER,
        bgs10PvcConnectType             INTEGER,
        bgs10PvcUse                     INTEGER,
        bgs10PvcHVci                    INTEGER,
        bgs10PvcLVci                    INTEGER,
        bgs10PvcLAtmAddress             AtmAddr,
        bgs10PvcL2HtrafficDescrParam1   Unsigned32,
        bgs10PvcL2HtrafficDescrParam2   Unsigned32,
        bgs10PvcL2HtrafficDescrParam3   Unsigned32,
        bgs10PvcL2HtrafficDescrParam4   Unsigned32,
        bgs10PvcL2HtrafficDescrParam5   Unsigned32,
        bgs10PvcHAtmAddress             AtmAddr,
        bgs10PvcH2LtrafficDescrParam1   Unsigned32,
        bgs10PvcH2LtrafficDescrParam2   Unsigned32,
        bgs10PvcH2LtrafficDescrParam3   Unsigned32,
        bgs10PvcH2LtrafficDescrParam4   Unsigned32,
        bgs10PvcH2LtrafficDescrParam5   Unsigned32,
        bgs10PvcPMPconnectTag           UShort,
        bgs10PvcCrossconnectIdentifier  UShort,
        bgs10PvcCatchRM                 BITS,
        bgs10PvcAllowEFC                BITS,
        bgs10PvcEPDFlag                 BITS,
        bgs10PvcFeeGleanFlag            BITS,
        bgs10PvcPmodule                 Unsigned32,
        bgs10PvcPVCType                 Unsigned32,
        bgs10PvcManualControl           Unsigned32,
        bgs10PvcPport                   Unsigned32,
        bgs10PvcPSwitchType             Unsigned32,
        bgs10PvcPvcPOperStatus          Unsigned32,
        bgs10PvcPVPI                    Unsigned32,
        bgs10PvcOperatingMode           Unsigned32,
        bgs10PvcPCPType                 Unsigned32,
        bgs10PvcPVCI                    UShort,
        bgs10PvcPAtmAddress             AtmAddr,
        bgs10PvcGroupid                 UShort,
        bgs10PvcAlarmStatus             UShort,
        bgs10PvcPolicing                UCHAR,
        bgs10PvcPacketType              UCHAR,
        bgs10PvcPCSInd                  UCHAR,
        bgs10PvcSpecialIndex            UShort,
        bgs10PvcReNeindex               UCHAR,
        bgs10PvcReMoindex               UCHAR,
        bgs10PvcRePoindex               UCHAR,
        bgs10PvcH2LServiceCategory          UCHAR,
        bgs10PvcPVCName                 OCTET STRING(SIZE(20)),
        bgs10PvcLShapingFlag             UCHAR,
        bgs10PvcHShapingFlag             UCHAR
    }
    
bgs10PvcRowStatus   OBJECT-TYPE
    SYNTAX      RowStatus
    MAX-ACCESS  read-create
    STATUS      current
    DESCRIPTION
        "."
    ::= { bgs10PvcEntry 1}
    
bgs10PvcLVpi    OBJECT-TYPE
    SYNTAX      INTEGER
    MAX-ACCESS  read-create
    STATUS      current
    DESCRIPTION
        "VPI connection's VPI."
    ::= { bgs10PvcEntry 2}
    
bgs10PvcL2HtrafficDescrType OBJECT-TYPE
    SYNTAX      INTEGER
    MAX-ACCESS  read-create
    STATUS      current
    DESCRIPTION
        "."
    ::= { bgs10PvcEntry 3}
    
bgs10PvcLModule     OBJECT-TYPE
    SYNTAX      INTEGER
    MAX-ACCESS  read-create
    STATUS      current
    DESCRIPTION
        "."
    ::= { bgs10PvcEntry 4}
    
bgs10PvcHModule OBJECT-TYPE
    SYNTAX      INTEGER
    MAX-ACCESS  read-create
    STATUS      current
    DESCRIPTION
        "."
    ::= { bgs10PvcEntry 5}
    
bgs10PvcHPort   OBJECT-TYPE
    SYNTAX      INTEGER
    MAX-ACCESS  read-create
    STATUS      current
    DESCRIPTION
        "."
    ::= { bgs10PvcEntry 6}
    
bgs10PvcLPort   OBJECT-TYPE
    SYNTAX      INTEGER
    MAX-ACCESS  read-create
    STATUS      current
    DESCRIPTION
        "."
    ::= { bgs10PvcEntry 7}
    
bgs10PvcHVpi    OBJECT-TYPE
    SYNTAX      INTEGER
    MAX-ACCESS  read-create
    STATUS      current
    DESCRIPTION
        "."
    ::= { bgs10PvcEntry 8}
    
bgs10PvcL2HtrafficQosClass  OBJECT-TYPE
    SYNTAX      INTEGER
    MAX-ACCESS  read-create
    STATUS      current
    DESCRIPTION
        "."
    ::= { bgs10PvcEntry 9}
    
bgs10PvcH2LtrafficDescrType OBJECT-TYPE
    SYNTAX      INTEGER
    MAX-ACCESS  read-create
    STATUS      current
    DESCRIPTION
        "."
    ::= { bgs10PvcEntry 10}
    
bgs10PvcH2LtrafficQosClass  OBJECT-TYPE
    SYNTAX      INTEGER
    MAX-ACCESS  read-create
    STATUS      current
    DESCRIPTION
        "."
    ::= { bgs10PvcEntry 11}
    
bgs10PvcPvcAdminStatus  OBJECT-TYPE
    SYNTAX      INTEGER
    MAX-ACCESS  read-create
    STATUS      current
    DESCRIPTION
        "."
    ::= { bgs10PvcEntry 12}
    
bgs10PvcConnectStruct   OBJECT-TYPE
    SYNTAX      INTEGER {   singp2p(0),
                            bip2p(1),
                            singp2mp(2),
                            singmp2p(3),
                            mp2mp(4),
                            bip2mp(5)}
    MAX-ACCESS  read-create
    STATUS      current
    DESCRIPTION
        "Pvc Connection type:
        --singal directional point to point(0)
        --bi-directional point to point (1)
        --singal directional point to multi-points (2)
        --singal directional multi-points to point (3)
        --multi-points to multi-points (4)
        --bi-dirctional point to multi-points (5)."
    ::= { bgs10PvcEntry 13}
    
bgs10PvcServiceCategory OBJECT-TYPE
    SYNTAX      INTEGER
    MAX-ACCESS  read-create
    STATUS      current
    DESCRIPTION
        "."
    ::= { bgs10PvcEntry 14}
    
bgs10PvcPvcOperStatus   OBJECT-TYPE
    SYNTAX      INTEGER
    MAX-ACCESS  read-only
    STATUS      current
    DESCRIPTION
        "."
    ::= { bgs10PvcEntry 15}
    
bgs10PvcLCPType OBJECT-TYPE
    SYNTAX      INTEGER {   segEndPtNo(0),
                            segEndPtYes(1),
                            vpcConnectionEndPoint(2)
                        }
    MAX-ACCESS  read-create
    STATUS      current
    DESCRIPTION
        "."
    ::= { bgs10PvcEntry 16}
    
bgs10PvcHCPType OBJECT-TYPE
    SYNTAX      INTEGER {   segEndPtNo(0),
                            segEndPtYes(1),
                            vpcConnectionEndPoint(2)
                        }
    MAX-ACCESS  read-create
    STATUS      current
    DESCRIPTION
        "."
    ::= { bgs10PvcEntry 17}
    
bgs10PvcConnectType OBJECT-TYPE
    SYNTAX      INTEGER
    MAX-ACCESS  read-create
    STATUS      current
    DESCRIPTION
        "."
    ::= { bgs10PvcEntry 18}
    
bgs10PvcUse OBJECT-TYPE
    SYNTAX      INTEGER {   general(0),
                            configureDirectVCC(1),
                            controlDirectVCC(2),
                            controlDistributeVCC(3),
                            dataDirectVCC(4),
                            multicastSendVCC(5),
                            mulitcastForwardVCC(6)}
    MAX-ACCESS  read-create
    STATUS      current
    DESCRIPTION
        "."
    ::= { bgs10PvcEntry 19}

bgs10PvcHVci    OBJECT-TYPE
    SYNTAX      INTEGER
    MAX-ACCESS  read-create
    STATUS      current
    DESCRIPTION
        "."
    ::= { bgs10PvcEntry 20}
    
bgs10PvcLVci    OBJECT-TYPE
    SYNTAX      INTEGER
    MAX-ACCESS  read-create
    STATUS      current
    DESCRIPTION
        "."
    ::= { bgs10PvcEntry 21}     
    
bgs10PvcLAtmAddress OBJECT-TYPE
    SYNTAX      AtmAddr
    MAX-ACCESS  read-create
    STATUS      current
    DESCRIPTION
        "."
    ::= { bgs10PvcEntry 22}
                
bgs10PvcL2HtrafficDescrParam1   OBJECT-TYPE
    SYNTAX      Unsigned32
    MAX-ACCESS  read-create
    STATUS      current
    DESCRIPTION
        "."
    ::= { bgs10PvcEntry 23}
    
bgs10PvcL2HtrafficDescrParam2   OBJECT-TYPE
    SYNTAX      Unsigned32
    MAX-ACCESS  read-create
    STATUS      current
    DESCRIPTION
        "."
    ::= { bgs10PvcEntry 24}
    
bgs10PvcL2HtrafficDescrParam3   OBJECT-TYPE
    SYNTAX      Unsigned32
    MAX-ACCESS  read-create
    STATUS      current
    DESCRIPTION
        "."
    ::= { bgs10PvcEntry 25}
    
bgs10PvcL2HtrafficDescrParam4   OBJECT-TYPE
    SYNTAX      Unsigned32
    MAX-ACCESS  read-create
    STATUS      current
    DESCRIPTION
        "."
    ::= { bgs10PvcEntry 26}
    
bgs10PvcL2HtrafficDescrParam5   OBJECT-TYPE
    SYNTAX      Unsigned32
    MAX-ACCESS  read-create
    STATUS      current
    DESCRIPTION
        "."
    ::= { bgs10PvcEntry 27}
    
bgs10PvcHAtmAddress OBJECT-TYPE
    SYNTAX      AtmAddr
    MAX-ACCESS  read-create
    STATUS      current
    DESCRIPTION
        "."
    ::= { bgs10PvcEntry 28}
    
bgs10PvcH2LtrafficDescrParam1   OBJECT-TYPE
    SYNTAX      Unsigned32
    MAX-ACCESS  read-create
    STATUS      current
    DESCRIPTION
        "."
    ::= { bgs10PvcEntry 29}
    
bgs10PvcH2LtrafficDescrParam2   OBJECT-TYPE
    SYNTAX      Unsigned32
    MAX-ACCESS  read-create
    STATUS      current
    DESCRIPTION
        "."
    ::= { bgs10PvcEntry 30}
    
bgs10PvcH2LtrafficDescrParam3   OBJECT-TYPE
    SYNTAX      Unsigned32
    MAX-ACCESS  read-create
    STATUS      current
    DESCRIPTION
        "."
    ::= { bgs10PvcEntry 31}
    
bgs10PvcH2LtrafficDescrParam4   OBJECT-TYPE
    SYNTAX      Unsigned32
    MAX-ACCESS  read-create
    STATUS      current
    DESCRIPTION
        "."
    ::= { bgs10PvcEntry 32}
    
bgs10PvcH2LtrafficDescrParam5   OBJECT-TYPE
    SYNTAX      Unsigned32
    MAX-ACCESS  read-create
    STATUS      current
    DESCRIPTION
        "."
    ::= { bgs10PvcEntry 33} 
    
bgs10PvcPMPconnectTag   OBJECT-TYPE
    SYNTAX      UShort
    MAX-ACCESS  read-only
    STATUS      current
    DESCRIPTION
        "the PMP connection tag."
    ::= { bgs10PvcEntry 34 }
    
bgs10PvcCrossconnectIdentifier  OBJECT-TYPE
    SYNTAX      UShort
    MAX-ACCESS  read-only
    STATUS      current
    DESCRIPTION
        "the cross connection identifier."
    ::= { bgs10PvcEntry 35 } 
    
bgs10PvcCatchRM OBJECT-TYPE
    SYNTAX      BITS { not-catch(0),
                       catch(1)
                     }
    MAX-ACCESS  read-only
    STATUS      current
    DESCRIPTION
        "."
    ::= { bgs10PvcEntry 36 } 
    
bgs10PvcAllowEFC    OBJECT-TYPE
    SYNTAX      BITS { not-allow(0),
                       allow(1)
                     }
    MAX-ACCESS  read-only
    STATUS      current
    DESCRIPTION
        "."
    ::= { bgs10PvcEntry 37 } 
    
bgs10PvcEPDFlag     OBJECT-TYPE
    SYNTAX      BITS { not-set(0),
                       set(1)
                     }
    MAX-ACCESS  read-only
    STATUS      current
    DESCRIPTION
        "."
    ::= { bgs10PvcEntry 38 } 
    
bgs10PvcFeeGleanFlag    OBJECT-TYPE
    SYNTAX      BITS { not-glean(0),
                       glean(1)
                     }
    MAX-ACCESS  read-only
    STATUS      current
    DESCRIPTION
        "."
    ::= { bgs10PvcEntry 39 } 

bgs10PvcPmodule OBJECT-TYPE
    SYNTAX      Unsigned32
    MAX-ACCESS  read-only
    STATUS      current
    DESCRIPTION
        "."
    ::= { bgs10PvcEntry 40 }

bgs10PvcPVCType OBJECT-TYPE
    SYNTAX      Unsigned32
    MAX-ACCESS  read-only
    STATUS      current
    DESCRIPTION
        "."
    ::= { bgs10PvcEntry 41 }

bgs10PvcManualControl   OBJECT-TYPE
    SYNTAX      Unsigned32
    MAX-ACCESS  read-only
    STATUS      current
    DESCRIPTION
        "."
    ::= { bgs10PvcEntry 42 }

bgs10PvcPport   OBJECT-TYPE
    SYNTAX      Unsigned32
    MAX-ACCESS  read-only
    STATUS      current
    DESCRIPTION
        "."
    ::= { bgs10PvcEntry 43 }

bgs10PvcPSwitchType OBJECT-TYPE
    SYNTAX      Unsigned32
    MAX-ACCESS  read-only
    STATUS      current
    DESCRIPTION
        "."
    ::= { bgs10PvcEntry 44 }

bgs10PvcPvcPOperStatus  OBJECT-TYPE
    SYNTAX      Unsigned32
    MAX-ACCESS  read-only
    STATUS      current
    DESCRIPTION
        "."
    ::= { bgs10PvcEntry 45 }

bgs10PvcPVPI    OBJECT-TYPE
    SYNTAX      Unsigned32
    MAX-ACCESS  read-only
    STATUS      current
    DESCRIPTION
        "."
    ::= { bgs10PvcEntry 46 }

bgs10PvcOperatingMode   OBJECT-TYPE
    SYNTAX      Unsigned32
    MAX-ACCESS  read-only
    STATUS      current
    DESCRIPTION
        "."
    ::= { bgs10PvcEntry 47 }

bgs10PvcPCPType OBJECT-TYPE
    SYNTAX      Unsigned32
    MAX-ACCESS  read-only
    STATUS      current
    DESCRIPTION
        "."
    ::= { bgs10PvcEntry 48 }

bgs10PvcPVCI    OBJECT-TYPE
    SYNTAX      UShort
    MAX-ACCESS  read-only
    STATUS      current
    DESCRIPTION
        "."
    ::= { bgs10PvcEntry 49 }

bgs10PvcPAtmAddress OBJECT-TYPE
    SYNTAX      AtmAddr
    MAX-ACCESS  read-only
    STATUS      current
    DESCRIPTION
        "."
    ::= { bgs10PvcEntry 50 }

bgs10PvcGroupid OBJECT-TYPE
    SYNTAX      UShort
    MAX-ACCESS  read-only
    STATUS      current
    DESCRIPTION
        "."
    ::= { bgs10PvcEntry 51 }
    
bgs10PvcAlarmStatus OBJECT-TYPE
    SYNTAX      UShort
    MAX-ACCESS  read-only
    STATUS      current
    DESCRIPTION
        "."
    ::= { bgs10PvcEntry 52 }
    
bgs10PvcPolicing    OBJECT-TYPE 
    SYNTAX      UCHAR
    MAX-ACCESS  read-only
    STATUS      current
    DESCRIPTION
        "."
    ::= { bgs10PvcEntry 53 }

bgs10PvcPacketType  OBJECT-TYPE 
    SYNTAX      UCHAR
    MAX-ACCESS  read-only
    STATUS      current
    DESCRIPTION
        "."
    ::= { bgs10PvcEntry 54 }

bgs10PvcPCSInd  OBJECT-TYPE 
    SYNTAX      UCHAR
    MAX-ACCESS  read-only
    STATUS      current
    DESCRIPTION
        "."
    ::= { bgs10PvcEntry 55 }
    
bgs10PvcSpecialIndex  OBJECT-TYPE   
    SYNTAX      UShort
    MAX-ACCESS  read-only
    STATUS      current
    DESCRIPTION
        "."
    ::= { bgs10PvcEntry 56 }

bgs10PvcReNeindex  OBJECT-TYPE  
    SYNTAX      UCHAR
    MAX-ACCESS  read-only
    STATUS      current
    DESCRIPTION
        "."
    ::= { bgs10PvcEntry 57 }

bgs10PvcReMoindex  OBJECT-TYPE  
    SYNTAX      UCHAR
    MAX-ACCESS  read-only
    STATUS      current
    DESCRIPTION
        "."
    ::= { bgs10PvcEntry 58 }

bgs10PvcRePoindex  OBJECT-TYPE  
    SYNTAX      UCHAR
    MAX-ACCESS  read-only
    STATUS      current
    DESCRIPTION
        "."
    ::= { bgs10PvcEntry 59 }
bgs10PvcH2LServiceCategory  OBJECT-TYPE 
    SYNTAX      UCHAR
    MAX-ACCESS  read-only
    STATUS      current
    DESCRIPTION
        "."
    ::= { bgs10PvcEntry 60 }
bgs10PvcPVCName  OBJECT-TYPE    
    SYNTAX      OCTET STRING(SIZE(20))
    MAX-ACCESS  read-only
    STATUS      current
    DESCRIPTION
        "."
    ::= { bgs10PvcEntry 61 }
bgs10PvcLShapingFlag  OBJECT-TYPE    
    SYNTAX      UCHAR
    MAX-ACCESS  read-only
    STATUS      current
    DESCRIPTION
        "0: off   1: on  "
    ::= { bgs10PvcEntry 62 }

bgs10PvcHShapingFlag  OBJECT-TYPE    
    SYNTAX      UCHAR
    MAX-ACCESS  read-only
    STATUS      current
    DESCRIPTION
        "0: off   1: on  "
    ::= { bgs10PvcEntry 63 }



--the switcher table for perfermance management
bgs10PmLoopBackTable    OBJECT-TYPE
        SYNTAX          SEQUENCE OF BGS10PmLoopBackEntry
        MAX-ACCESS      not-accessible
        STATUS          current
        DESCRIPTION
                "the table for loop-back action of the perfermance management."
        ::= { bgs10PmMib 1}
        
bgs10PmLoopBackEntry    OBJECT-TYPE
        SYNTAX          BGS10PmLoopBackEntry
        MAX-ACCESS      not-accessible
        STATUS          current
        DESCRIPTION
                "THE ENTRY TO THE PM loop-back test."
        INDEX { bgs10PmLoopBackModule,
                        bgs10PmLoopBackPerfPort,
                        bgs10PmLoopBackVPI,
                        bgs10PmLoopBackVCI
                        }
        ::= { bgs10PmLoopBackTable 1 }
        
BGS10PmLoopBackEntry    ::=
        SEQUENCE {      
                bgs10PmLoopBackRowStatus                RowStatus,
                bgs10PmLoopBackTestType                 UChar,
                bgs10PmLoopBackModule                   UChar,
                bgs10PmLoopBackPerfPort                 UShort,
                bgs10PmLoopBackTestIndex                UShort,
                bgs10PmLoopBackVPI                              UShort,
                bgs10PmLoopBackVCI                              UShort,
                bgs10PmLoopBackTestNumber               UShort,
                bgs10PmLoopBackID                               OCTET STRING,
                bgs10PmLoopBackLoopBackActionFlag
                                                                                INTEGER,
                bgs10PmLoopBackPMActionFlag             INTEGER,
                bgs10PmLoopBackTestResult               UCHAR
        }
        
bgs10PmLoopBackRowStatus        OBJECT-TYPE
        SYNTAX          RowStatus
        MAX-ACCESS      read-create
        STATUS          current
        DESCRIPTION
                "the row status of the switcher table."
        ::= { bgs10PmLoopBackEntry 1 }
        
bgs10PmLoopBackTestType         OBJECT-TYPE
        SYNTAX          UChar
        MAX-ACCESS      read-create
        STATUS          current
        DESCRIPTION
                "the test type includes :F4 end-to-end/segment-to-segment,F5 end-to-end/
        segment-to-segment."
        ::= { bgs10PmLoopBackEntry 2 }
        
bgs10PmLoopBackModule   OBJECT-TYPE
        SYNTAX          UChar
        MAX-ACCESS      read-create
        STATUS          current
        DESCRIPTION
                "the tested Mpdule."
        ::= { bgs10PmLoopBackEntry 3 }
        
bgs10PmLoopBackPerfPort OBJECT-TYPE
        SYNTAX          UShort
        MAX-ACCESS      read-create
        STATUS          current
        DESCRIPTION
                "the tested port."
        ::= { bgs10PmLoopBackEntry 4 }
        
bgs10PmLoopBackTestIndex        OBJECT-TYPE
        SYNTAX          UShort
        MAX-ACCESS      read-create
        STATUS          current
        DESCRIPTION
                "the test index."
        ::= { bgs10PmLoopBackEntry 5 }
        
bgs10PmLoopBackVPI              OBJECT-TYPE
        SYNTAX          UShort
        MAX-ACCESS      read-create
        STATUS          current
        DESCRIPTION
                "the test VPI."
        ::= { bgs10PmLoopBackEntry 6 }

bgs10PmLoopBackVCI              OBJECT-TYPE
        SYNTAX          UShort
        MAX-ACCESS      read-create
        STATUS          current
        DESCRIPTION
                "the test VCI."
        ::= { bgs10PmLoopBackEntry 7 }
        
bgs10PmLoopBackTestNumber OBJECT-TYPE
        SYNTAX          UShort
        MAX-ACCESS      read-create
        STATUS          current
        DESCRIPTION
                "the numbers of the loopback test."
        ::= { bgs10PmLoopBackEntry 8 }
        
bgs10PmLoopBackID       OBJECT-TYPE
        SYNTAX          OCTET STRING(SIZE(13))
        MAX-ACCESS      read-create
        STATUS          current
        DESCRIPTION
                "the loop back ID."
        ::= { bgs10PmLoopBackEntry 9 }
        
bgs10PmLoopBackLoopBackActionFlag       OBJECT-TYPE
        SYNTAX          INTEGER { down(0),
                                                up(1),
                                                close(2)
                                                }
        MAX-ACCESS      read-create
        STATUS          current
        DESCRIPTION
                "the loop-bakc action flag."
        ::= { bgs10PmLoopBackEntry 10 }
        
bgs10PmLoopBackPMActionFlag             OBJECT-TYPE
        SYNTAX          INTEGER { down(0),
                                                up(1),
                                                close(2)
                                                }
        MAX-ACCESS      read-create
        STATUS          current
        DESCRIPTION
                " the perfermance management action flag."
         ::= { bgs10PmLoopBackEntry 11 }
         
bgs10PmLoopBackTestResult               OBJECT-TYPE
        SYNTAX          UCHAR   
        MAX-ACCESS      read-create
        STATUS          current
        DESCRIPTION
                " the OAM Test result."
         ::= { bgs10PmLoopBackEntry 12 }
         
--The ZXBGS10 interface Configuration extensions.

bgs10IfConfigureTable   OBJECT-TYPE
        SYNTAX          SEQUENCE OF BGS10IfConfigureEntry
        MAX-ACCESS      not-accessible
        STATUS          current
        DESCRIPTION
                "The ZXBGS10 ATM interface configuration table extensions.This table 
                augments the atm interface configuration table in RFC 1695."
        ::= { zxbgs10mib 20 }
        
bgs10IfConfigureEntry   OBJECT-TYPE
        SYNTAX          BGS10IfConfigureEntry
        MAX-ACCESS      not-accessible
        STATUS          current
        DESCRIPTION     
                "Additional columns for the ATM interface configuration table entry."
        AUGMENTS        { atmInterfaceConfEntry }
        ::= { bgs10IfConfigureTable 1}
        
BGS10IfConfigureEntry   ::=
        SEQUENCE {
                bgs10IfConfigurePort            UChar,
                bgs10IfConfigureAdminState      UChar,
                bgs10IfConfigureOperState       UChar,
                bgs10IfConfigureSigVpi          INTEGER,
                bgs10IfConfigInterfaceSigVci    UShort,
                bgs10IfConfigInterfaceType      UShort,
                bgs10IfConfigilmiIMEType        UShort
        }
        
bgs10IfConfigurePort    OBJECT-TYPE
        SYNTAX          UChar
        MAX-ACCESS      read-write
        STATUS          current
        DESCRIPTION
                "The Port Number."
        ::= { bgs10IfConfigureEntry     1 }

bgs10IfConfigureAdminState      OBJECT-TYPE
        SYNTAX          UChar
        MAX-ACCESS      read-write
        STATUS          current
        DESCRIPTION
                "A control object to indicate the administratively desired state of the 
        interface configuration."
        ::= { bgs10IfConfigureEntry     2 }

bgs10IfConfigureOperState       OBJECT-TYPE
        SYNTAX          UChar
        MAX-ACCESS      read-only
        STATUS          current
        DESCRIPTION
                "A status object to indicate the operational state of the interface 
        configuration."
        ::= { bgs10IfConfigureEntry     3 }
        
bgs10IfConfigureSigVpi          OBJECT-TYPE
        SYNTAX          INTEGER
        MAX-ACCESS      read-only
        STATUS          current
        DESCRIPTION
                ""
        ::= { bgs10IfConfigureEntry     4 }
bgs10IfConfigInterfaceSigVci            OBJECT-TYPE
        SYNTAX          UShort
        MAX-ACCESS      read-only
        STATUS          current
        DESCRIPTION
                ""
        ::= { bgs10IfConfigureEntry     5 }
bgs10IfConfigInterfaceType              OBJECT-TYPE
        SYNTAX          UShort
        MAX-ACCESS      read-only
        STATUS          current
        DESCRIPTION
                ""
        ::= { bgs10IfConfigureEntry     6 }
bgs10IfConfigilmiIMEType                OBJECT-TYPE
        SYNTAX          UShort
        MAX-ACCESS      read-only
        STATUS          current
        DESCRIPTION
                ""
        ::= { bgs10IfConfigureEntry     7 }




--The Plug-in unit table
bgs10PlugInUnit     OBJECT IDENTIFIER   ::= { zxbgs10mib 32}
    
bgs10PlugInUnitTable    OBJECT-TYPE
    SYNTAX      SEQUENCE OF Bgs10PlugInUnitEntry
    MAX-ACCESS  not-accessible
    STATUS      current
    DESCRIPTION
        "the plug-in unittable."
    ::= { bgs10PlugInUnit 1 }
    
bgs10PlugInUnitEntry    OBJECT-TYPE
    SYNTAX      Bgs10PlugInUnitEntry
    MAX-ACCESS  not-accessible
    STATUS      current
    DESCRIPTION
        "the entry to the plug-in unit table."
    INDEX { entPhysicalIndex  }
    ::= { bgs10PlugInUnitTable 1 }
    
Bgs10PlugInUnitEntry    ::=
    SEQUENCE {
        bgs10PlugInUnitRowStatus        RowStatus,
        bgs10PlugInUnitMasterStatus     INTEGER,
        bgs10PlugInUnitEntPhysicalContainedIn
                                        INTEGER,
        bgs10PlugInUnitEthiVlanSwith        INTEGER,
        bgs10PlugInUnitCardType         INTEGER,
        bgs10PlugInUnitModule           INTEGER,
        bgs10PlugInUnitCardPosition     INTEGER,
        bgs10PlugInUnitPhysicalClass        INTEGER,
        bgs10PlugInUnitserbitmap        Unsigned32
    }
    
bgs10PlugInUnitRowStatus    OBJECT-TYPE
    SYNTAX      RowStatus
    MAX-ACCESS  read-create
    STATUS      current
    DESCRIPTION
        "the conceptual row status."
    ::= { bgs10PlugInUnitEntry 1 }
    
bgs10PlugInUnitMasterStatus OBJECT-TYPE
    SYNTAX      INTEGER { master(0),
                            slave(1)
                        }
    MAX-ACCESS  read-create
    STATUS      current
    DESCRIPTION
        "the Unit work status."
    ::= { bgs10PlugInUnitEntry 2 }
    
bgs10PlugInUnitEntPhysicalContainedIn   OBJECT-TYPE
    SYNTAX      INTEGER
    MAX-ACCESS  read-create
    STATUS      current
    DESCRIPTION
        "the physical contained position."
    ::= { bgs10PlugInUnitEntry 3 }
    
bgs10PlugInUnitEthiVlanSwith    OBJECT-TYPE
    SYNTAX      INTEGER
    MAX-ACCESS  read-create
    STATUS      current
    DESCRIPTION
        "the neighbor service card type."
    ::= { bgs10PlugInUnitEntry 4 }
    
bgs10PlugInUnitCardType     OBJECT-TYPE
    SYNTAX      INTEGER
    {
     UNKNOWN(0),  
     CORE   (1),   
     WANA   (3),   
     POWER  (4),  
     ATUCC  (5),  
     ATUCB  (6),  
     OTHER  (7), 
     COREA  (8), 
     COREC  (9),  
     WANA1  (10), 
     WANAD  (11), 
     WANE   (12),  
     LAN    (13),   
     ATUCD  (14), 
     ATUCE  (15), 
     ATUCF  (16), 
     ATUCH  (18), 
     ATUCI  (19), 
     IMAA   (20),  
     COREA2 (21),
     COREB2 (22),
     COREC2 (23),
     COREA3 (24),
     COREB3 (25),
     COREC3 (26),
     IMAB   (27),  
     LANAA  (28), 
     LANAB  (29), 
     LANAC  (30), 
     LANAD  (31), 
     LANBA  (32), 
     LANBB  (33), 
     LANCA  (34), 
     LANCB  (35), 
     LANCC  (36), 
     LANCD  (37), 
     LANDA  (38), 
     LANDB  (39), 
     

     ATUGA  (17), 
     ATUGB  (44), 
     ATUGI  (41),      
     STUCA  (40),      
     STUCB  (45),      
     VTUCA  (46),      
     VTUCB  (47),      
     PSUB   (48),      
     PSUP   (49),      
     PSUD   (50),      
     ISUP   (51),      
     ISUB   (52),      
     ISUD   (53),      
     VSUA   (54),      
     VSUB   (55),      
     SSU    (56),        
     PSUTA  (57),      
     PSUTP  (58),      
     PSUTD  (59),      
     ISUTP  (60), 
     ISUTB  (61), 
     ISUTD  (62), 
     VSUTA  (63),      
     VSUTB  (64),      
     SSUT   (65),      
     MATUD  (66),      
     LNP    (67),        
     LNR    (68),        
     COREM  (69),      
     CORES  (43),      
     WAND   (70),      
     GEIA   (71),      
     WANF   (72),      
     WANFS  (73),      
     WANFM  (74),      
     WANFL  (75),      
     WANC   (76),      
     WANAB  (77),      
     WANAS  (78),      
     WANAM  (79),      
     WANAL  (80),      
     WANB1  (42),      
     WANB   (2 ),      
     IMAA   (20), 
     IMAB   (27), 
     IMAD   (81), 
     E1A    (82), 
     IMAX   (83), 
     E1X    (84), 
     E1B    (85)  
     }
    MAX-ACCESS  read-create
    STATUS      current
    DESCRIPTION
        "the card type."
    ::= { bgs10PlugInUnitEntry 5 }
        
bgs10PlugInUnitModule   OBJECT-TYPE
    SYNTAX      INTEGER
    MAX-ACCESS  read-create
    STATUS      current
    DESCRIPTION
        "the Module Number."
    ::= { bgs10PlugInUnitEntry 6 }
    
bgs10PlugInUnitCardPosition OBJECT-TYPE
    SYNTAX      INTEGER
    MAX-ACCESS  read-create
    STATUS      current
    DESCRIPTION
        " the card position."
    ::= { bgs10PlugInUnitEntry 7}

bgs10PlugInUnitPhysicalClass    OBJECT-TYPE
    SYNTAX      INTEGER
    MAX-ACCESS  read-create
    STATUS      current
    DESCRIPTION
        " the card phyical class."
    ::= { bgs10PlugInUnitEntry 8}
bgs10PlugInUnitserbitmap    OBJECT-TYPE
    SYNTAX      Unsigned32
    MAX-ACCESS  read-create
    STATUS      current
    DESCRIPTION
        " the card phyical class."
    ::= { bgs10PlugInUnitEntry 9}
    



--bgs10atmfM4PlugInUnitTable
bgs10atmfM4PlugInUnitTable      OBJECT-TYPE
        SYNTAX          SEQUENCE OF BGS10atmfM4PlugInUnitEntry
        MAX-ACCESS      not-accessible
        STATUS          current
        DESCRIPTION
        "."
        ::= { zxbgs10mib 110 }

bgs10atmfM4PlugInUnitEntry      OBJECT-TYPE
        SYNTAX          BGS10atmfM4PlugInUnitEntry
        MAX-ACCESS      not-accessible
        STATUS          current
        DESCRIPTION
                "."
    INDEX { entPhysicalIndex  }
        ::= { bgs10atmfM4PlugInUnitTable 1 }

BGS10atmfM4PlugInUnitEntry ::=
        SEQUENCE { 
                bgs10PatmfM4PlugInzxDslamCardPortNum            UChar,
                bgs10PatmfM4PlugInzxDslamCardDescr              OCTET STRING(SIZE(32)),
                bgs10PatmfM4PlugInverNum                        Unsigned32,
                bgs10PatmfM4PlugInhardver                       OCTET STRING(SIZE(17)),
                bgs10PatmfM4PlugInsoftver                       OCTET STRING(SIZE(17)),
                bgs10PatmfM4PlugInbuildtime                     OCTET STRING(SIZE(17)),
                bgs10PatmfM4PlugInbackupsoftver                 OCTET STRING(SIZE(17)),
                bgs10PatmfM4PlugInbackupbuildtime               OCTET STRING(SIZE(17)),
                bgs10PatmfM4PlugInzxDCardChipsOperStatus        UChar,
                bgs10PatmfM4PlugInzxDCardType                   UChar,  
                bgs10PatmfM4PlugInzxDCardOperStatus             UChar,
                bgs10PatmfM4PlugInfirewarever                   OCTET STRING(SIZE(16)),
                bgs10PatmfM4PlugInCardReleasePVC                UChar,
                bgs10PatmfM4PlugInCardEnablePort                UChar,
                bgs10PatmfM4PlugInCardSwitchVersion             UChar,
                bgs10PatmfM4PlugInCardLogicPortNum              UChar
                
        }  
        
bgs10PatmfM4PlugInzxDslamCardPortNum    OBJECT-TYPE
        SYNTAX          UChar
        MAX-ACCESS      read-create
        STATUS          current
        DESCRIPTION
                "The remote port type."
        ::= {  bgs10atmfM4PlugInUnitEntry 2 }
bgs10PatmfM4PlugInzxDslamCardDescr      OBJECT-TYPE
        SYNTAX          OCTET STRING(SIZE(32))
        MAX-ACCESS      read-create
        STATUS          current
        DESCRIPTION
                "The remote port type."
        ::= {  bgs10atmfM4PlugInUnitEntry 3 }
bgs10PatmfM4PlugInverNum        OBJECT-TYPE
        SYNTAX          Unsigned32
        MAX-ACCESS      read-create
        STATUS          current
        DESCRIPTION
                "The remote port type."
        ::= {  bgs10atmfM4PlugInUnitEntry 4 }
bgs10PatmfM4PlugInhardver       OBJECT-TYPE
        SYNTAX          OCTET STRING(SIZE(17))
        MAX-ACCESS      read-create
        STATUS          current
        DESCRIPTION
                "The remote port type."
        ::= {  bgs10atmfM4PlugInUnitEntry 5 }
bgs10PatmfM4PlugInsoftver       OBJECT-TYPE
        SYNTAX          OCTET STRING(SIZE(17))
        MAX-ACCESS      read-create
        STATUS          current
        DESCRIPTION
                "The remote port type."
        ::= {  bgs10atmfM4PlugInUnitEntry 6 }
bgs10PatmfM4PlugInbuildtime     OBJECT-TYPE
        SYNTAX          OCTET STRING(SIZE(17))
        MAX-ACCESS      read-create
        STATUS          current
        DESCRIPTION
                "The remote port type."
        ::= {  bgs10atmfM4PlugInUnitEntry 7 }
bgs10PatmfM4PlugInbackupsoftver         OBJECT-TYPE
        SYNTAX          OCTET STRING(SIZE(17))
        MAX-ACCESS      read-create
        STATUS          current
        DESCRIPTION
                "The remote port type."
        ::= {  bgs10atmfM4PlugInUnitEntry 8 }
bgs10PatmfM4PlugInbackupbuildtime       OBJECT-TYPE
        SYNTAX          OCTET STRING(SIZE(17))
        MAX-ACCESS      read-create
        STATUS          current
        DESCRIPTION
                "The remote port type."
        ::= {  bgs10atmfM4PlugInUnitEntry 9 }
bgs10PatmfM4PlugInzxDCardChipsOperStatus        OBJECT-TYPE
        SYNTAX          UChar
        MAX-ACCESS      read-create
        STATUS          current
        DESCRIPTION
                "The remote port type."
        ::= {  bgs10atmfM4PlugInUnitEntry 10 }
bgs10PatmfM4PlugInzxDCardType   OBJECT-TYPE
        SYNTAX          UChar
        MAX-ACCESS      read-create
        STATUS          current
        DESCRIPTION
                "The remote port type."
        ::= {  bgs10atmfM4PlugInUnitEntry 11 }
bgs10PatmfM4PlugInzxDCardOperStatus     OBJECT-TYPE
        SYNTAX          UChar
        MAX-ACCESS      read-create
        STATUS          current
        DESCRIPTION
                "The remote port type."
        ::= {  bgs10atmfM4PlugInUnitEntry 12 }  
bgs10PatmfM4PlugInfirewarever   OBJECT-TYPE
        SYNTAX          OCTET STRING(SIZE(16))
        MAX-ACCESS      read-create
        STATUS          current
        DESCRIPTION
                "The remote port type."
        ::= {  bgs10atmfM4PlugInUnitEntry 13 }  

bgs10PatmfM4PlugInCardReleasePVC    OBJECT-TYPE
    SYNTAX      UChar
    MAX-ACCESS  read-create
    STATUS      current
    DESCRIPTION
        "The remote port type."
    ::= {  bgs10atmfM4PlugInUnitEntry 14 }  

bgs10PatmfM4PlugInCardEnablePort    OBJECT-TYPE
    SYNTAX      UChar
    MAX-ACCESS  read-create
    STATUS      current
    DESCRIPTION
        "The remote port type."
    ::= {  bgs10atmfM4PlugInUnitEntry 15 }  

                                            
bgs10PatmfM4PlugInCardSwitchVersion     OBJECT-TYPE
    SYNTAX      UChar
    MAX-ACCESS  read-create
    STATUS      current
    DESCRIPTION
        "The remote port type."
    ::= {  bgs10atmfM4PlugInUnitEntry 16 }  


bgs10PatmfM4PlugInCardLogicPortNum  OBJECT-TYPE
    SYNTAX      UChar
    MAX-ACCESS  read-create
    STATUS      current
    DESCRIPTION
        "The remote port type."
    ::= {  bgs10atmfM4PlugInUnitEntry 17 }  



--dsx1ConfigTable
dsx1ConfigTable OBJECT-TYPE
        SYNTAX  SEQUENCE OF E1ConfEntry
        MAX-ACCESS      not-accessible
        STATUS  current
        DESCRIPTION
                "A table of T1/E1 switch port configuration information."
        ::= { zxbgs10mib 55 }

dsx1ConfigEntry OBJECT-TYPE
        SYNTAX  E1ConfEntry
        MAX-ACCESS      not-accessible
        STATUS  current
        DESCRIPTION
                "A table entry containing T1/E1 configuration information for each
                port. Not all RFC1406 configuration table variables are
                included, and some are modified."
        INDEX   { dsx1ConfModule, dsx1ConfPort }
        ::= { dsx1ConfigTable 1 }

E1ConfEntry ::=
        SEQUENCE {
                dsx1RowStatus                   RowStatus,
                dsx1ConfModule                  INTEGER,
                dsx1ConfPort                    INTEGER,
                dsx1ConfLineType                INTEGER,
                dsx1ConfLineCoding              INTEGER,
                dsx1ConfLoopbackConfig  INTEGER,
                dsx1ConfLineStatus              INTEGER,
        dsx1ConfSignalMode      INTEGER,
                dsx1ConfTxClockSource   INTEGER,
                dsx1ConfIdleCells               INTEGER,
                dsx1ConfRxScrambling    INTEGER,
                dsx1ConfTxScrambling    INTEGER,
                dsx1ConfChannelNumber   INTEGER,
                dsx1ConfChannelization  INTEGER
}

dsx1RowStatus OBJECT-TYPE
        SYNTAX  RowStatus
        MAX-ACCESS      read-write
        STATUS  current
        DESCRIPTION
                "."
        ::= { dsx1ConfigEntry 1 }

dsx1ConfModule OBJECT-TYPE
        SYNTAX  INTEGER
        MAX-ACCESS      read-write
        STATUS  current
        DESCRIPTION
                "The network module of this port."
        ::= { dsx1ConfigEntry 2 }

dsx1ConfPort OBJECT-TYPE
        SYNTAX  INTEGER
        MAX-ACCESS      read-write
        STATUS  current
        DESCRIPTION
                "The number of this port."
        ::= { dsx1ConfigEntry 3 }

dsx1ConfLineType OBJECT-TYPE
        SYNTAX  INTEGER {
                     other(1),
                     dsx1E1(4),
                     dsx1E1CRC(5),
                     dsx1E1MF(6),
                     dsx1E1CRCMF(7),
                     dsx1E1Unframed(9),
                     dsx1Unframed(8),
                     dsx1ESF(2),
                     dsx1D4(3)
                }
        MAX-ACCESS      read-write
        STATUS  current
        DESCRIPTION
                "This variable indicates the variety of E1 Line implementing
                this circuit. The type of circuit affects the number of bits
                per second that the circuit can reasonably carry, as well as
                the interpretation of the usage and error statistics. This
                variable is defined in the rfc1406 configuration table as
                dsx1LineType.

                According to rfc1406, the different values are:
                 dsx1ESF         Extended SuperFrame DS1 (T1.107)
                 dsx1D4          AT&T D4 format DS1 (T1.107)
                 dsx1E1          ITU-T Recommendation G.704
                                  (Table 4a)
                 dsx1E1-CRC      ITU-T Recommendation G.704
                                  (Table 4b)
                 dsxE1-MF        G.704 (Table 4a) with TS16
                                  multiframing enabled
                 dsx1E1-CRC-MF   G.704 (Table 4b) with TS16
                                  multiframing enabled
                 dsx1Unframed    DS1 with No Framing
                 dsx1E1Unframed  E1 with No Framing (G.703)"
        ::= { dsx1ConfigEntry 4 }

dsx1ConfLineCoding OBJECT-TYPE
        SYNTAX  INTEGER
        MAX-ACCESS      read-write
        STATUS  current
        DESCRIPTION
                "This variable describes the variety of Zero Code suppression
                used on this link, which in turn affects a number of its
                characteristics. e1AMI(3) refers to a mode wherein no zero
                code suppression is present and the line encoding does not
                solve the problem directly. In this application, the higher
                layer must provide data which meets or exceeds the pulse
                density re-quirements, such as inverting HDLC data. This
                variable is defined in the rfc1406 configuration table as
                dsx1LineCoding."
        ::= { dsx1ConfigEntry 5 }

dsx1ConfLoopbackConfig OBJECT-TYPE
        SYNTAX  INTEGER {
                      dsx1NoLoop(1),
                      dsx1PayloadLoop(2),
                      dsx1LineLoop(3),
                      dsx1OtherLoop(4),
                      dsx1InwardLoop(5),
                      dsx1DualLoop(6)
                }
        MAX-ACCESS      read-write
        STATUS  current
        DESCRIPTION
                "This variable represents the loopback configuration of the E1
                interface. This variable is defined in the rfc1406
                configuration table as dsx1LoopbackConfig, with slightly
                different values.

                e1NoLoop (1) means that the interface is not in a loopback
                state.

                e1LineLoop (2) means that cells that are processed by the
                receiving component are not written into the receive FIFO, but
                into the transmit FIFO for retransmission.

                e1PayloadLoop (3) means that the receive signal is looped back
                for retransmission after it has passed through the port's
                reframing function.

                e1DiagLoop (4) means that the transmit data stream is looped
                back to the receiver.

                e1OtherLoop (5) means that the interface is in a loopback that
                is not defined here."
        DEFVAL  { 1 }
        ::= { dsx1ConfigEntry 6 }

dsx1ConfLineStatus OBJECT-TYPE
        SYNTAX  INTEGER (1..65534)
        MAX-ACCESS      read-write
        STATUS  current
        DESCRIPTION
                "This variable indicates the Line Status of the interface. A
                similar object is defined in the rfc1406 configuration table as
                dsx1LineStatus. The variable contains loopback state
                information and failure state information. It is a bit map
                represented as a sum. The e1NoAlarm should be set if and only
                if no other flag is set.

                The various bit positions are:
      1     dsx1NoAlarm           No alarm present
      2     dsx1RcvFarEndLOF      Far end LOF (a.k.a., Yellow Alarm)
      4     dsx1XmtFarEndLOF      Near end sending LOF Indication
      8     dsx1RcvAIS            Far end sending AIS
     16     dsx1XmtAIS            Near end sending AIS
     32     dsx1LossOfFrame       Near end LOF (a.k.a., Red Alarm)
     64     dsx1LossOfSignal      Near end Loss Of Signal
    128     dsx1LoopbackState     Near end is looped
    256     dsx1T16AIS            E1 TS16 AIS
    512     dsx1RcvFarEndLOMF     Far End Sending TS16 LOMF
   1024     dsx1XmtFarEndLOMF     Near End Sending TS16 LOMF
   2048     dsx1RcvTestCode       Near End detects a test code
   4096     dsx1OtherFailure      any line status not defined here
   8192     dsx1UnavailSigState   Near End in Unavailable Signal
                                  State
  16384     dsx1NetEquipOOS       Carrier Equipment Out of Service
  32768     dsx1RcvPayloadAIS     DS2 Payload AIS
  65536     dsx1Ds2PerfThreshold  DS2 Performance Threshold
                                  Exceeded"
        ::= { dsx1ConfigEntry 7 }

     dsx1ConfSignalMode OBJECT-TYPE
          SYNTAX  INTEGER
          MAX-ACCESS  read-write
          STATUS  current
          DESCRIPTION
            "."
    ::= { dsx1ConfigEntry 8 }

dsx1ConfTxClockSource OBJECT-TYPE
        SYNTAX  INTEGER {
                     loopTiming(1),
                     localTiming(2),
                     throughTiming(3)
                }
        MAX-ACCESS      read-write
        STATUS  current
        DESCRIPTION
                "The source of the transmit clock. rxTiming(1) indicated that
                the recovered receive clock is used as the transmit clock.
                localTiming(2) indicates that a local source clock is used as
                the transmit clock. To determine which local source clock is
                used advise the ntGlobalClock in the netmodTimingTable for this
                netmod (refer to the Fore-Switch-MIB for more information)."
        DEFVAL  { 2 }
        ::= { dsx1ConfigEntry 9 }

dsx1ConfIdleCells OBJECT-TYPE
        SYNTAX  INTEGER {
                unassigned(1),
                idle(2)
                }
        MAX-ACCESS      read-write
        STATUS  current
        DESCRIPTION
                "This variable indicates the types of cells that should be sent
                in case there is no real data to send. According to the ATM
                Forum, Unassigned cells should be sent (octet 1-3 are 0's,
                octet 4 is 0000xxx0, where x is 'don't care'). According to the
                CCITT specifications, Idle cells should be sent (everything is
                '0' except for the CLP bit which is '1'). By default,
                unassigned cells are transmitted is case there is no data to
                send."
        DEFVAL  { 1 }
        ::= { dsx1ConfigEntry 10 }

     
dsx1ConfRxScrambling OBJECT-TYPE
        SYNTAX  INTEGER {
                descrambling(1),
                noDescrambling(2)
                }
        MAX-ACCESS  read-write
        STATUS  current
        DESCRIPTION
                "This variable indicates whether the information is being
                descrambled on receiving. It should be set the same as the
                transmitting side."
        DEFVAL { 1 }
        ::= { dsx1ConfigEntry 11 }

dsx1ConfTxScrambling OBJECT-TYPE
        SYNTAX  INTEGER {
                scrambling(1),
                noScrambling(2)
                }
        MAX-ACCESS  read-write
        STATUS  current
        DESCRIPTION
                "This variable indicates whether the information (48 octet
                payload) is being scrambled before transmitting. It should
                be set the same as the receiving side."
        DEFVAL { 1 }
        ::= { dsx1ConfigEntry 12 }

     dsx1ConfChannelNumber  OBJECT-TYPE
          SYNTAX      INTEGER (0..28)
          MAX-ACCESS  read-write
          STATUS      current
          DESCRIPTION
                 "This variable represents the channel number of
                 the DS1/E1 on its parent Ds2/E2 or DS3/E3.  A
                 value of 0 indicated this DS1/E1 does not have a
                 parent DS3/E3."

     ::= { dsx1ConfigEntry 13 }

     dsx1ConfChannelization  OBJECT-TYPE
          SYNTAX      INTEGER {
                         disabled(1),
                         enabledDs0(2)
                      }
          MAX-ACCESS  read-write
          STATUS      current
          DESCRIPTION
                 "Indicates whether this ds1/e1 is channelized or
                 unchannelized.  The value of enabledDs0 indicates
                 that this is a DS1 channelized into DS0s.  The
                 value of enabledDs1 indicated that this is a DS2
                 channelized into DS1s.  Setting this value will
                 cause the creation or deletion of entries in the
                 ifTable for the DS0s that are within the DS1."
     ::= { dsx1ConfigEntry 14 }

-- dsx3ConfigTable
dsx3ConfigTable OBJECT-TYPE
        SYNTAX  SEQUENCE OF E3ConfEntry
        MAX-ACCESS      not-accessible
        STATUS  current
        DESCRIPTION
                "A table of T3/E3 switch port configuration information."
        ::= { zxbgs10mib 56 }

dsx3ConfigEntry OBJECT-TYPE
        SYNTAX  E3ConfEntry
        MAX-ACCESS      not-accessible
        STATUS  current
        DESCRIPTION
                "A table entry containing T3/E3 configuration information for each
                port. Not all RFC1406 configuration table variables are
                included, and some are modified."
        INDEX   { 
                dsx3ConfModule, 
                dsx3ConfPort
                }
        ::= { dsx3ConfigTable 1 }

E3ConfEntry ::=
        SEQUENCE {
                dsx3RowStatus                   RowStatus,
                dsx3ConfModule                  INTEGER,
                dsx3ConfPort                    INTEGER,
                dsx3ConfLineType                INTEGER,
                dsx3ConfLineCoding              INTEGER,
                dsx3ConfLoopbackConfig  INTEGER,
                dsx3ConfLineStatus              INTEGER,
                dsx3ConfTxClockSource   INTEGER,
                dsx3ConfIdleCells               INTEGER,
                dsx3ConfRxScrambling    INTEGER,
                dsx3ConfTxScrambling    INTEGER,
                dsx3ConfChannelization  INTEGER,
                dsx3Ds1ForRemoteLoop    INTEGER
}

dsx3RowStatus OBJECT-TYPE
        SYNTAX  RowStatus
        MAX-ACCESS      read-write
        STATUS  current
        DESCRIPTION
                "."
        ::= { dsx3ConfigEntry 1 }

dsx3ConfModule OBJECT-TYPE
        SYNTAX  INTEGER
        MAX-ACCESS      read-write
        STATUS  current
        DESCRIPTION
                "The network module of this port."
        ::= { dsx3ConfigEntry 2 }

dsx3ConfPort OBJECT-TYPE
        SYNTAX  INTEGER
        MAX-ACCESS      read-write
        STATUS  current
        DESCRIPTION
                "The number of this port."
        ::= { dsx3ConfigEntry 3 }

dsx3ConfLineType OBJECT-TYPE
        SYNTAX  INTEGER {
                     e3other(6),
                     e3Framed(7),
                     e3Plcp(8),
                     dsx3ClearChannel(5),
                     dsx3other(1),
                     dsx3M23(2),
                     dsx3SYNTRAN(3),
                     dsx3CbitParity(4)
                }
          MAX-ACCESS  read-write
          STATUS  current
          DESCRIPTION
                 "This variable indicates the variety of DS3 C-bit
                 or E3 application implementing this interface. The
                 type of interface affects the interpretation of
                 the usage and error statistics.  The rate of DS3
                 is 44.736 Mbps and E3 is 34.368 Mbps.  The
                 dsx3ClearChannel value means that the C-bits are
                 not used except for sending/receiving AIS.
                 The values, in sequence, describe:

                 TITLE:            SPECIFICATION:
                 dsx3M23            ANSI T1.107-1988 [9]
                 dsx3SYNTRAN        ANSI T1.107-1988 [9]
                 dsx3CbitParity     ANSI T1.107a-1990 [9a]
                 dsx3ClearChannel   ANSI T1.102-1987 [8]
                 e3Framed           CCITT G.751 [12]
                 e3Plcp             ETSI T/NA(91)18 [13]."
          ::= { dsx3ConfigEntry 4 }

dsx3ConfLineCoding OBJECT-TYPE
          SYNTAX  INTEGER {
                     dsx3Other(1),
                     e3HDB3(3),
                     dsx3B3ZS(2)
                 }
          MAX-ACCESS  read-write
          STATUS  current
          DESCRIPTION
                 "This variable describes the variety of Zero Code
                 Suppression used on this interface, which in turn
                 affects a number of its characteristics.

                 dsx3B3ZS and e3HDB3 refer to the use of specified
                 patterns of normal bits and bipolar violations
                 which are used to replace sequences of zero bits
                 of a specified length."
          ::= { dsx3ConfigEntry 5 }

dsx3ConfLoopbackConfig OBJECT-TYPE
        SYNTAX  INTEGER {
                ds3NoLoop (1),
                ds3PayloadLoop (3),
                ds3LineLoop (5),
                ds3OtherLoop (6)
                }
        MAX-ACCESS      read-write
        STATUS  current
        DESCRIPTION
                "This variable represents the loopback configuration of the DS3
                interface. This variable is defined in the rfc1407
                configuration table as dsx3LoopbackConfig, with slightly
                different values.

                ds3NoLoop (1) means that the interface is not in a loopback
                state.

                ds3CellLoop (2) means that cells that are processed by the
                receiving component are not written into the receive FIFO, but
                into the transmit FIFO for retransmission.

                ds3PayloadLoop (3) means that the receive signal is looped back
                for retransmission after it has passed through the port's
                reframing function.

                ds3DiagLoop (4) means that the transmit data stream is looped
                back to the receiver.

                ds3LineLoop (5) is only supported on series B and later
                netmods.

                ds3OtherLoop (6) means that the interface is in a loopback that
                is not defined here."
        DEFVAL  { 1 }
        ::= { dsx3ConfigEntry 6 }

dsx3ConfLineStatus OBJECT-TYPE
          SYNTAX  INTEGER (1..4095)
          MAX-ACCESS  read-write
          STATUS  current
          DESCRIPTION
                 "This variable indicates the Line Status of the
                 interface.  It contains loopback state information
                 and failure state information.  The dsx3LineStatus
                 is a bit map represented as a sum, therefore, it
                 can represent multiple failures and a loopback
                 (see dsx3LoopbackConfig object for the type of
                 loopback) simultaneously.  The dsx3NoAlarm must be
                 set if and only if no other flag is set.

                 If the dsx3loopbackState bit is set, the loopback
                 in effect can be determined from the
                 dsx3loopbackConfig object.
       The various bit positions are:
        1     dsx3NoAlarm         No alarm present
        2     dsx3RcvRAIFailure   Receiving Yellow/Remote
                                  Alarm Indication
        4     dsx3XmitRAIAlarm    Transmitting Yellow/Remote
                                  Alarm Indication
        8     dsx3RcvAIS          Receiving AIS failure state
       16     dsx3XmitAIS         Transmitting AIS
       32     dsx3LOF             Receiving LOF failure state
       64     dsx3LOS             Receiving LOS failure state
      128     dsx3LoopbackState   Looping the received signal
      256     dsx3RcvTestCode     Receiving a Test Pattern
      512     dsx3OtherFailure    any line status not defined
                                  here
     1024     dsx3UnavailSigState Near End in Unavailable Signal
                                  State
     2048     dsx3NetEquipOOS     Carrier Equipment Out of Service"
     ::= { dsx3ConfigEntry 7 }

dsx3ConfTxClockSource OBJECT-TYPE
     SYNTAX  INTEGER {
                loopTiming(1),
                localTiming(2),
                throughTiming(3)
            }
     MAX-ACCESS  read-write
     STATUS  current
     DESCRIPTION
            "The source of Transmit Clock.

            loopTiming indicates that the recovered receive clock
            is used as the transmit clock.

            localTiming indicates that a local clock source is used
            or that an external clock is attached to the box
            containing the interface.

            throughTiming indicates that transmit clock is derived
            from the recovered receive clock of another DS3
            interface."
          ::= { dsx3ConfigEntry 8 }

dsx3ConfIdleCells OBJECT-TYPE
        SYNTAX  INTEGER {
                unassigned(1),
                idle(2)
                }
        MAX-ACCESS      read-write
        STATUS  current
        DESCRIPTION
                "This variable indicates the types of cells that should be sent
                in case there is no real data to send. According to the ATM
                Forum, Unassigned cells should be sent (octet 1-3 are 0's,
                octet 4 is 0000xxx0, where x is 'don't care'). According to the
                CCITT specifications, Idle cells should be sent (everything is
                '0' except for the CLP bit which is '1'). By default,
                unassigned cells are transmitted is case there is no data to
                send."
        DEFVAL  { 1 }
        ::= { dsx3ConfigEntry 9 }

dsx3ConfRxScrambling OBJECT-TYPE
        SYNTAX  INTEGER {
                descrambling(1),
                noDescrambling(2)
                }
        MAX-ACCESS      read-write
        STATUS  current
        DESCRIPTION
                "This variable indicates whether the information is being
                descrambled on receiving. It should be set the same as the
                transmitting side."
        DEFVAL  { 2 }
        ::= { dsx3ConfigEntry 10 }

dsx3ConfTxScrambling OBJECT-TYPE
        SYNTAX  INTEGER {
                scrambling(1),
                noScrambling(2)
                }
        MAX-ACCESS      read-write
        STATUS  current
        DESCRIPTION
                "This variable indicates whether the information (48 octet
                payload) is being scrambled before transmitting. It should be
                set the same as the receiving side."
        DEFVAL  { 2 }
        ::= { dsx3ConfigEntry 11 }

     dsx3ConfChannelization  OBJECT-TYPE
          SYNTAX      INTEGER {
                         disabled(1),
                         enabledDs1(2),
                         enabledDs2(3)
                      }
          MAX-ACCESS  read-write
          STATUS      current
          DESCRIPTION
                 "Indicates whether this ds3/e3 is channelized or
                 unchannelized.  The value of enabledDs1 indicates
                 that this is a DS3 channelized into DS1s.  The
                 value of enabledDs3 indicated that this is a DS3
                 channelized into DS2s.  Setting this object will
                 cause the creation or deletion of DS2 or DS1
                 entries in the ifTable.  "
     ::= { dsx3ConfigEntry 12 }

     dsx3Ds1ForRemoteLoop  OBJECT-TYPE
          SYNTAX      INTEGER (0..29)

          MAX-ACCESS  read-write
          STATUS      current
          DESCRIPTION
                 "Indicates which ds1/e1 on this ds3/e3 will be
                 indicated in the remote ds1 loopback request.  A
                 value of 0 means no DS1 will be looped.  A value
                 of 29 means all ds1s/e1s will be looped."
     ::= { dsx3ConfigEntry 13 }



-- bgs10SDHConfigTable
bgs10SDHConfigTable OBJECT-TYPE
        SYNTAX  SEQUENCE OF BGS10SDHConfigEntry
        MAX-ACCESS      not-accessible
        STATUS  current
        DESCRIPTION
                ""
        ::= { zxbgs10mib 60 }

bgs10SDHConfigEntry OBJECT-TYPE
        SYNTAX  BGS10SDHConfigEntry
        MAX-ACCESS      not-accessible
        STATUS  current
        DESCRIPTION
                "."
        INDEX   { 
                bgs10SDHSonetConfModule,
                bgs10SDHSonetConfPort
                }
        ::= { bgs10SDHConfigTable 1 }
        
BGS10SDHConfigEntry ::=
        SEQUENCE {
                bgs10SDHRowStatus               RowStatus,
                bgs10SDHSonetConfModule         UCHAR,
                bgs10SDHSonetConfPort           UCHAR,
                bgs10SDHMediumType              UCHAR,
                bgs10SDHLineType                UCHAR,
                bgs10SDHLineCodeing             UCHAR,
                bgs10SDHTxClockSource           UCHAR,
                bgs10SDHTxClockClass            UCHAR,
                bgs10SDHRxClockClass            UCHAR,
                bgs10SDHTxScrambling            UCHAR,
                bgs10SDHRxScrambling            UCHAR,
                bgs10SDHIdleUnassignedCells     UCHAR,
                bgs10SDHCellHead                INTEGER,
                bgs10SDHsonetConfLoopbackConfig UCHAR
}

bgs10SDHRowStatus OBJECT-TYPE
        SYNTAX  RowStatus
        MAX-ACCESS      read-write
        STATUS  current
        DESCRIPTION
                "."
        ::= { bgs10SDHConfigEntry 1 }

bgs10SDHSonetConfModule OBJECT-TYPE
        SYNTAX  UCHAR
        MAX-ACCESS      read-write
        STATUS  current
        DESCRIPTION
                "."
        ::= { bgs10SDHConfigEntry 2 }

bgs10SDHSonetConfPort OBJECT-TYPE
        SYNTAX  UCHAR
        MAX-ACCESS      read-write
        STATUS  current
        DESCRIPTION
                "."
        ::= { bgs10SDHConfigEntry 3 }

bgs10SDHMediumType OBJECT-TYPE
        SYNTAX  UCHAR
        MAX-ACCESS      read-write
        STATUS  current
        DESCRIPTION
                "."
        ::= { bgs10SDHConfigEntry 4 }

bgs10SDHLineType OBJECT-TYPE
        SYNTAX  UCHAR
        MAX-ACCESS      read-write
        STATUS  current
        DESCRIPTION
                "."
        ::= { bgs10SDHConfigEntry 5 }

bgs10SDHLineCodeing OBJECT-TYPE
        SYNTAX  UCHAR
        MAX-ACCESS      read-write
        STATUS  current
        DESCRIPTION
                "."
        ::= { bgs10SDHConfigEntry 6 }

bgs10SDHTxClockSource OBJECT-TYPE
        SYNTAX  UCHAR
        MAX-ACCESS      read-write
        STATUS  current
        DESCRIPTION
                "."
        ::= { bgs10SDHConfigEntry 7 }

bgs10SDHTxClockClass OBJECT-TYPE
        SYNTAX  UCHAR
        MAX-ACCESS      read-write
        STATUS  current
        DESCRIPTION
                "."
        ::= { bgs10SDHConfigEntry 8 }

bgs10SDHRxClockClass OBJECT-TYPE
        SYNTAX  UCHAR
        MAX-ACCESS      read-write
        STATUS  current
        DESCRIPTION
                "."
        ::= { bgs10SDHConfigEntry 9 }

bgs10SDHTxScrambling OBJECT-TYPE
        SYNTAX  UCHAR
        MAX-ACCESS      read-write
        STATUS  current
        DESCRIPTION
                "."
        ::= { bgs10SDHConfigEntry 10 }

bgs10SDHRxScrambling OBJECT-TYPE
        SYNTAX  UCHAR
        MAX-ACCESS      read-write
        STATUS  current
        DESCRIPTION
                "."
        ::= { bgs10SDHConfigEntry 11 }

bgs10SDHIdleUnassignedCells OBJECT-TYPE
        SYNTAX  UCHAR
        MAX-ACCESS      read-write
        STATUS  current
        DESCRIPTION
                "."
        ::= { bgs10SDHConfigEntry 12 }

bgs10SDHCellHead OBJECT-TYPE
        SYNTAX  INTEGER
        MAX-ACCESS      read-write
        STATUS  current
        DESCRIPTION
                "."
        ::= { bgs10SDHConfigEntry 13 }

bgs10SDHsonetConfLoopbackConfig OBJECT-TYPE
    SYNTAX   UCHAR
    MAX-ACCESS  read-write
    STATUS  current
    DESCRIPTION
        "."
    ::= { bgs10SDHConfigEntry 14 }



-- bgs10IMAGroupConfTable
bgs10IMAGroupConfTable OBJECT-TYPE
        SYNTAX  SEQUENCE OF BGS10IMAGroupConfEntry
        MAX-ACCESS      not-accessible
        STATUS  current
        DESCRIPTION
                ""
        ::= { zxbgs10mib 61 }

bgs10IMAGroupConfEntry OBJECT-TYPE
        SYNTAX  BGS10IMAGroupConfEntry
        MAX-ACCESS      not-accessible
        STATUS  current
        DESCRIPTION
                "."
        INDEX {
                bgs10ImaGroupBetaValue
                }
        ::= { bgs10IMAGroupConfTable 1 }
        
BGS10IMAGroupConfEntry ::=
        SEQUENCE {
                bgs10ImaGroupRowStatus                  RowStatus,
                bgs10ImaGroupBetaValue                  UCHAR,
                bgs10ImaGroupGammaValue                 UCHAR,
                bgs10ImaGroupAlphaValue                 UCHAR,
                bgs10ImaGroupMinNumTxLinks              UCHAR,
                bgs10ImaGroupNeTxClkMode                UCHAR,
                bgs10ImaGroupMinNumRxLinks              UCHAR,
                bgs10ImaGroupNumTxCfgLnks               UCHAR,
                bgs10ImaGroupNumRxCfgLnks               UCHAR,
                bgs10ImaGroupSymmetry                   UCHAR,
                bgs10ImaGroupTxFrameLength              UCHAR,
                bgs10ImaGroupTxTimingRefLink            UCHAR,
                bgs10ImaGroupTxImaId                    UCHAR,
                bgs10ImaGroupDiffDelayMax               UCHAR,
                bgs10ImaOamLabel                        UCHAR,
                bgs10GroupAdminStatus                   UCHAR,
                bgs10ImaGroupFlag                       UCHAR,
                bgs10StatisticsTime                     Unsigned32,
                bgs10ImaGroupNeState                    UCHAR,
                bgs10ImaAlarmType                       UCHAR,
                bgs10imaGroupVer                        UCHAR,
                bgs10ImaGroupM2SClkMode                 UCHAR,
                bgs10imaGroupLinkScramble               UCHAR                
}

bgs10ImaGroupRowStatus OBJECT-TYPE
        SYNTAX  RowStatus
        MAX-ACCESS      read-write
        STATUS  current
        DESCRIPTION
                "."
        ::= { bgs10IMAGroupConfEntry 1 }

bgs10ImaGroupBetaValue OBJECT-TYPE
        SYNTAX  UCHAR
        MAX-ACCESS      read-write
        STATUS  current
        DESCRIPTION
                "."
        ::= { bgs10IMAGroupConfEntry 2 }

bgs10ImaGroupGammaValue OBJECT-TYPE
        SYNTAX  UCHAR
        MAX-ACCESS      read-write
        STATUS  current
        DESCRIPTION
                "."
        ::= { bgs10IMAGroupConfEntry 3 }

bgs10ImaGroupAlphaValue OBJECT-TYPE
        SYNTAX  UCHAR
        MAX-ACCESS      read-write
        STATUS  current
        DESCRIPTION
                "."
        ::= { bgs10IMAGroupConfEntry 4 }

bgs10ImaGroupMinNumTxLinks OBJECT-TYPE
        SYNTAX  UCHAR
        MAX-ACCESS      read-write
        STATUS  current
        DESCRIPTION
                "."
        ::= { bgs10IMAGroupConfEntry 5 }

bgs10ImaGroupNeTxClkMode OBJECT-TYPE
        SYNTAX  UCHAR
        MAX-ACCESS      read-write
        STATUS  current
        DESCRIPTION
                "."
        ::= { bgs10IMAGroupConfEntry 6 }

bgs10ImaGroupMinNumRxLinks OBJECT-TYPE
        SYNTAX  UCHAR
        MAX-ACCESS      read-write
        STATUS  current
        DESCRIPTION
                "."
        ::= { bgs10IMAGroupConfEntry 7 }

bgs10ImaGroupNumTxCfgLnks OBJECT-TYPE
        SYNTAX  UCHAR
        MAX-ACCESS      read-write
        STATUS  current
        DESCRIPTION
                "."
        ::= { bgs10IMAGroupConfEntry 8 }

bgs10ImaGroupNumRxCfgLnks OBJECT-TYPE
        SYNTAX  UCHAR
        MAX-ACCESS      read-write
        STATUS  current
        DESCRIPTION
                "."
        ::= { bgs10IMAGroupConfEntry 9 }

bgs10ImaGroupSymmetry OBJECT-TYPE
        SYNTAX  UCHAR
        MAX-ACCESS      read-write
        STATUS  current
        DESCRIPTION
                "."
        ::= { bgs10IMAGroupConfEntry 10 }

bgs10ImaGroupTxFrameLength OBJECT-TYPE
        SYNTAX  UCHAR
        MAX-ACCESS      read-write
        STATUS  current
        DESCRIPTION
                "."
        ::= { bgs10IMAGroupConfEntry 11 }

bgs10ImaGroupTxTimingRefLink OBJECT-TYPE
        SYNTAX  UCHAR
        MAX-ACCESS      read-write
        STATUS  current
        DESCRIPTION
                "."
        ::= { bgs10IMAGroupConfEntry 12 }

bgs10ImaGroupTxImaId OBJECT-TYPE
        SYNTAX  UCHAR
        MAX-ACCESS      read-write
        STATUS  current
        DESCRIPTION
                "."
        ::= { bgs10IMAGroupConfEntry 13 }

bgs10ImaGroupDiffDelayMax OBJECT-TYPE
        SYNTAX  UCHAR
        MAX-ACCESS      read-write
        STATUS  current
        DESCRIPTION
                "."
        ::= { bgs10IMAGroupConfEntry 14 }

bgs10ImaOamLabel OBJECT-TYPE
        SYNTAX  UCHAR
        MAX-ACCESS      read-write
        STATUS  current
        DESCRIPTION
                "."
        ::= { bgs10IMAGroupConfEntry 15 }

bgs10GroupAdminStatus OBJECT-TYPE
        SYNTAX  UCHAR
        MAX-ACCESS      read-write
        STATUS  current
        DESCRIPTION
                "."
        ::= { bgs10IMAGroupConfEntry 16 }

bgs10ImaGroupFlag OBJECT-TYPE
        SYNTAX  UCHAR
        MAX-ACCESS      read-write
        STATUS  current
        DESCRIPTION
                "."
        ::= { bgs10IMAGroupConfEntry 17 }

bgs10StatisticsTime OBJECT-TYPE
        SYNTAX  Unsigned32
        MAX-ACCESS      read-write
        STATUS  current
        DESCRIPTION
                "."
        ::= { bgs10IMAGroupConfEntry 18 }

bgs10ImaGroupNeState OBJECT-TYPE
        SYNTAX  UCHAR
        MAX-ACCESS      read-write
        STATUS  current
        DESCRIPTION
                "."
        ::= { bgs10IMAGroupConfEntry 19 }

bgs10ImaAlarmType OBJECT-TYPE
        SYNTAX  UCHAR
        MAX-ACCESS      read-write
        STATUS  current
        DESCRIPTION
                "."
        ::= { bgs10IMAGroupConfEntry 20 }

bgs10imaGroupVer OBJECT-TYPE
    SYNTAX  UCHAR
    MAX-ACCESS  read-write
    STATUS  current
    DESCRIPTION
        "."
    ::= { bgs10IMAGroupConfEntry 21 }
    
bgs10ImaGroupM2SClkMode OBJECT-TYPE
    SYNTAX  UCHAR
    MAX-ACCESS  read-write
    STATUS  current
    DESCRIPTION
        "."
    ::= { bgs10IMAGroupConfEntry 22 }
bgs10imaGroupLinkScramble   OBJECT-TYPE
    SYNTAX      UCHAR
    MAX-ACCESS  read-write
    STATUS  current
    DESCRIPTION
        "."
    ::= { bgs10IMAGroupConfEntry 23 }   


-- bgs10IMALinkConfTable
bgs10IMALinkConfTable OBJECT-TYPE
        SYNTAX  SEQUENCE OF BGS10IMALinkConfEntry
        MAX-ACCESS      not-accessible
        STATUS  current
        DESCRIPTION
                ""
        ::= { zxbgs10mib 62 }

bgs10IMALinkConfEntry OBJECT-TYPE
        SYNTAX  BGS10IMALinkConfEntry
        MAX-ACCESS      not-accessible
        STATUS  current
        DESCRIPTION
                "."
        INDEX {
                bgs10ImaLinkTxLid
                }
        ::= { bgs10IMALinkConfTable 1 }
        
BGS10IMALinkConfEntry ::=
        SEQUENCE {
                bgs10ImaLinkRowStatus                   RowStatus,
                bgs10ImaLinkTxLid                       UCHAR,
                bgs10ImaLinkTxStat                      UCHAR,
                bgs10ImaLinkRxStat                      UCHAR,
                bgs10ImaLinkGroupIndex                  UCHAR,
                bgs10ImaLinkFlag                        UCHAR,
                bgs10ImaLinkStatisticsTime              Unsigned32,
                bgs10imaLinkNeTxAdminStatus             UCHAR,
                bgs10imaLinkNeRxAdminStatus             UCHAR,
                bgs10imaLinkd                           UCHAR
}

bgs10ImaLinkRowStatus OBJECT-TYPE
        SYNTAX  RowStatus
        MAX-ACCESS      read-write
        STATUS  current
        DESCRIPTION
                "."
        ::= { bgs10IMALinkConfEntry 1 }

bgs10ImaLinkTxLid OBJECT-TYPE
        SYNTAX          UCHAR
        MAX-ACCESS      read-write
        STATUS  current
        DESCRIPTION
                "."
        ::= { bgs10IMALinkConfEntry 2 }

bgs10ImaLinkTxStat OBJECT-TYPE
        SYNTAX          UCHAR
        MAX-ACCESS      read-write
        STATUS  current
        DESCRIPTION
                "."
        ::= { bgs10IMALinkConfEntry 3 }

bgs10ImaLinkRxStat OBJECT-TYPE
        SYNTAX          UCHAR
        MAX-ACCESS      read-write
        STATUS  current
        DESCRIPTION
                "."
        ::= { bgs10IMALinkConfEntry 4 }

bgs10ImaLinkGroupIndex OBJECT-TYPE
        SYNTAX          UCHAR
        MAX-ACCESS      read-write
        STATUS  current
        DESCRIPTION
                "."
        ::= { bgs10IMALinkConfEntry 5 }

bgs10ImaLinkFlag OBJECT-TYPE
        SYNTAX          UCHAR
        MAX-ACCESS      read-write
        STATUS  current
        DESCRIPTION
                "."
        ::= { bgs10IMALinkConfEntry 6 }

bgs10ImaLinkStatisticsTime OBJECT-TYPE
        SYNTAX          Unsigned32
        MAX-ACCESS      read-write
        STATUS  current
        DESCRIPTION
                "."
        ::= { bgs10IMALinkConfEntry 7 }

bgs10imaLinkNeTxAdminStatus OBJECT-TYPE
        SYNTAX          UCHAR
        MAX-ACCESS      read-write
        STATUS  current
        DESCRIPTION
                "."
        ::= { bgs10IMALinkConfEntry 8 }

bgs10imaLinkNeRxAdminStatus     OBJECT-TYPE
        SYNTAX          UCHAR
        MAX-ACCESS      read-write
        STATUS  current
        DESCRIPTION
                "."
        ::= { bgs10IMALinkConfEntry 9 }

bgs10imaLinkd   OBJECT-TYPE
    SYNTAX      UCHAR
    MAX-ACCESS  read-write
    STATUS  current
    DESCRIPTION
        "."
    ::= { bgs10IMALinkConfEntry 10 }


-- ATM perfromance mgmt
        
--The TC adapter supplyment
bgs10TcProtoCurTable    OBJECT-TYPE
        SYNTAX          SEQUENCE OF ZXB10TCProtocolEntry
        MAX-ACCESS      not-accessible
        STATUS          current
        DESCRIPTION
                "the plug-in unittable."
        ::= { zxbgs10mib 34 }
        
bgs10TcProtoCurEntry    OBJECT-TYPE
        SYNTAX          ZXB10TCProtocolEntry
        MAX-ACCESS      not-accessible
        STATUS          current
        DESCRIPTION
                "the entry to the TC protocol table."
    INDEX { ifIndex }           
--      AUGMENTS { atmfM4TcProtoCurrEntry }
        ::= { bgs10TcProtoCurTable 1 }
        
ZXB10TCProtocolEntry    ::=
        SEQUENCE {
                zxb10TcProCurPerfModule         UCHAR,
                zxb10TcProCurPerfPort           UCHAR,
                zxb10TcProCurSectionbip8        Gauge32,
                zxb10TcProCurLinebip8           Gauge32,
                zxb10TcProCurLinefebe           Gauge32, 
                zxb10TcProCurPathbip24          Gauge32,
                zxb10TcProCurPathfebe           Gauge32,
                zxb10TcProCurCorrecthcs         Gauge32,
                zxb10TcProCurRxCell                     Gauge32,
                zxb10TcProCurTxCell                     Gauge32
        }

zxb10TcProCurPerfModule         OBJECT-TYPE
        SYNTAX          UCHAR
        MAX-ACCESS      read-only
        STATUS          current
        DESCRIPTION
                "."
        ::= { bgs10TcProtoCurEntry 1 }
        
zxb10TcProCurPerfPort           OBJECT-TYPE
        SYNTAX          UCHAR
        MAX-ACCESS      read-only
        STATUS          current
        DESCRIPTION
                "."
        ::= { bgs10TcProtoCurEntry 2 }
                
zxb10TcProCurSectionbip8        OBJECT-TYPE
        SYNTAX          Gauge32
        MAX-ACCESS      read-only
        STATUS          current
        DESCRIPTION
                "."
        ::= { bgs10TcProtoCurEntry 3 }
        
zxb10TcProCurLinebip8           OBJECT-TYPE
        SYNTAX          Gauge32
        MAX-ACCESS      read-only
        STATUS          current
        DESCRIPTION
                "."
        ::= { bgs10TcProtoCurEntry 4 }
        
        
zxb10TcProCurLinefebe           OBJECT-TYPE
        SYNTAX          Gauge32
        MAX-ACCESS      read-only
        STATUS          current
        DESCRIPTION
                "."
        ::= { bgs10TcProtoCurEntry 5 }
        
zxb10TcProCurPathbip24          OBJECT-TYPE
        SYNTAX          Gauge32
        MAX-ACCESS      read-only
        STATUS          current
        DESCRIPTION
                "."
        ::= { bgs10TcProtoCurEntry 6 }
        
zxb10TcProCurPathfebe           OBJECT-TYPE
        SYNTAX          Gauge32
        MAX-ACCESS      read-only
        STATUS          current
        DESCRIPTION
                "."
        ::= { bgs10TcProtoCurEntry 7 }
        
zxb10TcProCurCorrecthcs         OBJECT-TYPE
        SYNTAX          Gauge32
        MAX-ACCESS      read-only
        STATUS          current
        DESCRIPTION
                "."
        ::= { bgs10TcProtoCurEntry 8 }
        
zxb10TcProCurRxCell                     OBJECT-TYPE
        SYNTAX          Gauge32
        MAX-ACCESS      read-only
        STATUS          current
        DESCRIPTION
                "."
        ::= { bgs10TcProtoCurEntry 9 }
        
zxb10TcProCurTxCell                     OBJECT-TYPE
        SYNTAX          Gauge32
        MAX-ACCESS      read-only
        STATUS          current
        DESCRIPTION
                "."
        ::= { bgs10TcProtoCurEntry 10 }
        
        

--Man-Machine Language MIB
bgs10MMLResultTable OBJECT-TYPE
    SYNTAX      SEQUENCE OF BGS10MMLResultEntry
    MAX-ACCESS  not-accessible
    STATUS      current
    DESCRIPTION
        "A list of Man-Machine language."
    ::= { zxbgs10mib 8}
        
bgs10MMLResultEntry OBJECT-TYPE
    SYNTAX      BGS10MMLResultEntry
    MAX-ACCESS  not-accessible
    STATUS      current
    DESCRIPTION
        "An entry in the table."
    INDEX { bgs10MessageNo  }
    ::= { bgs10MMLResultTable 1}
    
BGS10MMLResultEntry ::=
    SEQUENCE {
        bgs10MMLResultRowStatus     RowStatus,
        bgs10MMLResultErrNumber     UShort
        }
        
bgs10MMLResultRowStatus OBJECT-TYPE
    SYNTAX      RowStatus
    MAX-ACCESS  read-create
    STATUS      current
    DESCRIPTION
        "row status."
    ::= { bgs10MMLResultEntry 1}
    
bgs10MMLResultErrNumber     OBJECT-TYPE
    SYNTAX      UShort
    MAX-ACCESS  read-create
    STATUS      current
    DESCRIPTION
        "row status."
    ::= { bgs10MMLResultEntry 2}


--bgs10NMSServer
bgs10NMSServer  OBJECT-TYPE
    SYNTAX      SEQUENCE OF BGS10NMSServerEntry
    MAX-ACCESS  not-accessible
    STATUS      current
    DESCRIPTION
        "."
    ::= { zxbgs10mib 54}
    
bgs10NMSServerEntry OBJECT-TYPE
    SYNTAX      BGS10NMSServerEntry
    MAX-ACCESS  not-accessible
    STATUS      current
    DESCRIPTION
        "An entry in the table."
    INDEX { 
        bgs10NMSServerIpAddress
        }
    ::= { bgs10NMSServer 1}
    
BGS10NMSServerEntry ::=
    SEQUENCE {
        bgs10NMSServerRowStatus             RowStatus,
        bgs10NMSServerIpAddress             IpAddress,
        bgs10NMSServersnmpversion           UChar
    }

bgs10NMSServerRowStatus OBJECT-TYPE 
    SYNTAX      RowStatus
    MAX-ACCESS  read-write
    STATUS      current
    DESCRIPTION
        ""
    ::= { bgs10NMSServerEntry 1}

bgs10NMSServerIpAddress OBJECT-TYPE 
    SYNTAX      IpAddress
    MAX-ACCESS  read-write
    STATUS      current
    DESCRIPTION
        ""
    ::= { bgs10NMSServerEntry 2}
bgs10NMSServersnmpversion OBJECT-TYPE 
    SYNTAX      UChar
    MAX-ACCESS  read-write
    STATUS      current
    DESCRIPTION
        ""
    ::= { bgs10NMSServerEntry 3}




--The Route Group       
bgs10RouteMIB           OBJECT IDENTIFIER   ::= { zxbgs10mib 3}
    
-- Defintion of objects for route set table.
    
bgs10RouteTable OBJECT-TYPE
    SYNTAX      SEQUENCE OF BGS10RouteEntry
    MAX-ACCESS  not-accessible
    STATUS      current
    DESCRIPTION
        "A list of the route information."
    ::= { bgs10RouteMIB 1}
        
bgs10RouteEntry OBJECT-TYPE
    SYNTAX      BGS10RouteEntry
    MAX-ACCESS  not-accessible
    STATUS      current
    DESCRIPTION
        "An entry to the table."
    INDEX   { bgs10RouteAtmAddress }
    ::= { bgs10RouteTable 1}
        
BGS10RouteEntry ::=
    SEQUENCE {
        bgs10RouteRowStatus         INTEGER,
        bgs10RouteAtmAddressStatus  INTEGER,
        bgs10RouteOperateStatus     INTEGER,
        bgs10RouteNodeNum           UChar,
        bgs10RouteAtmAddress        OCTET STRING,
        bgs10RouteServiceType       INTEGER,
        bgs10RouteRouteSet          UShort,
        bgs10RouteModule            UChar,
        bgs10RouteLength            UChar,
        bgs10RouteServicePID        OCTET STRING(SIZE(4)),
        bgs10RouteDefaultAddrFlag   INTEGER,
        bgs10RouteAddressPlan       INTEGER,
        bgs10RouteAlternateRouteDirect UShort,
        bgs10RouteAlternateRouteTwo UShort,
        bgs10RouteAlternateRouteThree UShort,
        bgs10RouteCurRouteSet       UShort,
        bgs10RouteRouteDirect       UShort,
        bgs10RouteRouteTwo          UShort,
        bgs10RouteRouteThree        UShort
        }
    
bgs10RouteRowStatus OBJECT-TYPE
    SYNTAX      INTEGER
    MAX-ACCESS  read-create
    STATUS      current
    DESCRIPTION 
        "the conteptual row."
    ::= { bgs10RouteEntry 1}
        
bgs10RouteAtmAddressStatus      OBJECT-TYPE
    SYNTAX      INTEGER
    MAX-ACCESS  read-create
    STATUS      current
    DESCRIPTION
        "the status of the ATM address: 0--IISP configure address,1--ILMI."
    ::= { bgs10RouteEntry 2}
        
bgs10RouteOperateStatus     OBJECT-TYPE
    SYNTAX      INTEGER {   up(0),
                            down(1)
                        }
    MAX-ACCESS  read-create
    STATUS      current
    DESCRIPTION
        "the node operate status."
    ::= { bgs10RouteEntry 3}
    
bgs10RouteNodeNum       OBJECT-TYPE
    SYNTAX      UChar
    MAX-ACCESS  read-create
    STATUS      current
    DESCRIPTION
        "the Node Number."
    ::= { bgs10RouteEntry 4}
    
bgs10RouteAtmAddress        OBJECT-TYPE
    SYNTAX      OCTET STRING(SIZE(20))
    MAX-ACCESS  read-create
    STATUS      current
    DESCRIPTION
        "the ATM address."
    ::= { bgs10RouteEntry 5}
    
bgs10RouteServiceType       OBJECT-TYPE
    SYNTAX      INTEGER
    MAX-ACCESS  read-create
    STATUS      current
    DESCRIPTION
        "Route No.4."
    ::= { bgs10RouteEntry 6}    
        
bgs10RouteRouteSet      OBJECT-TYPE
    SYNTAX      UShort
    MAX-ACCESS  read-create
    STATUS      current
    DESCRIPTION
        "RouteSet."
    ::= { bgs10RouteEntry 7}

bgs10RouteModule        OBJECT-TYPE
    SYNTAX      UChar
    MAX-ACCESS  read-create
    STATUS      current
    DESCRIPTION
        "Module No.."
    ::= { bgs10RouteEntry 8}
    
bgs10RouteLength        OBJECT-TYPE
    SYNTAX      UChar
    MAX-ACCESS  read-create
    STATUS      current
    DESCRIPTION
        "route's length."
    ::= { bgs10RouteEntry 9}
    
bgs10RouteServicePID    OBJECT-TYPE
    SYNTAX      OCTET STRING(SIZE(4))
    MAX-ACCESS  read-create
    STATUS      current
    DESCRIPTION
        "Service's PID."
    ::= { bgs10RouteEntry 10}
    
bgs10RouteDefaultAddrFlag       OBJECT-TYPE
    SYNTAX      INTEGER{ default(0),
                         no-default(1)
                       }
    MAX-ACCESS  read-create
    STATUS      current
    DESCRIPTION
        "Address's default flag."
    ::= { bgs10RouteEntry 11}
    
bgs10RouteAddressPlan   OBJECT-TYPE
    SYNTAX      INTEGER{ unknown(0),
                         isdn(1),
                         nsap(2),
                         private(9),
                         reversed(15)
                       }
    MAX-ACCESS  read-create
    STATUS      current
    DESCRIPTION
        "Address's default flag."
    ::= { bgs10RouteEntry 12}
    
bgs10RouteAlternateRouteDirect      OBJECT-TYPE
    SYNTAX      UShort
    MAX-ACCESS  read-create
    STATUS      current
    DESCRIPTION
            "alternate_route_direct."
    ::= { bgs10RouteEntry 13}
    
bgs10RouteAlternateRouteTwo         OBJECT-TYPE
    SYNTAX      UShort
    MAX-ACCESS  read-create
    STATUS      current
    DESCRIPTION
            "alternate_route_two."
    ::= { bgs10RouteEntry 14}

bgs10RouteAlternateRouteThree       OBJECT-TYPE
    SYNTAX      UShort
    MAX-ACCESS  read-create
    STATUS      current
    DESCRIPTION
            "alternate_route_three."
    ::= { bgs10RouteEntry 15}
    
bgs10RouteCurRouteSet              OBJECT-TYPE
    SYNTAX      UShort
    MAX-ACCESS  read-create
    STATUS      current
    DESCRIPTION
            "CurRouteSet."
    ::= { bgs10RouteEntry 16}
    
bgs10RouteRouteDirect       OBJECT-TYPE
    SYNTAX      UShort
    MAX-ACCESS  read-create
    STATUS      current
    DESCRIPTION
            "route_direct."
    ::= { bgs10RouteEntry 17}
    
bgs10RouteRouteTwo      OBJECT-TYPE
    SYNTAX      UShort
    MAX-ACCESS  read-create
    STATUS      current
    DESCRIPTION
            "route_two."
    ::= { bgs10RouteEntry 18}
    
bgs10RouteRouteThree        OBJECT-TYPE
    SYNTAX      UShort
    MAX-ACCESS  read-create
    STATUS      current
    DESCRIPTION
            "route_three."
    ::= { bgs10RouteEntry 19}   







--  zxDslamTrafficGradeParamTable
zxDslamTrafficGradeParamTable    OBJECT-TYPE
        SYNTAX SEQUENCE OF ZxDslamTrafficGradeParamEntry
        MAX-ACCESS      not-accessible
        STATUS          current
        DESCRIPTION
         ""
     ::= { zxDslam 8 }

zxDslamTrafficGradeParamEntry  OBJECT-TYPE
       SYNTAX      ZxDslamTrafficGradeParamEntry
       MAX-ACCESS  not-accessible
       STATUS      current
       DESCRIPTION
               ""
      INDEX           {  zxDslamTrafficGradeParamRowStatus    }
     ::= { zxDslamTrafficGradeParamTable 1 }
       
ZxDslamTrafficGradeParamEntry ::=
          SEQUENCE {
            zxDslamTrafficGradeParamRowStatus       UChar,
            zxDslamTrafficGradeParamIngRate         Unsigned32,
            zxDslamTrafficGradeParamEgRate          Unsigned32
          }
     
zxDslamTrafficGradeParamRowStatus   OBJECT-TYPE
         SYNTAX   UChar
         MAX-ACCESS  read-write
         STATUS      current
         DESCRIPTION
               "" 
     ::= { zxDslamTrafficGradeParamEntry 1 }       
zxDslamTrafficGradeParamIngRate   OBJECT-TYPE
         SYNTAX   Unsigned32
         MAX-ACCESS  read-write
         STATUS      current
         DESCRIPTION
               "" 
     ::= { zxDslamTrafficGradeParamEntry 2 }       
zxDslamTrafficGradeParamEgRate   OBJECT-TYPE
         SYNTAX   Unsigned32
         MAX-ACCESS  read-write
         STATUS      current
         DESCRIPTION
               "" 
     ::= { zxDslamTrafficGradeParamEntry 3 }       

 zxDslamatmfAtmServiceTypeTable   OBJECT-TYPE
    SYNTAX SEQUENCE OF ZxDslamatmfAtmServiceTypeEntry
    MAX-ACCESS not-accessible
    STATUS current
    DESCRIPTION
    "The ATM Forum ILMI Auto Configuration Extension ATM
    Service Type Information. "
    ::= { zxDslam 9  }
 
 zxDslamatmfAtmServiceTypeEntry OBJECT-TYPE
    SYNTAX ZxDslamatmfAtmServiceTypeEntry
    MAX-ACCESS not-accessible
    STATUS current
    DESCRIPTION
    "An entry in the service type table describes the reference
    information about a service that may be associated with
    individual ATM connections for the purpose of auto-
    configuration. This information describe the name and sub-
    name of the service, the client layer protocol using the ATM
    service, the TM 4.0 service category, and the TM 4.0
    conformance definition."
    INDEX { ifIndex }
--     AUGMENTS { atmfAtmServiceTypeEntry   }
    ::= { zxDslamatmfAtmServiceTypeTable 1 }
        
 ZxDslamatmfAtmServiceTypeEntry ::= SEQUENCE {
    atmfAtmServiceTypeRowStatus     UCHAR
    }
 
 atmfAtmServiceTypeRowStatus OBJECT-TYPE
    SYNTAX UCHAR
    MAX-ACCESS read-only
    STATUS current
    DESCRIPTION  " "
    ::= { zxDslamatmfAtmServiceTypeEntry  1 }
 
    
 zxDslamatmfAtmServiceConnInfoTable  OBJECT-TYPE
    SYNTAX SEQUENCE OF ZxDslamatmfAtmServiceConnInfoEntry
    MAX-ACCESS not-accessible
    STATUS current
    DESCRIPTION
    "The ATM Forum ILMI Auto Configuration Extension ATM
    Service Connection Information. "
    ::= { zxDslam 10 }
    
 zxDslamatmfAtmServiceConnInfoEntry OBJECT-TYPE
    SYNTAX ZxDslamatmfAtmServiceConnInfoEntry 
    MAX-ACCESS not-accessible
    STATUS current
    DESCRIPTION
    "An entry in the service connection information table
    describes the ATM connection that provides a service across
    an ATM interface. The connection is identified by port and
    VPI/VCI value. Information about the connection includes the
    connection type (VP or VC, SVC or PVC), and the association of
    the connection with a service type. Specific connection
    information, such as traffic descriptors, should be accessed
    in the atmfVpc and atmfVcc tables defined in ILMI. "
 -- INDEX { atmfAtmServicePortIndex, atmfAtmServiceVpi,atmfAtmServiceVci}
    INDEX { ifIndex }
   
--     AUGMENTS { atmfAtmServiceConnInfoEntry   }
    ::= { zxDslamatmfAtmServiceConnInfoTable  1 }
 
 ZxDslamatmfAtmServiceConnInfoEntry ::= SEQUENCE {
    atmfAtmServiceRowStatus     UCHAR
    }
    
 atmfAtmServiceRowStatus OBJECT-TYPE
    SYNTAX UCHAR
    MAX-ACCESS read-only
    STATUS current
    DESCRIPTION
    "The value of 0 (zero)has the special meaning of identifying
    the ATM Interface over which this ILMI message was received. "
    ::= { zxDslamatmfAtmServiceConnInfoEntry 1 }    
 
 zxDslamatmfAAL1ProfileTable OBJECT-TYPE
    SYNTAX SEQUENCE OF ZxDslamatmfAAL1ProfileEntry
    MAX-ACCESS not-accessible
    STATUS current
    DESCRIPTION
    "The ATM Forum ILMI Auto Configuration Extension AAL1
    Profile Information. "
    ::= { zxDslam 11}
    
 zxDslamatmfAAL1ProfileEntry OBJECT-TYPE
    SYNTAX ZxDslamatmfAAL1ProfileEntry
    MAX-ACCESS not-accessible
    STATUS current
    DESCRIPTION
    "An entry in the AAL1 Profile table provides data that
    describes the AAL1 processing function. "
 
--     AUGMENTS { atmfAAL1ProfileEntry  }
    INDEX { ifIndex }
     
    -- INDEX { atmfAAL1ProfileIndex }
    ::= { zxDslamatmfAAL1ProfileTable 1 }
 
 ZxDslamatmfAAL1ProfileEntry ::= SEQUENCE {
    atmfAAL1RowStatus   UCHAR
    }
 
 atmfAAL1RowStatus OBJECT-TYPE
    SYNTAX UCHAR
    MAX-ACCESS read-only
    STATUS current
    DESCRIPTION
    "A number between which identifies the entry in the AAL1
    Profile Table. "
    ::= { zxDslamatmfAAL1ProfileEntry 1 }
 
 --zxDslamatmfAAL34ProfileTable
 zxDslamatmfAAL34ProfileTable OBJECT-TYPE
    SYNTAX SEQUENCE OF ZxDslamatmfAAL34ProfileEntry
    MAX-ACCESS not-accessible
    STATUS current
    DESCRIPTION
    "The ATM Forum ILMI Auto Configuration Extension AAL3/4
    Profile Information. "
    ::= {zxDslam 12 }
    
 zxDslamatmfAAL34ProfileEntry OBJECT-TYPE
    SYNTAX ZxDslamatmfAAL34ProfileEntry
    MAX-ACCESS not-accessible
    STATUS current
    DESCRIPTION
    "An entry in the AAL34 Profile table provides data that
    describes the AAL3/4 processing function. "
 -- INDEX { atmfAAL34ProfileIndex }
--     AUGMENTS { atmfAAL34ProfileEntry }
    INDEX { ifIndex }

    ::= { zxDslamatmfAAL34ProfileTable 1 }
    
 ZxDslamatmfAAL34ProfileEntry ::= SEQUENCE {
    atmfAAL34RowStatus      UCHAR
    }
    
 atmfAAL34RowStatus  OBJECT-TYPE
    SYNTAX UCHAR
    MAX-ACCESS read-only
    STATUS current
    DESCRIPTION
    "A number between which identifies the entry in the AAL3/4
    Profile Table. "
    ::= { zxDslamatmfAAL34ProfileEntry 1 }
 
 zxDslamatmfAAL5ProfileTable OBJECT-TYPE
    SYNTAX SEQUENCE OF ZxDslamatmfAAL5ProfileEntry
    MAX-ACCESS not-accessible
    STATUS current
    DESCRIPTION
    "The ATM Forum ILMI Auto Configuration Extension AAL5
    Profile Information. "
    ::= { zxDslam 13 }
    
 zxDslamatmfAAL5ProfileEntry OBJECT-TYPE
    SYNTAX ZxDslamatmfAAL5ProfileEntry
    MAX-ACCESS not-accessible
    STATUS current
    DESCRIPTION
    "An entry in the AAL5 Profile table provides data that
    describes the AAL5 processing function. "
 -- INDEX { atmfAAL5ProfileIndex }
--     AUGMENTS { atmfAAL5ProfileEntry  }
    INDEX { ifIndex }
    ::= { zxDslamatmfAAL5ProfileTable 1 }
    
 ZxDslamatmfAAL5ProfileEntry ::= SEQUENCE {
    atmfAAL5RowStatus       UCHAR,
    atmfAAL5ProfileName     DisplayString
    }
    
 atmfAAL5RowStatus OBJECT-TYPE
    SYNTAX  UCHAR
    MAX-ACCESS read-only
    STATUS current
    DESCRIPTION
    " "
    ::= { zxDslamatmfAAL5ProfileEntry 1 }
 
 atmfAAL5ProfileName OBJECT-TYPE
     SYNTAX DisplayString (SIZE (1..33))
     MAX-ACCESS read-write
     STATUS current
     DESCRIPTION
         "
          The AAL5 Profile Name."
 ::= { zxDslamatmfAAL5ProfileEntry 2 }
 
 
 

zxDslamatmfAAL2ProfileTable OBJECT-TYPE
    SYNTAX SEQUENCE OF ZxDslamatmfAAL2ProfileEntry
    MAX-ACCESS not-accessible
    STATUS current
    DESCRIPTION
    "The ATM Forum ILMI Auto Configuration Extension AAL5
    Profile Information. "
    ::= { zxDslam 14 }
    
zxDslamatmfAAL2ProfileEntry OBJECT-TYPE
    SYNTAX ZxDslamatmfAAL2ProfileEntry
    MAX-ACCESS not-accessible
    STATUS current
    DESCRIPTION
    "An entry in the AAL2 Profile table provides data that
    describes the AAL2 processing function. "
    INDEX { ifIndex }
    ::= { zxDslamatmfAAL2ProfileTable 1 }
    
ZxDslamatmfAAL2ProfileEntry ::= SEQUENCE {
    atmfAAL2RowStatus       UCHAR
    }
    
atmfAAL2RowStatus OBJECT-TYPE
    SYNTAX  UCHAR
    MAX-ACCESS read-only
    STATUS current
    DESCRIPTION
    " "
    ::= { zxDslamatmfAAL2ProfileEntry 1 }



-- Dslam APS Mgmt Obj

zxDslamAPSLogicPortTable OBJECT-TYPE
    SYNTAX SEQUENCE OF ZxDslamAPSLogicPortEntry
    MAX-ACCESS not-accessible
    STATUS current
    DESCRIPTION
    "The APS 1+1 logic  port Information. "
    ::= { zxDslam 15 }
    
zxDslamAPSLogicPortEntry OBJECT-TYPE
    SYNTAX ZxDslamAPSLogicPortEntry
    MAX-ACCESS not-accessible
    STATUS current
    DESCRIPTION
    "An entry in the APS logic port table . "
    INDEX { zxDslamAPSLogicPort }
    ::= { zxDslamAPSLogicPortTable 1 }
    
ZxDslamAPSLogicPortEntry ::= SEQUENCE {
    zxDslamAPSLogicPortRowStatus                UCHAR,     
    zxDslamAPSLogicPort                         UCHAR,
    zxDslamAPSLogicPortSdhApsOptSet             UCHAR,
    zxDslamAPSLogicPortSdhApsLockSet            UCHAR,
    zxDslamAPSLogicPortSdhApsReverSet           UCHAR,
    zxDslamAPSLogicPortSdhApsServiceTransPort   UCHAR,
    zxDslamAPSLogicPortsdThresh                 UCHAR,
    zxDslamAPSLogicPortsfThresh                 UCHAR,
    zxDslamAPSLogicPortholdtime                 UCHAR,
    zxDslamAPSLogicPortSwitchReson              UCHAR,
    zxDslamAPSLogicPortSwitchResult             UCHAR,
    zxDslamAPSLogicPortRecoverTime              UCHAR,
    zxDslamAPSLogicPortSwitchChannel            UCHAR
    
    }                                     

zxDslamAPSLogicPortRowStatus OBJECT-TYPE             
    SYNTAX  UCHAR                         
    MAX-ACCESS read-write                 
    STATUS current                        
    DESCRIPTION
    " "
    ::= { zxDslamAPSLogicPortEntry 1 }  

zxDslamAPSLogicPort OBJECT-TYPE             
    SYNTAX  UCHAR                         
    MAX-ACCESS read-write                 
    STATUS current                        
    DESCRIPTION
    " "
    ::= { zxDslamAPSLogicPortEntry 2 }
                                          
zxDslamAPSLogicPortSdhApsOptSet OBJECT-TYPE             
    SYNTAX  UCHAR                         
    MAX-ACCESS read-write                 
    STATUS current                        
    DESCRIPTION
    " "
    ::= { zxDslamAPSLogicPortEntry 3 }

zxDslamAPSLogicPortSdhApsLockSet OBJECT-TYPE             
    SYNTAX  UCHAR                         
    MAX-ACCESS read-write                 
    STATUS current                        
    DESCRIPTION
    " "
    ::= { zxDslamAPSLogicPortEntry 4 }
    
zxDslamAPSLogicPortSdhApsReverSet OBJECT-TYPE             
    SYNTAX  UCHAR                         
    MAX-ACCESS read-write                 
    STATUS current                        
    DESCRIPTION
    " "
    ::= { zxDslamAPSLogicPortEntry 5 }
    
zxDslamAPSLogicPortSdhApsServiceTransPort OBJECT-TYPE             
    SYNTAX  UCHAR                         
    MAX-ACCESS read-write                 
    STATUS current                        
    DESCRIPTION
    " "
    ::= { zxDslamAPSLogicPortEntry 6 }
    
zxDslamAPSLogicPortsdThresh OBJECT-TYPE             
    SYNTAX  UCHAR                         
    MAX-ACCESS read-write                 
    STATUS current                        
    DESCRIPTION
    " "
    ::= { zxDslamAPSLogicPortEntry 7 }
    
zxDslamAPSLogicPortsfThresh OBJECT-TYPE             
    SYNTAX  UCHAR                         
    MAX-ACCESS read-write                 
    STATUS current                        
    DESCRIPTION
    " "
    ::= { zxDslamAPSLogicPortEntry 8 }
    
zxDslamAPSLogicPortholdtime OBJECT-TYPE             
    SYNTAX  UCHAR                         
    MAX-ACCESS read-write                 
    STATUS current                        
    DESCRIPTION
    " "
    ::= { zxDslamAPSLogicPortEntry 9 }
    
zxDslamAPSLogicPortSwitchReson OBJECT-TYPE             
    SYNTAX  UCHAR                         
    MAX-ACCESS read-write                 
    STATUS current                        
    DESCRIPTION
    " "
    ::= { zxDslamAPSLogicPortEntry 10 }
    
zxDslamAPSLogicPortSwitchResult OBJECT-TYPE             
    SYNTAX  UCHAR                         
    MAX-ACCESS read-write                 
    STATUS current                        
    DESCRIPTION
    " "
    ::= { zxDslamAPSLogicPortEntry 11 }



zxDslamAPSLogicPortRecoverTime OBJECT-TYPE             
    SYNTAX  UCHAR                         
    MAX-ACCESS read-write                 
    STATUS current                        
    DESCRIPTION
    " "
    ::= { zxDslamAPSLogicPortEntry 12 }

zxDslamAPSLogicPortSwitchChannel OBJECT-TYPE             
    SYNTAX  UCHAR                         
    MAX-ACCESS read-write                 
    STATUS current                        
    DESCRIPTION
    " 0:switch to working port; 1:switch to standby port "
    ::= { zxDslamAPSLogicPortEntry 13 }




--The Communication Alarm(SDH)
--The following traps are for ZXB10 and its successors.

bgs10CommSDHTraps                       OBJECT IDENTIFIER ::= { zxbgs10Traps 5 }
bgs10CommSDHTrapsPrefix         OBJECT IDENTIFIER ::= { bgs10CommSDHTraps 0 }

--The LCD Alarm has defined in ATM Forum af-nm-0095.001:atmf4IfLcdAlarm
--(atmfM4MIBTrapPrefix 2 },so it isn't necessary to redefine it.

bgs10CommSDHTroolAlarm  NOTIFICATION-TYPE
        OBJECTS {       ifOperStatus,
                                atmfM4TrapAlarmSeverity
                        }
        STATUS  current
        DESCRIPTION
                "indicates that transmitting reference out of lock(Abbr:TROOL) has
                occurred (PM5346 clip)."
        ::= { bgs10CommSDHTrapsPrefix 1 }
        
bgs10CommSDHRdoolAlarm  NOTIFICATION-TYPE
        OBJECTS {       ifOperStatus,
                                atmfM4TrapAlarmSeverity
                        }
        STATUS  current
        DESCRIPTION
                "Indicates that recieving data out of lock (Abbr:RDOOL) has
                occurred (PM5346 clip)."
        ::= { bgs10CommSDHTrapsPrefix 2 }

bgs10CommSDHOofAlarm            NOTIFICATION-TYPE
        OBJECTS {       ifOperStatus,
                                atmfM4TrapAlarmSeverity
                        }
        STATUS  current
        DESCRIPTION
                "Indicates that an OOFD Alarm condition has occurred(created by 
                PM5346 clip)."
        ::= { bgs10CommSDHTrapsPrefix 3 }

--The LOF Alarm has been defined by ATM Forum af-nm-0095.001:atmfM4LofAlarm
--(atmfM4MIBTrapPrefix 3).Here should not redefine it.
 
--The LOS Alarm has been defined by ATM Forum af-nm-0095.001:atmfM4LosAlarm
--(atmfM4MIBTrapPrefix 5).Here should not redefine it.

--The RDI Alarm has been defined in ATM Forum af-nm-0095.001:atmfM4RdiAlarm
--(atmfM4MIBTrapPrefix 9), Here define two Alarms sbout it: one for line,
--another for path.

bgs10CommSDHLRdiAlarm   NOTIFICATION-TYPE
        OBJECTS {       ifOperStatus,
                                atmfM4TrapAlarmSeverity
                        }
        STATUS  current
        DESCRIPTION
                "Indicates that an line RDI Alarm condition has occurred(created
                by PM5346 clip)."
        ::= { bgs10CommSDHTrapsPrefix 4 }
        
bgs10CommSDHPRdiAlarm   NOTIFICATION-TYPE
        OBJECTS {       ifOperStatus,
                                atmfM4TrapAlarmSeverity
                        }
        STATUS  current
        DESCRIPTION
                "indicates that a path RDT Alarm condition has occurred(created
                by PM5346 clip)."
        ::= { bgs10CommSDHTrapsPrefix 5  }
  
--The AIS Alarm has been defined in ATM Forum af-nm-0095.001:atmfM4AisAlarm
--(atmfM4MIBTrapPrefix 9), Here define two Alarms sbout it: one for line,
--another for path.
bgs10CommSDHLAisAlarm   NOTIFICATION-TYPE
        OBJECTS {       ifOperStatus,
                                atmfM4TrapAlarmSeverity
                        }
        STATUS  current
        DESCRIPTION
                "Indicates that a line Ais Alarm condition has occurred(created 
                by PM5346 clip)."
        ::= { bgs10CommSDHTrapsPrefix 6 }
        
bgs10CommSDHPAisAlarm   NOTIFICATION-TYPE
        OBJECTS {       ifOperStatus,
                                atmfM4TrapAlarmSeverity
                        }
        STATUS  current
        DESCRIPTION
                "Indicates that a path AIS Alarm condition has occurred(created
                by PM5346 clip)."
        ::= { bgs10CommSDHTrapsPrefix 7 }

bgs10CommSDHRroolAlarm  NOTIFICATION-TYPE
        OBJECTS {       ifOperStatus,
                                atmfM4TrapAlarmSeverity
                        }
        STATUS  current
        DESCRIPTION
                "Indicates that the recieving reference clock is out of lock(created
                PM5346)."
        ::= { bgs10CommSDHTrapsPrefix 8 }
        
--the atmfM4IfLopAlarm has defined LOP Alarm in ATM Forum af-nm-0095.001
--So here don't redefine it.

--the ATM Alarm has defined in ATM Forum af-nm-0095.001. So here should not
--redefine them.

        
bgs10Cardtraps                  OBJECT IDENTIFIER       ::= { zxbgs10Traps 8 }
bgs10CardTrapsPrefix    OBJECT IDENTIFIER       ::= { bgs10Cardtraps 0 }

bgs10CardOnLineStatus                   NOTIFICATION-TYPE
        OBJECTS {       bgs10PlugInUnitCardType,
                                atmfM4PlugInUnitAvailStatus,
                                bgs10PlugInUnitMasterStatus
                        }
        STATUS  current
        DESCRIPTION
                "the card stats's notification ."
        ::= { bgs10CardTrapsPrefix 1 }
        
bgs10PerfTraps                  OBJECT IDENTIFIER       ::= { zxbgs10Traps 9 }
bgs10PerfTrapsPrefix    OBJECT IDENTIFIER       ::= { bgs10PerfTraps 0 }

bgs10PerfPortDiscardHECViolCell         NOTIFICATION-TYPE
        OBJECTS {       alarmValue,
                                alarmRisingThreshold,
                                alarmFallingThreshold,
                                atmfM4TrapAlarmSeverity
                        }
        STATUS  current
        DESCRIPTION
                "the discard violate cells ."
        ::= { bgs10PerfTrapsPrefix 1 }
        
bgs10UpcNpcDisagreementCell                             NOTIFICATION-TYPE
        OBJECTS {       alarmValue,
                                alarmRisingThreshold,
                                atmfM4TrapAlarmSeverity
                        }
        STATUS  current
        DESCRIPTION
                "the UPC/NPC disagreement cells ."
        ::= { bgs10PerfTrapsPrefix 2 }
        
bgs10OAMLoopback        NOTIFICATION-TYPE
        OBJECTS {       bgs10PmLoopBackTestIndex,
                                bgs10PmLoopBackTestResult
                        }
        STATUS  current
        DESCRIPTION
                "the OAM loop-back test notification ."
        ::= { bgs10PerfTrapsPrefix 3 }
        
bgs10OAMLoopbackTestOver NOTIFICATION-TYPE
        OBJECTS {       bgs10PmLoopBackTestIndex,
                                bgs10PmLoopBackTestResult
                        }
        STATUS  current
        DESCRIPTION
                "the OAM loop-back test notification ."
        ::= { bgs10PerfTrapsPrefix 4 }



--The Fans' Alarm, different from ATM Forum

bgs10FanTraps                           OBJECT IDENTIFIER       ::= { zxbgs10Traps 11 }
bgs10FanTrapsPrefix                     OBJECT IDENTIFIER       ::= { bgs10FanTraps 0 }

bgs10Fan1Alarm                  NOTIFICATION-TYPE
        OBJECTS {       atmfM4TrapAlarmSeverity
                        }
        STATUS  current
        DESCRIPTION
                "The Alarm of Fan No.1"
        ::= { bgs10FanTrapsPrefix 1}
        
bgs10Fan2Alarm                  NOTIFICATION-TYPE
        OBJECTS {       atmfM4TrapAlarmSeverity
                        }
        STATUS  current
        DESCRIPTION
                "The Alarm of Fan No.2"
        ::= { bgs10FanTrapsPrefix 2}
        
        
bgs10Fan3Alarm                  NOTIFICATION-TYPE
        OBJECTS {       atmfM4TrapAlarmSeverity
                        }
        STATUS  current
        DESCRIPTION
                "The Alarm of Fan No.3"
        ::= { bgs10FanTrapsPrefix 3}


bgs10Fan4Alarm                  NOTIFICATION-TYPE
        OBJECTS {       atmfM4TrapAlarmSeverity
                        }
        STATUS  current
        DESCRIPTION
                "The Alarm of Fan No.4"
        ::= { bgs10FanTrapsPrefix 4}


--the E3 Traps
bgs10E3Traps                    OBJECT IDENTIFIER       ::= { zxbgs10Traps 16 }
bgs10E3TrapsPrefix              OBJECT IDENTIFIER       ::= { bgs10E3Traps 0 }

bgs10E3RAIAlarm NOTIFICATION-TYPE
        OBJECTS {       entPhysicalContainedIn,
                                entPhysicalParentRelPos,
                                entPhysicalClass,
                                atmfM4TrapAlarmSeverity
                        }
        STATUS  current
        DESCRIPTION
                "the RAI Alarm of the E3 Physical  Port."
        ::= { bgs10E3TrapsPrefix 1 }
        
bgs10E3LOFAlarm NOTIFICATION-TYPE
        OBJECTS {       entPhysicalContainedIn,
                                entPhysicalParentRelPos,
                                entPhysicalClass,
                                atmfM4TrapAlarmSeverity
                        }
        STATUS  current
        DESCRIPTION
                "the LOF Alarm of the E3 Physical  Port."
        ::= { bgs10E3TrapsPrefix 2 }
        
bgs10E3LOSAlarm NOTIFICATION-TYPE
        OBJECTS {       entPhysicalContainedIn,
                                entPhysicalParentRelPos,
                                entPhysicalClass,
                                atmfM4TrapAlarmSeverity
                        }
        STATUS  current
        DESCRIPTION
                "the LOS Alarm of the E3 Physical  Port."
        ::= { bgs10E3TrapsPrefix 3 }

bgs10E3AISAlarm NOTIFICATION-TYPE
        OBJECTS {       entPhysicalContainedIn,
                                entPhysicalParentRelPos,
                                entPhysicalClass,
                                atmfM4TrapAlarmSeverity
                        }
        STATUS  current
        DESCRIPTION
                "the AIS Alarm of the E3 Physical  Port."
        ::= { bgs10E3TrapsPrefix 4 }
        
bgs10E3FERFAlarm        NOTIFICATION-TYPE
        OBJECTS {       entPhysicalContainedIn,
                                entPhysicalParentRelPos,
                                entPhysicalClass,
                                atmfM4TrapAlarmSeverity
                        }
        STATUS  current
        DESCRIPTION
                "the FERF Alarm of the E3 Physical  Port."
        ::= { bgs10E3TrapsPrefix 5 }

bgs10E3LCDAlarm NOTIFICATION-TYPE
        OBJECTS {       entPhysicalContainedIn,
                                entPhysicalParentRelPos,
                                entPhysicalClass,
                                atmfM4TrapAlarmSeverity
                        }
        STATUS  current
        DESCRIPTION
                "the LCD Alarm of the E3 Physical  Port."
        ::= { bgs10E3TrapsPrefix 6 }
        
--the PVC Traps
bgs10PVCTraps                   OBJECT IDENTIFIER       ::= { zxbgs10Traps 17 }
bgs10PVCTrapsPrefix             OBJECT IDENTIFIER       ::= { bgs10PVCTraps 0 }

bgs10PVCNIAlarm NOTIFICATION-TYPE
        OBJECTS {       bgs10PvcLModule,
                                bgs10PvcLPort,
                                bgs10PvcLVpi,
                                bgs10PvcLVci,
                                atmfM4TrapAlarmSeverity
                        }
        STATUS  current
        DESCRIPTION
                "the PVCNI Alarm ."
        ::= { bgs10PVCTrapsPrefix 1 }
        

--The POS Alarm
bgs10POSTraps                   OBJECT IDENTIFIER       ::= { zxbgs10Traps 19 }
bgs10POSTrapsPrefix             OBJECT IDENTIFIER       ::= { bgs10POSTraps 0 }

bgs10POSLOS                     NOTIFICATION-TYPE
        OBJECTS {               entPhysicalContainedIn,
                                entPhysicalParentRelPos,
                                entPhysicalClass,
                                atmfM4TrapAlarmSeverity
                }
        STATUS  current
        DESCRIPTION
                "The port  Alarm of POS LOS"
        ::= { bgs10POSTrapsPrefix 1}

bgs10POSLOF                     NOTIFICATION-TYPE
        OBJECTS {               entPhysicalContainedIn,
                                entPhysicalParentRelPos,
                                entPhysicalClass,
                                atmfM4TrapAlarmSeverity
                }
        STATUS  current
        DESCRIPTION
                "The port  Alarm of POS LOF"
        ::= { bgs10POSTrapsPrefix 2}

bgs10POSLOP                     NOTIFICATION-TYPE
        OBJECTS {               entPhysicalContainedIn,
                                entPhysicalParentRelPos,
                                entPhysicalClass,
                                atmfM4TrapAlarmSeverity
                }
        STATUS  current
        DESCRIPTION
                "The port  Alarm of POS LOP"
        ::= { bgs10POSTrapsPrefix 3}

bgs10POSAISL                    NOTIFICATION-TYPE
        OBJECTS {               entPhysicalContainedIn,
                                entPhysicalParentRelPos,
                                entPhysicalClass,
                                atmfM4TrapAlarmSeverity
                }
        STATUS  current
        DESCRIPTION
                "The port  Alarm of POS AIS-L"
        ::= { bgs10POSTrapsPrefix 4}

bgs10POSRDIL                    NOTIFICATION-TYPE
        OBJECTS {               entPhysicalContainedIn,
                                entPhysicalParentRelPos,
                                entPhysicalClass,
                                atmfM4TrapAlarmSeverity
                }
        STATUS  current
        DESCRIPTION
                "The port  Alarm of POS RDI-L"
        ::= { bgs10POSTrapsPrefix 5}

bgs10POSAISP                    NOTIFICATION-TYPE
        OBJECTS {               entPhysicalContainedIn,
                                entPhysicalParentRelPos,
                                entPhysicalClass,
                                atmfM4TrapAlarmSeverity
                }
        STATUS  current
        DESCRIPTION
                "The port  Alarm of POS AISP"
        ::= { bgs10POSTrapsPrefix 6}

bgs10POSRDIP                    NOTIFICATION-TYPE
        OBJECTS {               entPhysicalContainedIn,
                                entPhysicalParentRelPos,
                                entPhysicalClass,
                                atmfM4TrapAlarmSeverity
                }
        STATUS  current
        DESCRIPTION
                "The port  Alarm of POS RDI-P-P"
        ::= { bgs10POSTrapsPrefix 7}



--  zxDslamTraps    
 
--zxDslamMibTableLastChangeTrap 
zxDslamMibTableLastChangeTrap NOTIFICATION-TYPE
           OBJECTS { zxDslamMibTableLastChange }
           STATUS  current
           DESCRIPTION
               "A zxDslamMibTableLastChangeTrap trap signifies that the zxDslamMibDataLoadEntry has 
                been changed"
       ::= { zxDslamTraps 0 1 }  

--zxDslamCommandModifyDataTrap
zxDslamCommandModifyDataTrap    NOTIFICATION-TYPE
           OBJECTS { zxDslamMibTableLastChange }
           STATUS  current
           DESCRIPTION
               "A zxDslamMibTableLastChangeTrap trap signifies that the zxDslamMibDataLoadEntry has 
                been changed"
       ::= { zxDslamTraps 0 2 }  




END

------------------------------------------------------------------------------
------------------------------------------------------------------------------
--
--  File         : vdslmib.mib
--  Description  : VDSL mib
--  Version      : 0.00   
--  Date         : Mar 01, 2003     
--
--  Copyright (c) 2003-2005 ZTE, Inc.  All Rights Reserved.
--
------------------------------------------------------------------------------
------------------------------------------------------------------------------
--  VDSL MIB
--
--  NOTES:
--   1. This is a SMIv2 MIB.
--
--   2. The following groups are supported in this MIB:
--      - oemArchIface  Configure/retrieve architecture interface specific info
--	  - vdslGeneralTable
--	  - vdslLinkTable
--	  - ethernetConfig   	
--      - oemChipIface  Configure/retrieve chipset interface specific info
--
------------------------------------------------------------------------------
------------------------------------------------------------------------------

    VDSL-MIB DEFINITIONS ::= BEGIN

    IMPORTS
        MODULE-IDENTITY, OBJECT-TYPE, NOTIFICATION-TYPE,
        Integer32, Counter64,TimeTicks,Counter32,enterprises            FROM SNMPv2-SMI
        
        DisplayString, TruthValue,               
        MacAddress, RowStatus				FROM SNMPv2-TC
        
        SnmpAdminString                         FROM SNMP-FRAMEWORK-MIB

	zxDslam				FROM ZXDSLAM-MIB
        
        MODULE-COMPLIANCE, OBJECT-GROUP         FROM SNMPv2-CONF;    
        


zxVdsl MODULE-IDENTITY
LAST-UPDATED "2003200300Z"
ORGANIZATION ""
CONTACT-INFO ""
DESCRIPTION  ""
::= { zxDslam 5 } 
    

zxVdslMibObjects    OBJECT IDENTIFIER ::= { zxVdsl 1 }
zxVdslTrap          OBJECT IDENTIFIER ::= { zxVdsl 2 }


   zxVdslMaxCfgProfileNum OBJECT-TYPE
          SYNTAX  INTEGER 
          MAX-ACCESS  read-only
          STATUS  current
          DESCRIPTION
                  "The maximum number of profiles."
          ::= { zxVdslMibObjects 1 }
          
          
------------------------------------------------------------------------------------
------------------------------------------------------------------------------------
--  
--	vdsl Config Table 
--
   zxVdslConfigTable OBJECT-TYPE
        SYNTAX  SEQUENCE OF ZxVdslCfgEntry
        MAX-ACCESS  not-accessible
        STATUS  current
        DESCRIPTION
              "A table that contains general config information 
	      about every VDSL port that is associated with this switch."
        ::= { zxVdslMibObjects 2 }
        
   zxVdslCfgEntry  OBJECT-TYPE
        SYNTAX  ZxVdslCfgEntry
        MAX-ACCESS  not-accessible
        STATUS  current
        DESCRIPTION
                "A list of general VDSL information for each port."
        INDEX  { zxVdslCfgIndex  }
        ::= { zxVdslConfigTable 1 }


   ZxVdslCfgEntry ::=
        SEQUENCE {
            zxVdslCfgIndex           	     INTEGER,
            zxVdslNtTrigAutonego             INTEGER, 
	        zxVdslNtad100full                INTEGER,
	        zxVdslNtad100half                INTEGER,
	        zxVdslNtad10full                 INTEGER,
	        zxVdslNtad10half                 INTEGER,
	        zxVdslNtTrigForce                INTEGER,
	        zxVdslNtForceSpeed               INTEGER,
            zxVdslNtForceDuplex              INTEGER,
            zxVdslCfgProfile          	     SnmpAdminString,
                                             
            zxVdslCfgRowstatus               RowStatus,
            zxVdslLoopBackType               INTEGER,         
            zxVdslPerfStatisticTableIdList   Unsigned32,
            zxVdslPerfStatisticAction        INTEGER
        }       
        
   zxVdslCfgIndex OBJECT-TYPE
          SYNTAX  	INTEGER (1..244)
          MAX-ACCESS  	not-accessible
          STATUS  	current
          DESCRIPTION
                  "The index of the VDSL config table. it associate 
                  with port."
          ::= { zxVdslCfgEntry 1 }

   zxVdslNtTrigAutonego OBJECT-TYPE
          SYNTAX  INTEGER {
	                  enable(1),
	                  disable(2)
		  }
          MAX-ACCESS  read-create
          STATUS  current
          DESCRIPTION
                 "trig autonego process of remote modem of the port."
          ::= { zxVdslCfgEntry 2 }

  zxVdslNtad100full OBJECT-TYPE
          SYNTAX  INTEGER {
		    adenable(1),
		    addisable(2)
	          }
          MAX-ACCESS  read-create
          STATUS  current
          DESCRIPTION
                 "advertise ability of nt mac of the port."
          ::= { zxVdslCfgEntry 3 }
  
  zxVdslNtad100half OBJECT-TYPE
          SYNTAX  INTEGER {
		    adenable(1),
		    addisable(2)
	          }
          MAX-ACCESS  read-create
          STATUS  current
          DESCRIPTION
                 "advertise ability of nt mac of the port."
          ::= { zxVdslCfgEntry 4 }
  
  zxVdslNtad10full OBJECT-TYPE
          SYNTAX  INTEGER {
		    adenable(1),
		    addisable(2)
	          }
          MAX-ACCESS  read-create
          STATUS  current
          DESCRIPTION
                 "advertise ability of nt mac of the port."
          ::= { zxVdslCfgEntry 5 }
  
  zxVdslNtad10half OBJECT-TYPE
          SYNTAX  INTEGER {
		    adenable(1),
		    addisable(2)
	          }
          MAX-ACCESS  read-create
          STATUS  current
          DESCRIPTION
                 "advertise ability of nt mac of the port."
          ::= { zxVdslCfgEntry 6 }
  
  zxVdslNtTrigForce OBJECT-TYPE
          SYNTAX  INTEGER {
		          enable(1),
		          disable(2)			  
	          }
          MAX-ACCESS  read-create
          STATUS  current
          DESCRIPTION
                 "trig force process of remote modem of the port."
          ::= { zxVdslCfgEntry 7 }

  zxVdslNtForceSpeed OBJECT-TYPE
          SYNTAX  INTEGER {
		          vforce10M(1),
			  vforce100M(2)
	          }
          MAX-ACCESS  read-create
          STATUS  current
          DESCRIPTION
                 "speed used with force process of remote modem of the port."
          ::= { zxVdslCfgEntry 8 }

  zxVdslNtForceDuplex OBJECT-TYPE
          SYNTAX  INTEGER {
		          vforcehalf(1),
			  vforcefull(2)
	          }
          MAX-ACCESS  read-create
          STATUS  current
          DESCRIPTION
                 "duplex mode used with force process of NT of the port."
          ::= { zxVdslCfgEntry 9 }

   zxVdslCfgProfile OBJECT-TYPE
      SYNTAX      SnmpAdminString (SIZE(1..32))
      MAX-ACCESS  read-write
      STATUS      current
      DESCRIPTION
        "This object is a pointer to a VDSL configuration profile in 
        the zxVdslConfProfileTable.  The value of this object is the
        index of the referenced profile in the zxVdslConfProfileTable.
        Note that VDSL configuration profiles are only applicable to 
        VDSL lines.  
        Any attempt to set this object to a value that is not the value
        of the index for an active entry in the profile table,
        zxVdslConfProfileTable, MUST be rejected."
      ::= { zxVdslCfgEntry 10 }
      
   zxVdslCfgRowstatus OBJECT-TYPE
          SYNTAX  RowStatus
          MAX-ACCESS  read-create
          STATUS  current
          DESCRIPTION
                  "This object is used to create and delete rows in the
                   zxVdslConfigTable."
          ::= { zxVdslCfgEntry 11 }
          
  zxVdslLoopBackType OBJECT-TYPE
          SYNTAX  INTEGER 
          MAX-ACCESS  read-create
          STATUS  current
          DESCRIPTION
                  " vdsl link loop type, the value is 0 no loop  1 LTLcLoop  
                  2 LTLnLoop  3 NTLnLoop"
          ::= { zxVdslCfgEntry 12 }
          
  zxVdslPerfStatisticTableIdList  OBJECT-TYPE
          SYNTAX  Unsigned32 
          MAX-ACCESS  read-create
          STATUS  current
          DESCRIPTION
                  " bitmap of vdsl perf ,the value is 0x00002000"
          ::= { zxVdslCfgEntry 13 }
          
   zxVdslPerfStatisticAction OBJECT-TYPE
          SYNTAX  INTEGER 
          MAX-ACCESS  read-create
          STATUS  current
          DESCRIPTION
                  " switch of perf   0: disable  1: enable"
          ::= { zxVdslCfgEntry 14 }
      
------------------------------------------------------------------------------------
------------------------------------------------------------------------------------
--  
--	vdsl Config Profile Table 
--
   zxVdslConfProfileTable OBJECT-TYPE
        SYNTAX  SEQUENCE OF ZxVdslCfgProfEntry
        MAX-ACCESS  not-accessible
        STATUS  current
        DESCRIPTION
              "A table that contains general config information profiles
	      about every VDSL port that is associated with this switch."
        ::= { zxVdslMibObjects 3 }
        
   zxVdslCfgProfEntry  OBJECT-TYPE
        SYNTAX  ZxVdslCfgProfEntry
        MAX-ACCESS  not-accessible
        STATUS  current
        DESCRIPTION
                "A list of general VDSL information profiles for each port."
        INDEX  { zxVdslCfgProfName  }
        ::= { zxVdslConfProfileTable 1 }


   ZxVdslCfgProfEntry ::=
        SEQUENCE {
            zxVdslCfgProfName          	SnmpAdminString,
            zxVdslLinkUpInterp  	    INTEGER,
            zxVdslLinkDownInterp  	    INTEGER,
            zxVdslLinkUpConste  	    INTEGER,
            zxVdslLinkDownConste  	    INTEGER,
            zxVdslLinkUpFreq  		    INTEGER,
            zxVdslLinkDownFreq  	    INTEGER,
            zxVdslLinkPowerBack  	    INTEGER,
            zxVdslLinkLTMaxPSD       	INTEGER,
            zxVdslLinkNTMaxPSD       	INTEGER,
	        zxVdslLinkNTMinPSD       	INTEGER,
            zxVdslLinkLTTransNotch 	    INTEGER,
            zxVdslLinkNTTransNotch 	    INTEGER,
            zxVdslLinkLTInterDepth	    INTEGER,
            zxVdslLinkNTInterDepth	    INTEGER,
	        zxVdslLinkAutochg           INTEGER	,
	        zxVdslLinkReserved1         INTEGER,
	        zxVdslLinkReserved2         INTEGER,
	        zxVdslLinkReserved3         INTEGER,
	        zxVdslLinkReserved4         INTEGER,
	        zxVdslLinkReserved5         INTEGER,
	        zxVdslLinkReserved6         INTEGER,
	        zxVdslLinkReserved7         INTEGER,
	        zxVdslLinkReserved8         INTEGER,
	        zxVdslLinkReserved9         INTEGER,
	        zxVdslLinkReserved10        INTEGER,
	        zxVdslCfgProfRowStatus      RowStatus,
	        
	        zxVdslCfgProfUserNum        INTEGER,
	        zxVdslLinkCfgMode           INTEGER
        }
      
   zxVdslCfgProfName OBJECT-TYPE
      SYNTAX      SnmpAdminString (SIZE(1..32))
      MAX-ACCESS  not-accessible
      STATUS      current
      DESCRIPTION
        "This object is the unique index associated with this profile.
         Entries in this table are referenced via the object
         zxVdslCfgProfile in zxVdslCfgEntry."
      ::= { zxVdslCfgProfEntry 1 }

   zxVdslLinkUpInterp OBJECT-TYPE
          SYNTAX  INTEGER 
          MAX-ACCESS  read-create
          STATUS  current
          DESCRIPTION
                  ""
          ::= { zxVdslCfgProfEntry 2 }

   zxVdslLinkDownInterp OBJECT-TYPE
          SYNTAX  INTEGER 
          MAX-ACCESS  read-create
          STATUS  current
          DESCRIPTION
                  ""
          ::= { zxVdslCfgProfEntry 3 }

   zxVdslLinkUpConste OBJECT-TYPE
          SYNTAX  INTEGER 
          MAX-ACCESS  read-create
          STATUS  current
          DESCRIPTION
                  ""
          ::= { zxVdslCfgProfEntry 4 }

   zxVdslLinkDownConste OBJECT-TYPE
          SYNTAX  INTEGER 
          MAX-ACCESS  read-create
          STATUS  current
          DESCRIPTION
                  ""
          ::= { zxVdslCfgProfEntry 5 }

   zxVdslLinkUpFreq OBJECT-TYPE
          SYNTAX  INTEGER(0..800) 
          MAX-ACCESS  read-create
          STATUS  current
          DESCRIPTION
                  "Linkup frequence of the port."
          ::= { zxVdslCfgProfEntry 6 }

   zxVdslLinkDownFreq OBJECT-TYPE
          SYNTAX  INTEGER(0..800) 
          MAX-ACCESS  read-create
          STATUS  current
          DESCRIPTION
                  "Linkdown frequence of the port."
          ::= { zxVdslCfgProfEntry 7 }

   zxVdslLinkPowerBack OBJECT-TYPE
          SYNTAX  INTEGER {
	               enable(1),
		       disable(2)
                  }
          MAX-ACCESS  read-create
          STATUS  current
          DESCRIPTION
                  "power back off mode enable/disable of the port."
          ::= { zxVdslCfgProfEntry 8 }

   zxVdslLinkLTMaxPSD OBJECT-TYPE
          SYNTAX  INTEGER(55..100) 
          MAX-ACCESS  read-create
          STATUS  current
          DESCRIPTION 
          	"Max PSD of the port."
          ::= { zxVdslCfgProfEntry 9 }

   zxVdslLinkNTMaxPSD OBJECT-TYPE
          SYNTAX  INTEGER(55..100)
          MAX-ACCESS  read-create
          STATUS  current
          DESCRIPTION
                  "NT MAX PSD of the port."
          ::= { zxVdslCfgProfEntry 10 }

   zxVdslLinkNTMinPSD OBJECT-TYPE
          SYNTAX  INTEGER(55..100)
          MAX-ACCESS  read-create
          STATUS  current
          DESCRIPTION
                  "NT MIN PSD of the port."
          ::= { zxVdslCfgProfEntry 11 }

   zxVdslLinkLTTransNotch OBJECT-TYPE
          SYNTAX  INTEGER{
	               enable(1),
		       disable(2)
                  }
          MAX-ACCESS  read-create
          STATUS  current
          DESCRIPTION
                  "LT transmit notch of the port."
          ::= { zxVdslCfgProfEntry 12 }

   zxVdslLinkNTTransNotch OBJECT-TYPE
          SYNTAX  INTEGER {
	               enable(1),
		       disable(2)
                  }
          MAX-ACCESS  read-create
          STATUS  current
          DESCRIPTION
                  "NT transmit notch of the port."
          ::= { zxVdslCfgProfEntry 13 }

   zxVdslLinkLTInterDepth OBJECT-TYPE
          SYNTAX  INTEGER 
          MAX-ACCESS  read-create
          STATUS  current
          DESCRIPTION
                  ""
          ::= { zxVdslCfgProfEntry 14 }

   zxVdslLinkNTInterDepth OBJECT-TYPE
          SYNTAX  INTEGER 
          MAX-ACCESS  read-create
          STATUS  current
          DESCRIPTION
                  ""
          ::= { zxVdslCfgProfEntry 15 }

   zxVdslLinkAutochg OBJECT-TYPE
          SYNTAX  INTEGER{
                      enable(1),
		       disable(2)
	          		} 
          MAX-ACCESS  read-create
          STATUS  current
          DESCRIPTION
                  "Link speed auto change enable/disable of the port."
          ::= { zxVdslCfgProfEntry 16 }
                  
   zxVdslLinkReserved1 OBJECT-TYPE
          SYNTAX  INTEGER
          MAX-ACCESS  read-only
          STATUS  current
          DESCRIPTION
                  "Reserved."
          ::= { zxVdslCfgProfEntry 17 }

   zxVdslLinkReserved2 OBJECT-TYPE
          SYNTAX  INTEGER
          MAX-ACCESS  read-only
          STATUS  current
          DESCRIPTION
                  "Reserved."
          ::= { zxVdslCfgProfEntry 18 }

   zxVdslLinkReserved3 OBJECT-TYPE
          SYNTAX  INTEGER
          MAX-ACCESS  read-only
          STATUS  current
          DESCRIPTION
                  "Reserved."
          ::= { zxVdslCfgProfEntry 19 }
          
   zxVdslLinkReserved4 OBJECT-TYPE
          SYNTAX  INTEGER
          MAX-ACCESS  read-only
          STATUS  current
          DESCRIPTION
                  "Reserved."
          ::= { zxVdslCfgProfEntry 20 }

   zxVdslLinkReserved5 OBJECT-TYPE
          SYNTAX  INTEGER
          MAX-ACCESS  read-only
          STATUS  current
          DESCRIPTION
                  "Reserved."
          ::= { zxVdslCfgProfEntry 21 }
   
   zxVdslLinkReserved6 OBJECT-TYPE
          SYNTAX  INTEGER
          MAX-ACCESS  read-only
          STATUS  current
          DESCRIPTION
                  "Reserved."
          ::= { zxVdslCfgProfEntry 22 }
   
   zxVdslLinkReserved7 OBJECT-TYPE
          SYNTAX  INTEGER
          MAX-ACCESS  read-only
          STATUS  current
          DESCRIPTION
                  "Reserved."
          ::= { zxVdslCfgProfEntry 23 }

   zxVdslLinkReserved8 OBJECT-TYPE
          SYNTAX  INTEGER
          MAX-ACCESS  read-only
          STATUS  current
          DESCRIPTION
                  "Reserved."
          ::= { zxVdslCfgProfEntry 24 }

   zxVdslLinkReserved9 OBJECT-TYPE
          SYNTAX  INTEGER
          MAX-ACCESS  read-only
          STATUS  current
          DESCRIPTION
                  "Reserved."
          ::= { zxVdslCfgProfEntry 25 }

   zxVdslLinkReserved10 OBJECT-TYPE
          SYNTAX  INTEGER
          MAX-ACCESS  read-only
          STATUS  current
          DESCRIPTION
                  "Reserved."
          ::= { zxVdslCfgProfEntry 26 }

   zxVdslCfgProfRowStatus OBJECT-TYPE
          SYNTAX  RowStatus
          MAX-ACCESS  read-create
          STATUS  current
          DESCRIPTION
                  "This object is used to create and delete rows in the
                   zxVdslConfProfileTable."
          ::= { zxVdslCfgProfEntry 27 }
          
   zxVdslCfgProfUserNum OBJECT-TYPE
          SYNTAX  INTEGER 
          MAX-ACCESS  read-create
          STATUS  current
          DESCRIPTION
                  " link num of using this profile  Min is 0  Max is DISLAM_PORT_MAX "
          ::= { zxVdslCfgProfEntry 28 }
          
   zxVdslLinkCfgMode OBJECT-TYPE
          SYNTAX  INTEGER 
          MAX-ACCESS  read-create
          STATUS  current
          DESCRIPTION
                  " profile mod  from 1 to 20 "
          ::= { zxVdslCfgProfEntry 29 }
          
-------------------------------------------------------------------------------          
--
-- This is VDSL statisitc table
--
   zxVdslStatTable OBJECT-TYPE
        SYNTAX  SEQUENCE OF ZxVdslStatEntry
        MAX-ACCESS  not-accessible
        STATUS  current
        DESCRIPTION
              "A table that contains general status information 
	      about every VDSL port that is associated with this switch."
        ::= { zxVdslMibObjects 4 }

   zxVdslStatEntry  OBJECT-TYPE
        SYNTAX   ZxVdslStatEntry
        MAX-ACCESS  not-accessible
        STATUS  current
        DESCRIPTION
                "A list of general VDSL information for each port."
        INDEX  { zxVdslCfgIndex  }
        ::= { zxVdslStatTable 1 }


   ZxVdslStatEntry ::=
        SEQUENCE {
            zxVdslStatSNR          	    INTEGER,
            zxVdslStatMSE         	    INTEGER,
            zxVdslStatCRSE       	    INTEGER,
            zxVdslStatTPower    	    INTEGER,
            zxVdslStatLnkStat       	INTEGER,
            zxVdslStatLnkFail     	    INTEGER,
            zxVdslStatPMDStat       	INTEGER,
            zxVdslNTStatSNR       	    INTEGER,
            zxVdslNTStatMSE    	        INTEGER,
            zxVdslNTStatCRSE       	    INTEGER,
            zxVdslNTStatTPower      	INTEGER,
            zxVdslRecvPauseFrames 	    INTEGER,
            zxVdslRecvBroadcastFrames 	INTEGER,
            zxVdslCollisionCounters   	INTEGER,
            zxVdslSingleCollision   	INTEGER,
            zxVdslMultipleCollision   	INTEGER,
            zxVdslLateCollision   	    INTEGER,
            zxVdslExcessiveCollision  	Counter32,
            zxVdslErrorCounters       	Counter32,
            zxVdslReceivedError       	Counter32,
            zxVdslCarrierError       	Counter32,
            zxVdslFrameTooLongError   	Counter32,
            zxVdslFrameCRCError       	Counter32,
            zxVdslLinkUpRate  		    INTEGER,
            zxVdslLinkDownRate  	    INTEGER,            
       	    zxVdslLinkCurUSRate         INTEGER,
	        zxVdslLinkCurDSRate         INTEGER,
            zxVdslEthphylink            INTEGER,
            zxVdslEthphyNegoDone        INTEGER,
            zxVdslEthNtSpeed            INTEGER,
            zxVdslEthNtDuplex           INTEGER,
            zxVdslEthLtSpeed            INTEGER,
            zxVdslEthLtDuplex           INTEGER,
            
            ZxVdslStatRowstatus         RowStatus,
            zxVdslifInOctets                  INTEGER,
            zxVdslifOutOctets                   INTEGER,
            zxVdslifOutOctets                 INTEGER,
            zxVdslifOutFrame                  INTEGER
	}	

   zxVdslStatSNR OBJECT-TYPE
          SYNTAX  	INTEGER
          MAX-ACCESS  	read-only
          STATUS  	current
          DESCRIPTION
                  "The SNR of recv signal of the port ."
          ::= { zxVdslStatEntry 1 }

   zxVdslStatMSE OBJECT-TYPE
          SYNTAX  	INTEGER
          MAX-ACCESS  	read-only
          STATUS  	current
          DESCRIPTION
                  "The mean square error of the port ."
          ::= { zxVdslStatEntry 2 }

   zxVdslStatCRSE OBJECT-TYPE
          SYNTAX  	INTEGER 
          MAX-ACCESS  	read-only
          STATUS  	current
          DESCRIPTION
                  "The corrected rs error of the port ."
          ::= { zxVdslStatEntry 3 }

   zxVdslStatTPower OBJECT-TYPE
          SYNTAX  	INTEGER 
          MAX-ACCESS  	read-only
          STATUS  	current
          DESCRIPTION
                  "The tramsmit power of the port ."
          ::= { zxVdslStatEntry 4 }

   zxVdslStatLnkStat OBJECT-TYPE
          SYNTAX  	INTEGER {
	       up(1),
               down(2),
               testing(3)
	  }
          MAX-ACCESS  	read-only
          STATUS  	current
          DESCRIPTION
                  "The vdsl link state of the port ."
          ::= { zxVdslStatEntry 5 }

   zxVdslStatLnkFail OBJECT-TYPE
          SYNTAX  	INTEGER 
          MAX-ACCESS  	read-only
          STATUS  	current
          DESCRIPTION
                  "The link fail count of the port ."
          ::= { zxVdslStatEntry 6 }

   zxVdslStatPMDStat OBJECT-TYPE
          SYNTAX  	INTEGER {
	      microInter(0),
              agcConverged(1),
              timConverged(2),
              adcSaturation(3)
          }
          MAX-ACCESS  	read-only
          STATUS  	current
          DESCRIPTION
                  "The PMD state of the port ."
          ::= { zxVdslStatEntry 7 }

   zxVdslNTStatSNR OBJECT-TYPE
          SYNTAX  	INTEGER
          MAX-ACCESS  	read-only
          STATUS  	current
          DESCRIPTION
                  " ."
          ::= { zxVdslStatEntry 8 }

   zxVdslNTStatMSE OBJECT-TYPE
          SYNTAX  	INTEGER 
          MAX-ACCESS  	read-only
          STATUS  	current
          DESCRIPTION
                  " ."
          ::= { zxVdslStatEntry 9 }

   zxVdslNTStatCRSE OBJECT-TYPE
          SYNTAX  	INTEGER 
          MAX-ACCESS  	read-only
          STATUS  	current
          DESCRIPTION
                  "."
          ::= { zxVdslStatEntry 10 }

   zxVdslNTStatTPower OBJECT-TYPE
          SYNTAX  	INTEGER 
          MAX-ACCESS  	read-only
          STATUS  	current
          DESCRIPTION
                  "."
          ::= { zxVdslStatEntry 11 }

   zxVdslRecvPauseFrames OBJECT-TYPE
          SYNTAX  	INTEGER
          MAX-ACCESS  	read-only
          STATUS  	current
          DESCRIPTION
                  "Received pause frame couter ."
          ::= { zxVdslStatEntry 12 }

   zxVdslRecvBroadcastFrames OBJECT-TYPE
          SYNTAX  	INTEGER 
          MAX-ACCESS  	read-only
          STATUS  	current
          DESCRIPTION
                  "Received broadcast frame couter."
          ::= { zxVdslStatEntry 13 }

   zxVdslCollisionCounters OBJECT-TYPE
          SYNTAX  	INTEGER 
          MAX-ACCESS  	read-only
          STATUS  	current
          DESCRIPTION
                  ""
          ::= { zxVdslStatEntry 14 }

   zxVdslSingleCollision OBJECT-TYPE
          SYNTAX  	INTEGER 
          MAX-ACCESS  	read-only
          STATUS  	current
          DESCRIPTION
                  ""
          ::= { zxVdslStatEntry 15 }

   zxVdslMultipleCollision OBJECT-TYPE
          SYNTAX  	INTEGER 
          MAX-ACCESS  	read-only
          STATUS  	current
          DESCRIPTION
                  ""
          ::= { zxVdslStatEntry 16 }

   zxVdslLateCollision OBJECT-TYPE
          SYNTAX  	INTEGER 
          MAX-ACCESS  	read-only
          STATUS  	current
          DESCRIPTION
                  ""
          ::= { zxVdslStatEntry 17 }

   zxVdslExcessiveCollision OBJECT-TYPE
          SYNTAX  	Counter32
          MAX-ACCESS  	read-only
          STATUS  	current
          DESCRIPTION
                  ""
          ::= { zxVdslStatEntry 18 }

   zxVdslErrorCounters OBJECT-TYPE
          SYNTAX  	Counter32
          MAX-ACCESS  	read-only
          STATUS  	current
          DESCRIPTION
                  "Error frame couter."
          ::= { zxVdslStatEntry 19 }

   zxVdslReceivedError OBJECT-TYPE
          SYNTAX  	Counter32
          MAX-ACCESS  	read-only
          STATUS  	current
          DESCRIPTION
                  "Received error frame couter ."
          ::= { zxVdslStatEntry 20 }

   zxVdslCarrierError OBJECT-TYPE
          SYNTAX  	Counter32
          MAX-ACCESS  	read-only
          STATUS  	current
          DESCRIPTION
                  "Error frame couter due to carrier error."
          ::= { zxVdslStatEntry 21 }

   zxVdslFrameTooLongError OBJECT-TYPE
          SYNTAX  	Counter32
          MAX-ACCESS  	read-only
          STATUS  	current
          DESCRIPTION
                  "Error frame couter due to frame too long."
          ::= { zxVdslStatEntry 22 }

   zxVdslFrameCRCError OBJECT-TYPE
          SYNTAX  	Counter32
          MAX-ACCESS  	read-only
          STATUS  	current
          DESCRIPTION
                  "Error frame couter due to CRC error. "
          ::= { zxVdslStatEntry 23 }

   zxVdslLinkUpRate OBJECT-TYPE
          SYNTAX  INTEGER 
          MAX-ACCESS  read-only
          STATUS  current
          DESCRIPTION
                  "Linkup Rate of the port."
          ::= { zxVdslStatEntry 24 }

   zxVdslLinkDownRate OBJECT-TYPE
          SYNTAX  INTEGER 
          MAX-ACCESS  read-only
          STATUS  current
          DESCRIPTION
                  "Linkdown rate of the port."
          ::= { zxVdslStatEntry 25 }

   zxVdslLinkCurUSRate OBJECT-TYPE
          SYNTAX  INTEGER
          MAX-ACCESS  read-only
          STATUS  current
          DESCRIPTION
                  "Current  US rate of the port."
          ::= { zxVdslStatEntry 26 }

   zxVdslLinkCurDSRate OBJECT-TYPE
          SYNTAX  INTEGER
          MAX-ACCESS  read-only
          STATUS  current
          DESCRIPTION
                  "Current  DS rate of the port."
          ::= { zxVdslStatEntry 27 }
          
   zxVdslEthphylink OBJECT-TYPE
          SYNTAX  INTEGER {
                          ethlinking(1),
                          ethbroken(2) 
	          }
          MAX-ACCESS  read-only
          STATUS  current
          DESCRIPTION
                 "ether link state of NT of the port."
          ::= { zxVdslStatEntry 28 }

   zxVdslEthphyNegoDone OBJECT-TYPE
          SYNTAX  INTEGER {
		          negodone(1),
			  negonotdone(2)
	          }
          MAX-ACCESS  read-only
          STATUS  current
          DESCRIPTION
                 "autonego complete state of NT of the port."
          ::= { zxVdslStatEntry 29 }

   zxVdslEthNtSpeed OBJECT-TYPE
          SYNTAX  INTEGER {
		          v10M(1),
			  v100M(2)
	          }
          MAX-ACCESS  read-only
          STATUS  current
          DESCRIPTION
                 "speed of nt phy of the port."
          ::= { zxVdslStatEntry 30 }

   zxVdslEthNtDuplex OBJECT-TYPE
          SYNTAX  INTEGER {
		          vhalf(1),
			  vfull(2)
	          }
          MAX-ACCESS  read-only
          STATUS  current
          DESCRIPTION
                 "duplex mode of nt phy of the port."
          ::= { zxVdslStatEntry 31 }

   zxVdslEthLtSpeed OBJECT-TYPE
          SYNTAX  INTEGER {
		          v10M(1),
			  v100M(2)
	          }
          MAX-ACCESS  read-only
          STATUS  current
          DESCRIPTION
                 "speed of lt smi reg of the port."
          ::= { zxVdslStatEntry 32 }

   zxVdslEthLtDuplex OBJECT-TYPE
          SYNTAX  INTEGER {
		          vhalf(1),
			  vfull(2)
	          }
          MAX-ACCESS  read-only
          STATUS  current
          DESCRIPTION
                 "duplex mode of lt smi reg of the port."
          ::= { zxVdslStatEntry 33 }
          
   ZxVdslStatRowstatus OBJECT-TYPE
          SYNTAX  RowStatus
          MAX-ACCESS  read-create
          STATUS  current
          DESCRIPTION
                  "This object is used to create and delete rows in the
                   zxVdslStatTable."
          ::= { zxVdslStatEntry 34 }
          
   zxVdslifInOctets OBJECT-TYPE
          SYNTAX  INTEGER
          MAX-ACCESS  read-only
          STATUS  current
          DESCRIPTION
                  "Current In Octets of the port."
          ::= { zxVdslStatEntry 35 }
          
   zxVdslifInFrame OBJECT-TYPE
          SYNTAX  INTEGER
          MAX-ACCESS  read-only
          STATUS  current
          DESCRIPTION
                  "Current In Frame of the port."
          ::= { zxVdslStatEntry 36 }
          
  zxVdslifOutOctets OBJECT-TYPE
          SYNTAX  INTEGER
          MAX-ACCESS  read-only
          STATUS  current
          DESCRIPTION
                  "Current Out Octets of the port."
          ::= { zxVdslStatEntry 37 }
   
   zxVdslifOutFrame OBJECT-TYPE
          SYNTAX  INTEGER
          MAX-ACCESS  read-only
          STATUS  current
          DESCRIPTION
                  "Current Out Frame of the port."
          ::= { zxVdslStatEntry 38 }
 
-- ----------------------------------------------------------------------------
   END
