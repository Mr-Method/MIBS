ATM-FORUM-SNMP-M4-MIB DEFINITIONS ::= BEGIN
     IMPORTS
         MODULE-IDENTITY, OBJECT-TYPE,
         Integer32, Gauge32,
         Unsigned32              FROM SNMPv2-SMI
         TEXTUAL-CONVENTION, DisplayString,
         entPhysicalIndex                    FROM ENTITY-MIB
         ifIndex                             FROM IF-MIB
         atmfM4SnmpNEView                    FROM IANAifType-MIB
         atmVclEntry, atmVclVpi, atmVclVci,
         atmVplVpi                           FROM ATM-MIB;
 
 atmfM4MIB MODULE-IDENTITY
     LAST-UPDATED "9805140000Z"
     ORGANIZATION "The ATM Forum"
     CONTACT-INFO
         "The ATM Forum
         2570 West El Camino Real, Suite 304
         Mountain View, CA 94040-1313 USA
         Phone: +1 415-949-6700
         Fax: +1 415-949-6705
         info@atmforum.com"
     DESCRIPTION 
         "This MIB module is the SNMP version of the ATM Forum's
         M4 interface (network element view)."
     REVISION "9805140000Z"
     DESCRIPTION
         "Initial version of MIB module ATM-FORUM-SNMP-M4-MIB."
     ::= { atmfM4SnmpNEView 1 }
 
 atmfM4MIBObjects OBJECT IDENTIFIER ::= { atmfM4MIB 1 }
 
 -- ATM Forum M4 Plug-In Unit Table
      atmfM4PlugInUnitTable OBJECT-TYPE
          SYNTAX SEQUENCE OF AtmfM4PlugInUnitEntry
          MAX-ACCESS not-accessible
          STATUS current
          DESCRIPTION
              "The ATM Forum M4 Plug-In Unit table. This table augments
              the entPhysicalTable."
          ::= { atmfM4MIBObjects 30 }
      atmfM4PlugInUnitEntry OBJECT-TYPE
          SYNTAX AtmfM4PlugInUnitEntry
          MAX-ACCESS not-accessible
          STATUS current
          DESCRIPTION
              "An entry in the ATM Forum M4 Plug-In Unit table. Each
              entry of this table represents a piece of equipment within
              the ATM NE that is inserted into and removed from an
              Equipment Holder."
          INDEX { entPhysicalIndex  }
          ::= { atmfM4PlugInUnitTable 1 }
      AtmfM4PlugInUnitEntry ::= SEQUENCE {
              atmfM4PlugInUnitAdminStatus INTEGER,  
              atmfM4PlugInUnitAvailStatus INTEGER,
             atmfM4PlugInUnitOperStatus INTEGER,
             atmfM4PlugInUnitVendor DisplayString,
             atmfM4PlugInUnitVersion AutonomousType,
            atmfM4PlugInUnitAlarmSeverityIndex Integer32
            }
      atmfM4PlugInUnitAdminStatus OBJECT-TYPE
                  SYNTAX INTEGER {
                  up(1),
                  down(2)
                  }
          MAX-ACCESS read-write
          STATUS current
          DESCRIPTION
              "Used by the administrator to lock and unlock the object."
              ::= { atmfM4PlugInUnitEntry 1 }
      atmfM4PlugInUnitAvailStatus OBJECT-TYPE
              SYNTAX INTEGER {
              available(1),
              inTest(2),
              failed(3),
              powerOff(4),
              notInstalled(5),
              offLine(6),
              dependency(7)
              }
          MAX-ACCESS read-only
          STATUS current
          DESCRIPTION
              "Provides further information regarding the state of the
              component."
          ::= { atmfM4PlugInUnitEntry 2 }
      atmfM4PlugInUnitOperStatus OBJECT-TYPE
              SYNTAX INTEGER {
              up(1),
              down(2),
              unknown(3)
              }
          MAX-ACCESS read-only
          STATUS current
          DESCRIPTION
              "This attributes identifies whether or not the component is
              capable of performing its normal functions."
          ::= { atmfM4PlugInUnitEntry 3 }
      atmfM4PlugInUnitVendor OBJECT-TYPE
          SYNTAX DisplayString
          MAX-ACCESS read-only
          STATUS current
          DESCRIPTION
              "The vendor of the component."
          ::= { atmfM4PlugInUnitEntry 4 }
      atmfM4PlugInUnitVersion OBJECT-TYPE
          SYNTAX AutonomousType
          MAX-ACCESS read-only
          STATUS current
          DESCRIPTION
              "The version of the component."
          ::= { atmfM4PlugInUnitEntry 5 }
      atmfM4PlugInUnitAlarmSeverityIndex OBJECT-TYPE
          SYNTAX Integer32
          MAX-ACCESS read-write
          STATUS current
          DESCRIPTION
              "An index into the alarm severity profile table, specifying
              the severity assignments for M4 alarms reported for this
              component. The default value of this object is zero."
          ::= { atmfM4PlugInUnitEntry 6 }
  
   
  
 
-- ATM Forum M4 Interface Configuration Table Extensions
-- ATM Cell Layer
 atmfM4AtmLayerTable OBJECT-TYPE
     SYNTAX SEQUENCE OF AtmfM4AtmLayerEntry
     MAX-ACCESS not-accessible
     STATUS current
     DESCRIPTION
         "The ATM Forum M4 interface Configuration table extensions
         for the ATM cell layer."
     ::= { atmfM4MIBObjects 8 }
 
 atmfM4AtmLayerEntry OBJECT-TYPE
     SYNTAX AtmfM4AtmLayerEntry
     MAX-ACCESS not-accessible
     STATUS current
     DESCRIPTION
         "Columns conceptually added to the interface table
         entry for an ATM interface to model the ATM cell layer.
         The row of the interface table modeling this object should
         also include columns for the physical path TP and TC Adapter
         object, as well as the ATM interface table defined in
         RFC 1695.
         The default configuration of an entry in this table is
         used whenever the entries for the physical path TP, etc.,
         are created. The management system configures a UNI,
         B-ICI, or B-ISSI on the interface by first modifying the
         atmfM4IfType column (this can be done in the same SNMP
         set-request that sets up the other necessary variables."
     INDEX { ifIndex }
     ::= { atmfM4AtmLayerTable 1 }
 
 AtmfM4AtmLayerEntry ::= SEQUENCE {
     atmfM4IfType INTEGER,
     atmfM4IfLoopbackLocationCode Integer32,
     atmfM4IfSubscriberAddress DisplayString,
     atmfM4IfPreferredCarrier DisplayString,
     atmfM4IfFarEndCarrierNetwork DisplayString
     }
 
 atmfM4IfType OBJECT-TYPE
     SYNTAX INTEGER {
         none(0),
         uni(1),
         bici(2),
         bissi(3)
     }
     MAX-ACCESS read-write
     STATUS current
     DESCRIPTION
         "Specifies the type of ATM cell layer interface defined
         on the physical path termination point modeled by this
         entry in the interface table. The default value of this
         object is none(0)."
     ::= { atmfM4AtmLayerEntry 1 }
 
 atmfM4IfLoopbackLocationCode OBJECT-TYPE
     SYNTAX Integer32
     MAX-ACCESS read-write
     STATUS current
     DESCRIPTION
         "Specifies the code that shall exist in incoming OAM
         Loopback cells that are to be looped back at this
         interface.
         A value of zero shall indicate that the management system
         has not set any loopback location code for this interface.
         Therefore, zero should not be used as the actual loopback
         location code for any interface.
         This object shall be present only for table entries that
         represent an actual ATM cell layer interface (i.e., the
         atmfM4IfType is not none(0)).
         The default value of this object is zero."
     ::= { atmfM4AtmLayerEntry 2 }
 
 atmfM4IfSubscriberAddress OBJECT-TYPE
     SYNTAX DisplayString
     MAX-ACCESS read-write
     STATUS current
     DESCRIPTION
         "Specifies the address or newline-delimited list of
         addresses assigned to the UNI.
         This object shall be present only for table entries that
         represent a UNI interface.
         The default value of this object is the null string."
     ::= { atmfM4AtmLayerEntry 3 }
 
 atmfM4IfPreferredCarrier OBJECT-TYPE
     SYNTAX DisplayString
     MAX-ACCESS read-write
     STATUS current
     DESCRIPTION
         "Specifies the name of the default carrier to use when one
         is not explicitly identified in the call set-up message.
         This object shall be present only for table entries that
         represent a UNI interface and only when SVC services are
         supported.
         The default value of this object is the null string."
     ::= { atmfM4AtmLayerEntry 4 }
 
 atmfM4IfFarEndCarrierNetwork OBJECT-TYPE
     SYNTAX DisplayString
     MAX-ACCESS read-write
     STATUS current
     DESCRIPTION
         "Specifies the adjacent carrier to which the B-ICI
         transmission path is connected.
         This object shall be present only for table entries that
         represent a B-ICI interface and only when SVC services are
         supported.
         The default value of this object is the null string."
     ::= { atmfM4AtmLayerEntry 5 }
     
     
-- ATM Performance     
     

-- TC Adapter Protocol Monitoring Current Data (per interface)
atmfM4TcProtoCurrTable OBJECT-TYPE
    SYNTAX SEQUENCE OF AtmfM4TcProtoCurrEntry
    MAX-ACCESS not-accessible
    STATUS current
    DESCRIPTION
        "The ATM Forum M4 TC Adapter Protocol Monitoring Current
        Data table.
        This table maintains per-interface statistics for the
        fifteen-minute interval currently being collected."
    ::= { atmfM4MIBObjects 18 }
atmfM4TcProtoCurrEntry OBJECT-TYPE
    SYNTAX AtmfM4TcProtoCurrEntry
    MAX-ACCESS not-accessible
    STATUS current
    DESCRIPTION
        "An entry in the ATM Forum M4 TC Adapter Protocol Monitoring
        Current Data table.
        Each ATM interface (UNI, BICI, BISSI) automatically has
        an entry in this table associated with it."
    INDEX { ifIndex }
    ::= { atmfM4TcProtoCurrTable 1 }
        AtmfM4TcProtoCurrEntry ::= SEQUENCE {
        atmfM4TcProtoCurrSuspect TruthValue,
        atmfM4TcProtoCurrElapsedTime TimeInterval,
        atmfM4TcProtoCurrSupprIntvls Gauge32,
        atmfM4TcProtoCurrDiscardHECViol Gauge32
        }
atmfM4TcProtoCurrSuspect OBJECT-TYPE
    SYNTAX TruthValue
    MAX-ACCESS read-only
    STATUS current
    DESCRIPTION
        "If true, the statistics in this entry may be unreliable."
    ::= { atmfM4TcProtoCurrEntry 1 }
atmfM4TcProtoCurrElapsedTime OBJECT-TYPE
    SYNTAX TimeInterval
    MAX-ACCESS read-only
    STATUS current
    DESCRIPTION
        "Amount of time, measured in units of 0.01 second, that
        statistics for this entry (the current interval) have been
        counted."
    ::= { atmfM4TcProtoCurrEntry 2 }
atmfM4TcProtoCurrSupprIntvls OBJECT-TYPE
    SYNTAX Gauge32
    MAX-ACCESS read-only
    STATUS current
    DESCRIPTION
        "This attribute is non-zero only if the ATM NE is
        suppressing ATM TC Adapter Protocol Monitoring History Data
        entry creation when the current interval terminates with
        'all-zeroes' performance measurements.
        When non-zero, this attribute represents the number of
        'all-zeroes' intervals that were suppressed immediately
        prior to the current interval.
        Note that the suppression of 'all-zeroes' intervals is
        controlled by the atmfM4NeSuppressZeroStats object."
    ::= { atmfM4TcProtoCurrEntry 3 }
atmfM4TcProtoCurrDiscardHECViol OBJECT-TYPE
    SYNTAX Gauge32
    MAX-ACCESS read-only
    STATUS current
    DESCRIPTION
        "The number of ATM cells discarded on this interface, due to
        a HEC violation, since the start of this interval."
    ::= { atmfM4TcProtoCurrEntry 4 }




-- UPC/NPC Disagreement Monitoring Current Data (per VCL
-- termination point)
atmfM4VcUpcNpcCurrTable OBJECT-TYPE
    SYNTAX SEQUENCE OF AtmfM4VcUpcNpcCurrEntry
    MAX-ACCESS not-accessible
    STATUS current
    DESCRIPTION
        "The ATM Forum M4 UPC/NPC Disagreement Monitoring Current
        Data table for VCL termination points.
        This table maintains per-TP statistics for the
        fifteen-minute interval currently being collected."
    ::= { atmfM4MIBObjects 22 }
atmfM4VcUpcNpcCurrEntry OBJECT-TYPE
        SYNTAX AtmfM4VcUpcNpcCurrEntry
        MAX-ACCESS not-accessible
        STATUS current
        DESCRIPTION
            "An entry in the ATM Forum M4 UPC/NPC Disagreement
            Monitoring Current Data table for VCL termination points.
            Each VCL Termination Point automatically has
            an entry in this table associated with it."
            INDEX { ifIndex,atmVclVpi,atmVclVci }
        ::= { atmfM4VcUpcNpcCurrTable 1 }
AtmfM4VcUpcNpcCurrEntry ::= SEQUENCE {
        atmfM4VcUpcNpcCurrSuspect TruthValue,
        atmfM4VcUpcNpcCurrElapsedTime TimeInterval,
        atmfM4VcUpcNpcCurrSupprIntvls Gauge32,
        atmfM4VcUpcNpcCurrDiscardedCells Gauge32,
        atmfM4VcUpcNpcCurrDiscardedClp0 Gauge32,
        atmfM4VcUpcNpcCurrPassedCells Gauge32,
        atmfM4VcUpcNpcCurrPassedClp0 Gauge32
        }
atmfM4VcUpcNpcCurrSuspect OBJECT-TYPE
    SYNTAX TruthValue
    MAX-ACCESS read-only
    STATUS current
    DESCRIPTION
            "If true, the statistics in this entry may be unreliable."
    ::= { atmfM4VcUpcNpcCurrEntry 1 }
atmfM4VcUpcNpcCurrElapsedTime OBJECT-TYPE
    SYNTAX TimeInterval
    MAX-ACCESS read-only
    STATUS current
    DESCRIPTION
        "Amount of time, measured in units of 0.01 second, that
        statistics for this entry (the current interval) have been
        counted."
    ::= { atmfM4VcUpcNpcCurrEntry 2 }
atmfM4VcUpcNpcCurrSupprIntvls OBJECT-TYPE
    SYNTAX Gauge32
    MAX-ACCESS read-only
    STATUS current
    DESCRIPTION
            "This attribute is non-zero only if the ATM NE is
            suppressing UPC/NPC Disagreement Monitoring History Data
            entry creation when the current interval terminates with
            'all-zeroes' performance measurements.
            When non-zero, this attribute represents the number of
            'all-zeroes' intervals that were suppressed immediately
            prior to the current interval.
            Note that the suppression of 'all-zeroes' intervals is
            controlled by the atmfM4NeSuppressZeroStats object."
    ::= { atmfM4VcUpcNpcCurrEntry 3 }
atmfM4VcUpcNpcCurrDiscardedCells OBJECT-TYPE
    SYNTAX Gauge32
    MAX-ACCESS read-only
    STATUS current
    DESCRIPTION
        "The number of discarded cells due to combined CLP=0 and
        CLP=1 UPC/NPC policing."
    ::= { atmfM4VcUpcNpcCurrEntry 4 }
atmfM4VcUpcNpcCurrDiscardedClp0 OBJECT-TYPE
    SYNTAX Gauge32
    MAX-ACCESS read-only
    STATUS current
    DESCRIPTION
        "The number of discarded CLP=0 cells due to CLP=0 only
        UPC/NPC policing.
        This object shall be present only if CLP=0 traffic is
        separately policed."
    ::= { atmfM4VcUpcNpcCurrEntry 5 }
atmfM4VcUpcNpcCurrPassedCells OBJECT-TYPE
    SYNTAX Gauge32
    MAX-ACCESS read-only
    STATUS current
    DESCRIPTION
        "The number of cells that have been successfully passed by
        the combined CLP=0 and CLP=1 UPC/NPC policing."
    ::= { atmfM4VcUpcNpcCurrEntry 6 }
atmfM4VcUpcNpcCurrPassedClp0 OBJECT-TYPE
    SYNTAX Gauge32
    MAX-ACCESS read-only
    STATUS current
    DESCRIPTION
        "The number of CLP=0 cells that have been successfully
        passed by the CLP=0 UPC/NPC policing.
        This object shall be present only if CLP=0 traffic is
        separately policed."
    ::= { atmfM4VcUpcNpcCurrEntry 7 }





-- UPC/NPC Disagreement Monitoring Current Data (per VPL
-- termination point)
atmfM4VpUpcNpcCurrTable OBJECT-TYPE
    SYNTAX SEQUENCE OF AtmfM4VpUpcNpcCurrEntry
    MAX-ACCESS not-accessible
    STATUS current
    DESCRIPTION
        "The ATM Forum M4 UPC/NPC Disagreement Monitoring Current
        Data table for VPL termination points.
        This table maintains per-TP statistics for the
        fifteen-minute interval currently being collected."
    ::= { atmfM4MIBObjects 20 }
atmfM4VpUpcNpcCurrEntry OBJECT-TYPE
    SYNTAX AtmfM4VpUpcNpcCurrEntry
    MAX-ACCESS not-accessible
    STATUS current
    DESCRIPTION
        "An entry in the ATM Forum M4 UPC/NPC Disagreement
        Monitoring Current Data table for VPL termination points.
        Each VPL Termination Point automatically has
        an entry in this table associated with it."
    INDEX { ifIndex,atmVplVpi }
    ::= { atmfM4VpUpcNpcCurrTable 1 }
        AtmfM4VpUpcNpcCurrEntry ::= SEQUENCE {
        atmfM4VpUpcNpcCurrSuspect TruthValue,
        atmfM4VpUpcNpcCurrElapsedTime TimeInterval,
        atmfM4VpUpcNpcCurrSupprIntvls Gauge32,
        atmfM4VpUpcNpcCurrDiscardedCells Gauge32,
        atmfM4VpUpcNpcCurrDiscardedClp0 Gauge32,
        atmfM4VpUpcNpcCurrPassedCells Gauge32,
        atmfM4VpUpcNpcCurrPassedClp0 Gauge32
        }
atmfM4VpUpcNpcCurrSuspect OBJECT-TYPE
    SYNTAX TruthValue
    MAX-ACCESS read-only
    STATUS current
    DESCRIPTION
        "If true, the statistics in this entry may be unreliable."
    ::= { atmfM4VpUpcNpcCurrEntry 1 }
atmfM4VpUpcNpcCurrElapsedTime OBJECT-TYPE
    SYNTAX TimeInterval
    MAX-ACCESS read-only
    STATUS current
    DESCRIPTION
        "Amount of time, measured in units of 0.01 second, that
        statistics for this entry (the current interval) have been
        counted."
    ::= { atmfM4VpUpcNpcCurrEntry 2 }
atmfM4VpUpcNpcCurrSupprIntvls OBJECT-TYPE
    SYNTAX Gauge32
    MAX-ACCESS read-only
    STATUS current
    DESCRIPTION
        "This attribute is non-zero only if the ATM NE is
        suppressing UPC/NPC Disagreement Monitoring History Data
        entry creation when the current interval terminates with
        'all-zeroes' performance measurements.
        When non-zero, this attribute represents the number of
        'all-zeroes' intervals that were suppressed immediately
        prior to the current interval.
        Note that the suppression of 'all-zeroes' intervals is
        controlled by the atmfM4NeSuppressZeroStats object."
    ::= { atmfM4VpUpcNpcCurrEntry 3 }
atmfM4VpUpcNpcCurrDiscardedCells OBJECT-TYPE
    SYNTAX Gauge32
    MAX-ACCESS read-only
    STATUS current
    DESCRIPTION
        "The number of discarded cells due to combined CLP=0 and
        CLP=1 UPC/NPC policing."
    ::= { atmfM4VpUpcNpcCurrEntry 4 }
atmfM4VpUpcNpcCurrDiscardedClp0 OBJECT-TYPE
    SYNTAX Gauge32
    MAX-ACCESS read-only
    STATUS current
    DESCRIPTION
        "The number of discarded CLP=0 cells due to CLP=0 only
        UPC/NPC policing.
        This object shall be present only if CLP=0 traffic is
        separately policed."
    ::= { atmfM4VpUpcNpcCurrEntry 5 }
atmfM4VpUpcNpcCurrPassedCells OBJECT-TYPE
    SYNTAX Gauge32
    MAX-ACCESS read-only
    STATUS current
    DESCRIPTION
        "The number of cells that have been successfully passed by
        the combined CLP=0 and CLP=1 UPC/NPC policing."
    ::= { atmfM4VpUpcNpcCurrEntry 6 }
atmfM4VpUpcNpcCurrPassedClp0 OBJECT-TYPE
    SYNTAX Gauge32
    MAX-ACCESS read-only
    STATUS current
    DESCRIPTION
        "The number of CLP=0 cells that have been successfully
        passed by the CLP=0 UPC/NPC policing.
        This object shall be present only if CLP=0 traffic is
        separately policed."
    ::= { atmfM4VpUpcNpcCurrEntry 7 }
     
     
  END
 



ATM-FORUM-MIB DEFINITIONS ::= BEGIN
        IMPORTS
                atmForum, atmfPhysicalGroup,
                atmfAtmLayerGroup           FROM ATM-FORUM-TC-MIB
                Counter, IpAddress                      FROM RFC1155-SMI
                DisplayString, PhysAddress      FROM SNMPv2-TC
                TRAP-TYPE                                       FROM RFC-1215
                OBJECT-TYPE                             FROM RFC-1212;

-- Textual Conventions
-- All representations of ATM addresses in this MIB Module use
-- the data type:

        AtmAddress ::= OCTET STRING (SIZE (0 .. 32))

        atmForumUni OBJECT IDENTIFIER ::= { atmForum 2 }
        atmfAddressRegistrationAdminGroup OBJECT IDENTIFIER ::= { atmForumUni 11 }

    atmfAutoConfigGroup OBJECT IDENTIFIER ::= { atmForumUni 12 }

    atmfAtmServiceTypeTable OBJECT-TYPE
        SYNTAX SEQUENCE OF atmfAtmServiceTypeEntry
        MAX-ACCESS not-accessible
        STATUS current
        DESCRIPTION
            "The ATM Forum ILMI Auto Configuration Extension ATM
            Service Type Information. "
        ::= { atmfAutoConfigGroup 1 }
    atmfAtmServiceTypeEntry OBJECT-TYPE
        SYNTAX atmfAtmServiceTypeEntry
        MAX-ACCESS not-accessible
        STATUS current
        DESCRIPTION
            "An entry in the service type table describes the reference
            information about a service that may be associated with
            individual ATM connections for the purpose of auto-
            configuration. This information describe the name and sub-
            name of the service, the client layer protocol using the ATM
            service, the TM 4.0 service category, and the TM 4.0
            conformance definition."
        INDEX { atmfAtmServiceTypeIndex }
        ::= { atmfAtmServiceTypeTable 1 }
        
    atmfAtmServiceTypeEntry ::= SEQUENCE {
            atmfAtmServiceTypeIndex         INTEGER,
            atmfAtmServiceProviderName      DisplayString,
            atmfAtmServiceName              DisplayString,
            atmfAtmServiceSubName           DisplayString,
            atmfAtmServiceClient            DisplayString,
            atmfAtmServiceTMCategory        INTEGER,
            atmfAtmServiceTMConformanceDef  INTEGER
            }
    atmfAtmServiceTypeIndex OBJECT-TYPE
        SYNTAX INTEGER (1..2147483647)
        MAX-ACCESS read-only
        STATUS current
        DESCRIPTION
            "A number between which identifies the entry in the Service
            Type Table. "
        ::= { atmfAtmServiceTypeEntry 1 }
    atmfAtmServiceProviderName OBJECT-TYPE
        SYNTAX DisplayString
        MAX-ACCESS read-only
        STATUS current
        DESCRIPTION
            "This string identifies the name of the service provider for
            the service described in this profile. The value of this
            attribute should not set to NULL."
        ::= { atmfAtmServiceTypeEntry 2 }
    atmfAtmServiceName OBJECT-TYPE
        SYNTAX DisplayString
        MAX-ACCESS read-only
        STATUS current
        DESCRIPTION
            "This string identifies the name of the service described in
            this profile. The value of this attribute should not be set
            to NULL. "
        ::= { atmfAtmServiceTypeEntry 3 }
    atmfAtmServiceSubName OBJECT-TYPE
        SYNTAX DisplayString
        MAX-ACCESS read-only
        STATUS current
        DESCRIPTION
            "This string identifies the sub-name of the service described
            in this profile. A Service may have zero or more sub-names,
            each with its own service type profile. "
        ::= { atmfAtmServiceTypeEntry 4 }
    atmfAtmServiceClient OBJECT-TYPE
        SYNTAX DisplayString
        MAX-ACCESS read-only
        STATUS current
        DESCRIPTION
            "This string identifies the client protocol of the service
            described in this profile. A Service (sub-service) may have
            zero or more described client, each with its own service type
            profile. "
        ::= { atmfAtmServiceTypeEntry 5 }
    atmfAtmServiceTMCategory OBJECT-TYPE
        SYNTAX INTEGER {
            other (1),
            cbr (2),
            rtVbr (3),
            nrtVbr (4),
            abr (5),
            ubr (6),
            gfr (7)
                }
        MAX-ACCESS read-only
        STATUS current
        DESCRIPTION
            "The TM 4.0 Service category used for this service type.
            Indicates CBR, rt-VBR, nrt-VBR, ABR, UBR, (or GFR)"
        ::= { atmfAtmServiceTypeEntry 6 }
    atmfAtmServiceTMConformanceDef OBJECT-TYPE
        SYNTAX INTEGER {
            none (0),
            other(1),
            cbr1 (2),
            vbr1 (3),
            vbr2 (4),
            vbr3 (5),
            ubr1 (6),
            ubr2 (7),
            abr (8),
            gfr1 (9),
            gfr2 (10)
            }
        MAX-ACCESS read-only
        STATUS current
        DESCRIPTION
            "The TM 4.1 conformance definition used for this service type.
            Indicates CBR.1, VBR.1, VBR.2, VBR.3, UBR.1, UBR.2, ABR,
            GFR.1, or GFR.2. "
        ::= { atmfAtmServiceTypeEntry 7 }
    ------------------------------------------------------------------
    -- ATM Forum ILMI Extension for Auto Configuration
    -- ATM Service Connection Information
    ------------------------------------------------------------------
    atmfAtmServiceConnInfoTable OBJECT-TYPE
        SYNTAX SEQUENCE OF atmfAtmServiceConnInfoEntry
        MAX-ACCESS not-accessible
        STATUS current
        DESCRIPTION
            "The ATM Forum ILMI Auto Configuration Extension ATM
            Service Connection Information. "
        ::= { atmfAutoConfigGroup 2 }
    atmfAtmServiceConnInfoEntry OBJECT-TYPE
        SYNTAX atmfAtmServiceConnInfoEntry
        MAX-ACCESS not-accessible
        STATUS current
        DESCRIPTION
            "An entry in the service connection information table
            describes the ATM connection that provides a service across
            an ATM interface. The connection is identified by port and
            VPI/VCI value. Information about the connection includes the
            connection type (VP or VC, SVC or PVC), and the association of
            the connection with a service type. Specific connection
            information, such as traffic descriptors, should be accessed
            in the atmfVpc and atmfVcc tables defined in ILMI. "
        INDEX { atmfAtmServicePortIndex, atmfAtmServiceVpi, atmfAtmServiceVci }
        ::= { atmfAtmServiceConnInfoTable 1 }
    atmfAtmServiceConnInfoEntry ::= SEQUENCE {
        atmfAtmServicePortIndex     INTEGER,
        atmfAtmServiceVpi           INTEGER,
        atmfAtmServiceVci           INTEGER,
        atmfAtmServiceSignalID      INTEGER,
        atmfAtmServiceConnServiceIndex INTEGER,
        atmfAtmServiceConnName      DisplayString,
        atmfAtmServiceConnAALType   INTEGER,
        atmfAtmServiceConnAALIndex  INTEGER
        }
    atmfAtmServicePortIndex OBJECT-TYPE
        SYNTAX INTEGER (0..2147483647)
        MAX-ACCESS read-only
        STATUS current
        DESCRIPTION
            "The value of 0 (zero)has the special meaning of identifying
            the ATM Interface over which this ILMI message was received. "
        ::= { atmfAtmServiceConnInfoEntry 1 }
    atmfAtmServiceVpi OBJECT-TYPE
        SYNTAX INTEGER (0..255)
        MAX-ACCESS read-only
        STATUS current
        DESCRIPTION
            "The VPI value of the ATM service connection at the local ATM
            interface. "
        ::= { atmfAtmServiceConnInfoEntry 2 }
    atmfAtmServiceVci OBJECT-TYPE
        SYNTAX INTEGER (0..65535)
        MAX-ACCESS read-only
        STATUS current
        DESCRIPTION
            "The VCI value of the ATM service connection at the local ATM
            interface. If the atmfAtmServiceSignalId indicates that the
            connection is a VP connection, the value of this attribute
            shall be set to 0 (zero) and any meaning of this attribute
            ignored."
        ::= { atmfAtmServiceConnInfoEntry 3 }
    atmfAtmServiceSignalID OBJECT-TYPE
        SYNTAX INTEGER {
            vcCI(0),
            vpCI(1)
            }
        MAX-ACCESS read-only
        STATUS current
        DESCRIPTION
            "This attribute represents the characteristic
            information of the layer network domain. It may be set to
            either VC characteristic information (vcCI) or VP
            characteristic information (vpCI)."
        ::= { atmfAtmServiceConnInfoEntry 4 }
    atmfAtmServiceConnServiceIndex OBJECT-TYPE
        SYNTAX INTEGER
        MAX-ACCESS read-only
        STATUS current
        DESCRIPTION
            "The value of this object identifies the row in the
            atmfAtmServiceTypeTable. This entry represents the
            association between an ATM service connection and an ATM
            service type profile that describes it. "
        ::= { atmfAtmServiceConnInfoEntry 5 }
    atmfAtmServiceConnName OBJECT-TYPE
        SYNTAX DisplayString
        MAX-ACCESS read-only
        STATUS current
        DESCRIPTION
            "This string identifies the name of the service connection.
            The value of this attribute may be set to NULL. "
        ::= { atmfAtmServiceConnInfoEntry 6 }
    atmfAtmServiceConnAALType OBJECT-TYPE
        SYNTAX INTEGER {
            none (0),
            aal1 (1),
            aal34 (2),
            aal5 (3),
            other (4),
            unknown (5),
            aal2 (6)
            }
        MAX-ACCESS read-only
        STATUS current
        DESCRIPTION
            "Describes the AAL Type of the ATM service connection. A
            value of none indicates that no AAL is used. The AAL types
            include AAL1, AAL 3/4, and AAL 5. The value other may be a
            user-defined AAL type. The unknown type indicates that the
            AAL type cannot be determined. "
        ::= { atmfAtmServiceConnInfoEntry 7 }
    atmfAtmServiceConnAALIndex OBJECT-TYPE
        SYNTAX INTEGER
        MAX-ACCESS read-only
        STATUS current
        DESCRIPTION
            "The value of this object identifies the row in the
            atmfAAL1ProfileTable for AAL 1 connection, the
            atmfAAL34ProfileTable for AAL3/4 connection, and the
            atmfAAL5ProfileTable for AAL 5 connections. This entry
            represents the association between an ATM service connection
            and an ATM Adaptation Layer profile that describes it. "
        ::= { atmfAtmServiceConnInfoEntry 8 }
    ------------------------------------------------------------------
    -- ATM Forum ILMI Extension for Auto Configuration
    -- ATM AAL1 Profile
    ------------------------------------------------------------------
    atmfAAL1ProfileTable OBJECT-TYPE
        SYNTAX SEQUENCE OF atmfAAL1ProfileEntry
        MAX-ACCESS not-accessible
        STATUS current
        DESCRIPTION
            "The ATM Forum ILMI Auto Configuration Extension AAL1
            Profile Information. "
        ::= { atmfAutoConfigGroup 3 }
    atmfAAL1ProfileEntry OBJECT-TYPE
        SYNTAX atmfAAL1ProfileEntry
        MAX-ACCESS not-accessible
        STATUS current
        DESCRIPTION
            "An entry in the AAL1 Profile table provides data that
            describes the AAL1 processing function. "
        INDEX { atmfAAL1ProfileIndex }
        ::= { atmfAAL1ProfileTable 1 }
    atmfAAL1ProfileEntry ::= SEQUENCE {
        atmfAAL1ProfileIndex INTEGER,
        atmfAAL1Subtype INTEGER,
        atmfAAL1CBRRate INTEGER,
        atmfAAL1ClkRecoveryType INTEGER,
        atmfAAL1FEC INTEGER,
        atmfAAL1SDT INTEGER,
        atmfAAL1PartiallyFilledCells INTEGER,
        atmfAAL1CellLossIntegrPeriod INTEGER
        }
    atmfAAL1ProfileIndex OBJECT-TYPE
        SYNTAX INTEGER (1..2147483647)
        MAX-ACCESS read-only
        STATUS current
            DESCRIPTION
            "A number between which identifies the entry in the AAL1
            Profile Table. "
        ::= { atmfAAL1ProfileEntry 1 }
    atmfAAL1Subtype OBJECT-TYPE
        SYNTAX INTEGER {
            null (0),
            voiceBand (1),
            circuitEmulationSynchronous (2),
            circuitEmulationAsynchronous (3),
            highQualityAuto (4),
            video (5)
            }
        MAX-ACCESS read-only
        STATUS current
        DESCRIPTION
            "This attribute describes AAL type 1 subtype used by the CBR
            service application (e.g. 64 KBPS voice band signal
            transport, circuit transport). "
        ::= { atmfAAL1ProfileEntry 2 }
    atmfAAL1CBRRate OBJECT-TYPE
        SYNTAX INTEGER
        MAX-ACCESS read-only
        STATUS current
        DESCRIPTION
            "This attribute describes the rate of the CBR service
            supported by the AAL."
        ::= { atmfAAL1ProfileEntry 3 }
    atmfAAL1ClkRecoveryType OBJECT-TYPE
        SYNTAX INTEGER {
            synchronous (0),
            srts(1),
            adaptive (2)
            }
        MAX-ACCESS read-only
        STATUS current
        DESCRIPTION
            "This attribute indicates whether the clock recovery type is
            synchronous, asynchronous-SRTS(Synchronous Residual Time Stamp),
            or asynchronous-Adaptive Clock Recovery. "
        ::= { atmfAAL1ProfileEntry 4 }
    atmfAAL1FEC OBJECT-TYPE
        SYNTAX INTEGER {
            noFEC (0),
            lossSensitiveSignalFEC (1),
            delaySensitiveSignalFEC (2)
            }
        MAX-ACCESS read-only
        STATUS current
        DESCRIPTION
            "This attribute indicates the FEC method: no FEC, FEC for
            Loss Sensitive Signal Transport, or FEC for Delay Sensitive
            Signal Transport. "
        ::= { atmfAAL1ProfileEntry 5 }
    atmfAAL1SDT OBJECT-TYPE
        SYNTAX INTEGER {
            false (0),
            true(1)
            }
        MAX-ACCESS read-only
        STATUS current
            DESCRIPTION
            "This attribute indicates whether Structured Data Transfer
            (SDT) has been configured at the AAL. A value of TRUE means
            SDT has been selected. This attribute value can be set to
            TRUE only when the Forward Error Correction Type attribute
            equals noFEC. "
        ::= { atmfAAL1ProfileEntry 6 }
    atmfAAL1PartiallyFilledCells OBJECT-TYPE
        SYNTAX INTEGER
        MAX-ACCESS read-only
        STATUS current
        DESCRIPTION
            "This attribute identifies the number of leading octets in
            use."
        ::= { atmfAAL1ProfileEntry 7 }
    atmfAAL1CellLossIntegrPeriod OBJECT-TYPE
        SYNTAX INTEGER
        MAX-ACCESS read-only
        STATUS current
        DESCRIPTION
            "This attribute represents the time in milliseconds for the
            cell loss integration period. If cells are lost for this
            period of time, the Interworking VCC Termination Point entity
            will generate a cell starvation alarm."
        ::= { atmfAAL1ProfileEntry 8 }
    ------------------------------------------------------------------
    -- ATM Forum ILMI Extension for Auto Configuration
    -- ATM AAL3/4 Profile
    ------------------------------------------------------------------
    atmfAAL34ProfileTable OBJECT-TYPE
        SYNTAX SEQUENCE OF atmfAAL34ProfileEntry
        MAX-ACCESS not-accessible
        STATUS current
        DESCRIPTION
            "The ATM Forum ILMI Auto Configuration Extension AAL3/4
            Profile Information. "
        ::= { atmfAutoConfigGroup 4 }
    atmfAAL34ProfileEntry OBJECT-TYPE
        SYNTAX atmfAAL34ProfileEntry
        MAX-ACCESS not-accessible
        STATUS current
        DESCRIPTION
            "An entry in the AAL34 Profile table provides data that
            describes the AAL3/4 processing function. "
        INDEX { atmfAAL34ProfileIndex }
        ::= { atmfAAL34ProfileTable 1 }
    atmfAAL34ProfileEntry ::= SEQUENCE {
        atmfAAL34ProfileIndex INTEGER,
        atmfAAL34MaxCpcsSduSizeForward INTEGER,
        atmfAAL34MaxCpcsSduSizeBackward INTEGER,
        atmfAAL34MIDRangeLow INTEGER,
        atmfAAL34MIDRangeHigh INTEGER,
        atmfAAL34AALMode INTEGER,
        atmfAAL34SscsType INTEGER
        }
    atmfAAL34ProfileIndex OBJECT-TYPE
        SYNTAX INTEGER (1..2147483647)
        MAX-ACCESS read-only
        STATUS current
        DESCRIPTION
            "A number between which identifies the entry in the AAL3/4
            Profile Table. "
        ::= { atmfAAL34ProfileEntry 1 }
    atmfAAL34MaxCpcsSduSizeForward OBJECT-TYPE
        SYNTAX INTEGER (1..65535)
        MAX-ACCESS read-only
        STATUS current
        DESCRIPTION
            "This attribute represents the maximum CPCS_PDU size that will
            be transmitted over the connection in both the incoming
            (forward) direction of transmission. "
        ::= { atmfAAL34ProfileEntry 2 }
    atmfAAL34MaxCpcsSduSizeBackward OBJECT-TYPE
        SYNTAX INTEGER (1..65535)
        MAX-ACCESS read-only
        STATUS current
        DESCRIPTION
            "This attribute represents the maximum CPCS_PDU size that will
            be transmitted over the connection in both the outgoing
            (backward) direction of transmission. "
        ::= { atmfAAL34ProfileEntry 3 }
    atmfAAL34MIDRangeLow OBJECT-TYPE
        SYNTAX INTEGER (1..66536)
        MAX-ACCESS read-only
        STATUS current
        DESCRIPTION
            "This attribute represents the low value of MID supported at
            the AAL for the supporting VCC."
        ::= { atmfAAL34ProfileEntry 4 }
    atmfAAL34MIDRangeHigh OBJECT-TYPE
        SYNTAX INTEGER (1..66536)
        MAX-ACCESS read-only
        STATUS current
        DESCRIPTION
            "This attribute represents the high value of MID supported at
            the AAL for the supporting VCC."
        ::= { atmfAAL34ProfileEntry 5 }
    atmfAAL34AALMode OBJECT-TYPE
        SYNTAX INTEGER {
            messageAssured (0),
            messageUnassured (1),
            streamingAssured (2),
            streamingUnassured (3)
            }
        MAX-ACCESS read-only
        STATUS current
        DESCRIPTION
            "This attribute indicates whether the AAL for the supporting
            VCC is operating in message mode or streaming mode, assured or
            unassured. "
        ::= { atmfAAL34ProfileEntry 6 }
    atmfAAL34SscsType OBJECT-TYPE
        SYNTAX INTEGER {
            null (0),
            dataAssured (1),
            dataNonAssured (2),
            frameRelay (3)
            }
        MAX-ACCESS read-only
        STATUS current
        DESCRIPTION
            "This attribute identifies the SSCS type for the AAL. Valid
            values are NULL, Data SSCS based on SSCOP (assured operation),
            Data SSCS based on SSCOP (non-assured operation), or Frame
            Relay SSCS "
        ::= { atmfAAL34ProfileEntry 7 }
    ------------------------------------------------------------------
    -- ATM Forum ILMI Extension for Auto Configuration
    -- ATM AAL5 Profile
    ------------------------------------------------------------------
    atmfAAL5ProfileTable OBJECT-TYPE
        SYNTAX SEQUENCE OF atmfAAL5ProfileEntry
        MAX-ACCESS not-accessible
        STATUS current
        DESCRIPTION
            "The ATM Forum ILMI Auto Configuration Extension AAL5
            Profile Information. "
        ::= { atmfAutoConfigGroup 5 }
    atmfAAL5ProfileEntry OBJECT-TYPE
        SYNTAX atmfAAL5ProfileEntry
        MAX-ACCESS not-accessible
        STATUS current
        DESCRIPTION
            "An entry in the AAL5 Profile table provides data that
            describes the AAL5 processing function. "
        INDEX { atmfAAL5ProfileIndex }
        ::= { atmfAAL5ProfileTable 1 }
    atmfAAL5ProfileEntry ::= SEQUENCE {
        atmfAAL5ProfileIndex INTEGER,
        atmfAAL5MaxCpcsSduSizeForward INTEGER,
        atmfAAL5MaxCpcsSduSizeBackward INTEGER,
        atmfAAL5AALMode INTEGER,
        atmfAAL5SscsType INTEGER
        }
    atmfAAL5ProfileIndex OBJECT-TYPE
        SYNTAX INTEGER (1..2147483647)
        MAX-ACCESS read-only
        STATUS current
        DESCRIPTION
            "A number between which identifies the entry in the AAL5
            Profile Table. "
        ::= { atmfAAL5ProfileEntry 1 }
    atmfAAL5MaxCpcsSduSizeForward OBJECT-TYPE
        SYNTAX INTEGER (1..65535)
        MAX-ACCESS read-only
        STATUS current
        DESCRIPTION
            "This attribute represents the maximum CPCS_PDU size that will
            be transmitted over the connection in both the incoming
            (forward) direction of transmission. "
        ::= { atmfAAL5ProfileEntry 2 }
    atmfAAL5MaxCpcsSduSizeBackward OBJECT-TYPE
        SYNTAX INTEGER (1..65535)
        MAX-ACCESS read-only
        STATUS current
        DESCRIPTION
            "This attribute represents the maximum CPCS_PDU size that will
            be transmitted over the connection in both the outgoing
            (backward) direction of transmission. "
        ::= { atmfAAL5ProfileEntry 3 }
    atmfAAL5AALMode OBJECT-TYPE
        SYNTAX INTEGER {
            messageAssured (0),
            messageUnassured (1),
            streamingAssured (2),
            streamingUnassured (3)
            }
        MAX-ACCESS read-only
        STATUS current
        DESCRIPTION
            "This attribute indicates whether the AAL for the supporting
            VCC is operating in message mode or streaming mode, assured or
            unassured. "
        ::= { atmfAAL5ProfileEntry 4 }
    atmfAAL5SscsType OBJECT-TYPE
        SYNTAX INTEGER {
            null (0),
            dataAssured (1),
            dataNonAssured (2),
            frameRelay (3)
            }
        MAX-ACCESS read-only
        STATUS current
        DESCRIPTION
            "This attribute identifies the SSCS type for the AAL. Valid
            values are NULL, Data SSCS based on SSCOP (assured operation),
            Data SSCS based on SSCOP (non-assured operation), or Frame
            Relay SSCS "
        ::= { atmfAAL5ProfileEntry 5 }
    
    ------------------------------------------------------------------
    -- ATM Forum ILMI Extension for Auto Configuration
    -- ATM Common AAL2 Profile
    -- In the case where an AAL2CommonProfileEntry contains parameter(s)
    -- which is/are set to a value that is/are not supported by the AAL2
    -- entity in the ATU-R, the user-side IME must raise an
    -- atmfAtmServiceConfFail trap towards the network-side IME. The
    -- atmfAtmServiceConfFailReason should be 'unsupportedAAL' and
    -- the atmfAtmServiceConfFailOID must point to the
    -- atmfAAL2CommonProfileEntry that contains the unsupported
    -- parameter(s).
    ------------------------------------------------------------------
    atmfAAL2CommonProfileTable OBJECT-TYPE
        SYNTAX SEQUENCE OF atmfAAL2CommonProfileEntry
        MAX-ACCESS not-accessible
        STATUS current
        DESCRIPTION
            "The ATM Forum ILMI Auto Configuration Extension AAL2 Profile
            Information. This table contains AAL2 parameters that are common
            to all AAL2 applications. These parameters are taken from
            I.363.2, I.366.1 and I.366.2"
        ::= { atmfAutoConfigGroup 6 }
    atmfAAL2CommonProfileEntry OBJECT-TYPE
        SYNTAX atmfAAL2CommonProfileEntry
        MAX-ACCESS not-accessible
        STATUS current
        DESCRIPTION
            "An atmfAAL2CommonProfileEntry provides AAL2 common parameters
            of operation that are to be used by the PVC associated with this
            entry."
        INDEX { atmfAAL2ProfileIndex }
        ::= { atmfAAL2CommonProfileTable 1 }
    atmfAAL2CommonProfileEntry ::= SEQUENCE {
        atmfAAL2ProfileIndex                INTEGER,
        atmfAAL2ConfigResponsibility        INTEGER,
        atmfAAL2CpsMaxMultiplexedChannels   INTEGER,
        atmfAAL2CpsMaxSduLength             INTEGER,
        atmfAAL2SscsMaxSssarSduLength       INTEGER,
        atmfAAL2SscsSstedStatus             INTEGER,
        atmfAAL2SscsSsadtStatus             INTEGER,
        atmfAAL2SscsServiceCategory         INTEGER,
        atmfAAL2SscsAudioServiceTransport   INTEGER,
        atmfAAL2SscsProfileSource           INTEGER,
        atmfAAL2SscsIeeeOui                 INTEGER,
        atmfAAL2SscsPredefinedProfileIdentifier INTEGER,
        atmfAAL2PcmEncoding                 INTEGER,
        atmfAAL2SscsFaxDemodulationTransport INTEGER,
        atmfAAL2SscsCasSignalingTransport   INTEGER,
        atmfAAL2SscsDtmfDigitPacketTransport INTEGER,
        atmfAAL2SscsMfR1DigitPacketTransport INTEGER,
        atmfAAL2SscsMfR2DigitPacketTransport INTEGER,
        atmfAAL2SscsCircuitModeDataTransport INTEGER,
        atmfAAL2SscsCircuitModeDataNumChannels INTEGER,
        atmfAAL2SscsFrameModeDataTransport      INTEGER,
        atmfAAL2SscsFrameModeDataMaxLength      INTEGER
    }
    
    atmfAAL2ProfileIndex OBJECT-TYPE
        SYNTAX INTEGER
        MAX-ACCESS read-only
        STATUS current
        DESCRIPTION
            "A number which uniquely identifies the entry in the AAL2
            Profile Table."
        ::= { atmfAAL2CommonProfileEntry 1 }
    atmfAAL2ConfigResponsibility OBJECT-TYPE
        SYNTAX INTEGER {
            ilmi (1),
            lesEoc (2),
            other (3)
            }
        MAX-ACCESS read-only
        STATUS current
        DESCRIPTION
            "This object identifies which management channel is responsible
            for AAL2 provisioning and auto-configuration. The user-side IME
            must check the value of this parameter first before configuring
            the AAL2 aspects of a PVC to determined whether or not this
            responsibility lies with ILMI.
            ilmi - if this is selected then the user-side IME should use the
            AAL2 Profile defined in this entry and any extension table entries
            (if applicable) to auto-configure the AAL2 for the associated PVC.
            lesEoc - if this is selected then the user-side IME must not
            auto-configure the AAL2 using ILMI. The AAL2 Profile parameters
            do not need to be provisioned by the network-side IME and the
            user-side IME should not read the AAL2 Profile parameters other
            than this one. The Loop Emulation Service Embedded Operations
            Channel (LES EOC) will be used to provision the AAL2 for the
            associated PVC. The selection of this option implies that the AAL2
            entity in the ATU-R must support I.366.1 SSSAR with SSTED'selected'
            and SSADT 'not selected' with the SSSAR capable of handling SDU
            lengths of at least 493 octets. It further implies that the CP-IWF
            in the ATU-R which is attached to the PVC associated with this
            AAL2CommonProfileEntry must be configured to receive SNMP messages
            on CID=9.
            other - if this is selected then the user-side IME must not
            auto-configure the AAL2 using ILMI. The AAL2 Profile parameters
            do not need to be provisioned by the network-side IME and the
            user-side IME must not read the AAL2 Profile parameters other
            than this one. Another mechanism will be used to provision the
            AAL2 at the ATU-R for the associated PVC."
        ::= { atmfAAL2CommonProfileEntry 2 }

    atmfAAL2CpsMaxMultiplexedChannels OBJECT-TYPE
        SYNTAX INTEGER (1..255)
        MAX-ACCESS read-only
        STATUS current
        DESCRIPTION
             "Maximum number of multiplexed channels."
        DEFVAL { 255 }
        ::= { atmfAAL2CommonProfileEntry 3 }
    atmfAAL2CpsMaxSDULength OBJECT-TYPE
        SYNTAX INTEGER (45 | 64)
        MAX-ACCESS read-only
        STATUS current
        DESCRIPTION
            "Maximum CPS-SDU size given in octets. This parameter is
            bidirectional, i.e. its value applies to both directions of the
            AAL2 connection."
        DEFVAL { 45 }
        ::= { atmfAAL2CommonProfileEntry 4 }
    atmfAAL2SscsMaxSssarSduLength OBJECT-TYPE
        SYNTAX INTEGER (1..65568)
        MAX-ACCESS read-only
        STATUS current
        DESCRIPTION
            "This is the maximum size and SSSAR-SDU can take as defined
            in I.366.1. This parameter only applies to those AAL2 channels
            using I.366.1 SSSAR. This parameter is bidirectional, i.e its value
            applies to both directions of the AAL2 connection. Note that if the
            appID indicates Loop Emulation Service as the AAL2 application
            then the minimum allowable value of this parameter is 493."
        ::= { atmfAAL2CommonProfileEntry 5 }
    atmfAAL2SscsSstedStatus OBJECT-TYPE
        SYNTAX INTEGER {
            selected(1),
            notSelected(2)
            }
        MAX-ACCESS read-only
        STATUS current
        DESCRIPTION
            "This specifies whether the SSTED service is used or not.
            If the value of this object is 'selected' then I.366.1
            SSSAR must be supported by the AAL2. This parameter only
            applies to those AAL2 channels using I.366.1 SSSAR."
        ::= { atmfAAL2CommonProfileEntry 6 }
    atmfAAL2SscsSsadtStatus OBJECT-TYPE
        SYNTAX INTEGER {
            selected(1),
            notSelected(2)
            }
        MAX-ACCESS read-only
        STATUS current
        DESCRIPTION
            "This specifies whether SSADT service is used or not.
            Note that if the value of this object is 'selected' then
            I.366.1 SSSAR must be supported and by implication the SSTED
            service must also be 'selected'. This parameter only applies
            to those AAL2 channels using I.366.1 SSSAR."
        ::= { atmfAAL2CommonProfileEntry 7 }
    atmfAAL2SscsServiceCategory OBJECT-TYPE
        SYNTAX INTEGER {
            audio (1),
            multirate (2),
            audioAndMultiRate (3)
            }
        MAX-ACCESS read-only
        STATUS current
        DESCRIPTION
            "This object describes the type of service category supported
            by this AAL2 PVC."
        DEFVAL { audio }
        ::= { atmfAAL2CommonProfileEntry 8 }
    atmfAAL2SscsAudioServiceTransport OBJECT-TYPE
        SYNTAX INTEGER {
            disabled (1),
            enabled (2)
            }
        MAX-ACCESS read-only
        STATUS current
        DESCRIPTION
            "This object describes whether the Audio Service that
            is used for transporting voice and voiceband data is enabled
            or disabled."
        DEFVAL { enabled }
        ::= { atmfAAL2CommonProfileEntry 9 }
    atmfAAL2SscsProfileSource OBJECT-TYPE
        SYNTAX INTEGER {
            itut (1),
            other (2)
            }
        MAX-ACCESS read-only
        STATUS current
        DESCRIPTION
            "This attribute describes the source of the profile. "
        DEFVAL { itut }
        ::= { atmfAAL2CommonProfileEntry 10 }
    atmfAAL2SscsIeeeOui OBJECT-TYPE
        SYNTAX INTEGER
        MAX-ACCESS read-only
        STATUS current
        DESCRIPTION
            "This attribute contains the IEEE Organizationally Unique
            Identifier (OUI) of the organisation that specified the
            profile being used, if other than ITU-T. For example, if
            the source is the ATM Forum, the value of this object is 00A03E.
            This attribute is only meaningful if atmfAAL2SccsProfileSource
            has the value 'other'."
        ::= { atmfAAL2CommonProfileEntry 11 }
    atmfAAL2SscsPredefinedProfileIdentifier OBJECT-TYPE
        SYNTAX INTEGER
        MAX-ACCESS read-only
        STATUS current
        DESCRIPTION
            "This object describes the predefined profile identifier."
        DEFVAL { 1 }
        ::= { atmfAAL2CommonProfileEntry 12 }
    atmfAAL2SscsPcmEncoding OBJECT-TYPE
        SYNTAX INTEGER {
            aLaw (1),
            ulaw (2)
            }
        MAX-ACCESS read-only
        STATUS current
        DESCRIPTION
            "This object describes the type of PCM encoding used."
        DEFVAL { aLaw }
        ::= { atmfAAL2CommonProfileEntry 13 }
    atmfAAL2SscsFaxDemodulationTransport OBJECT-TYPE
        SYNTAX INTEGER {
            disabled (1),
            enabled (2)
            }
        MAX-ACCESS read-only
        STATUS current
        DESCRIPTION
            "This object describes whether transport of demodulated
            facsimile data is enabled or disabled."
        DEFVAL { disabled }
        ::= { atmfAAL2CommonProfileEntry 14 }
    atmfAAL2SscsCasSignalingTransport OBJECT-TYPE
        SYNTAX INTEGER {
            disabled (1),
            enabled (2)
            }
        MAX-ACCESS read-only
        STATUS current
        DESCRIPTION
            "This attribute describes whether transport of CAS
            signaling bits is enabled or disabled."
        DEFVAL { disabled }
        ::= { atmfAAL2CommonProfileEntry 15 }
    atmfAAL2SscsDtmfDigitPacketTransport OBJECT-TYPE
        SYNTAX INTEGER {
            disabled (1),
            enabled (2)
            }
        MAX-ACCESS read-only
        STATUS current
        DESCRIPTION
            "This attribute describes whether transport of DTMF dialled
            digits is enabled or disabled."
        DEFVAL { disabled }
        ::= { atmfAAL2CommonProfileEntry 16 }
    atmfAAL2SscsMfR1DigitPacketTransport OBJECT-TYPE
        SYNTAX INTEGER {
            disabled (1),
            enabled (2)
            }
        MAX-ACCESS read-only
        STATUS current
        DESCRIPTION
            "This object describes whether transport of MF-R1 dialled
            digits is enabled or disabled."
        DEFVAL { disabled }
        ::= { atmfAAL2CommonProfileEntry 17 }
    atmfAAL2SscsMfR2DigitPacketTransport OBJECT-TYPE
        SYNTAX INTEGER {
            disabled (1),
            enabled (2)
            }
        MAX-ACCESS read-only
        STATUS current
        DESCRIPTION
            "This object describes whether transport of MF-R2 dialled
            digits is enabled or disabled."
        DEFVAL { disabled }
        ::= { atmfAAL2CommonProfileEntry 18 }
    atmfAAL2SscsCircuitModeDataTransport OBJECT-TYPE
        SYNTAX INTEGER {
            disabled (1),
            enabled (2)
            }
        MAX-ACCESS read-only
        STATUS current
        DESCRIPTION
            "This object describes whether transport of circuit mode
            data is enabled or disabled."
        DEFVAL { disabled }
        ::= { atmfAAL2CommonProfileEntry 19 }
    atmfAAL2SscsCircuitModeDataNumChannels OBJECT-TYPE
        SYNTAX INTEGER (1..31)
        MAX-ACCESS read-only
        STATUS current
        DESCRIPTION
            "This object describes the multiplier N in N*64kbit/s
            circuit mode data. It is only applicable if the value of
            atmfAAL2SscsCircuitModeDataTransport is 'enabled'."
        DEFVAL { 1 }
        ::= { atmfAAL2CommonProfileEntry 20 }
    atmfAAL2SscsFrameModeDataTransport OBJECT-TYPE
        SYNTAX INTEGER {
            disabled (1),
            enabled (2)
            }
        MAX-ACCESS read-only
        STATUS current
        DESCRIPTION
            "This object describes whether the I.366.2 frame mode data
            service is enabled or disabled."
        DEFVAL { disabled }
        ::= { atmfAAL2CommonProfileEntry 21 }
    atmfAAL2SscsFrameModeDataMaxLength OBJECT-TYPE
        SYNTAX INTEGER (1..65535)
        MAX-ACCESS read-only
        STATUS current
        DESCRIPTION
            "This object specifies the maximum length of I.366.2
            frame mode data. It is only applicable if the value
            of atmfAAL2FrameModeDataTransport is 'enabled'."
        ::= { atmfAAL2CommonProfileEntry 22 }
    ------------------------------------------------------------------
    -- ATM Forum ILMI Extension for Auto Configuration
    -- ATM Trunking AAL2 Profile
    ------------------------------------------------------------------
    atmfAAL2TrunkingProfileTable OBJECT-TYPE
        SYNTAX SEQUENCE OF atmfAAL2TrunkingProfileEntry
        MAX-ACCESS not-accessible
        STATUS current
        DESCRIPTION
            "The ATM Forum ILMI Auto Configuration Extension AAL2
            Profile Information. This table contains AAL2 parameters
            that are specific to the ATM Trunking AAL 2 application.
            These parameters are taken from af-vtoa-0113.000"
        ::= { atmfAutoConfigGroup 7 }
    atmfAAL2TrunkingProfileEntry OBJECT-TYPE
        SYNTAX atmfAAL2TrunkingProfileEntry
        MAX-ACCESS not-accessible
        STATUS current
        DESCRIPTION
            "An atmfAAL2TrunkingProfileEntry provides AAL2 parameters
            of operation for ATM Trunking applications to be used in
            addition to those provided in the Common AAL2 Profile Table.
            These together provide complete configuration of AAL2 for
            PVCs that support ATM Trunking using AAl2 as defined in
            af-vtoa-0113.000."
        INDEX { atmfAAL2ProfileIndex }
        ::= { atmfAAL2TrunkingProfileTable 1 }
    atmfAAL2TrunkingProfileEntry ::= SEQUENCE {
        atmfAAL2TrunkingAppId INTEGER,
        atmfAAL2Vcci INTEGER,
        atmfAAL2SignalingVcci INTEGER
        }
    atmfAAL2TrunkingAppId OBJECT-TYPE
        SYNTAX INTEGER
        MAX-ACCESS read-only
        STATUS current
        DESCRIPTION
            "The application identifier specifies protocol combinations
            to be used on AAL2 channels between IWFs, i.e. it implicitly
            configures the use of I.366.1 or I.366.2 for bearer and
            signaling AAL2 channels. The value of this object should be
            one of those values given in the administered list of AppIDs
            for ATM Trunking in section 5 of the ATM Forum document of
            well-known addresses and assigned codes which can be located at
            http://www.atmforum.com/atmforum/specs/public_assigned_codes.pdf."
        ::= { atmfAAL2TrunkingProfileEntry 1 }
    atmfAAL2Vcci OBJECT-TYPE
        SYNTAX INTEGER
        MAX-ACCESS read-only
        STATUS current
        DESCRIPTION
             "This object uniquely identifies a PVC between IWFs."
        ::= { atmfAAL2TrunkingProfileEntry 2 }
    atmfAAL2SignalingVcci OBJECT-TYPE
        SYNTAX INTEGER
        MAX-ACCESS read-only
        STATUS current
        DESCRIPTION
                 "This object specifies the VCCI of the PVC that is used
            to carry the CCS for this PVC."
        ::= { atmfAAL2TrunkingProfileEntry 3 }
    ------------------------------------------------------------------
    -- ATM Forum ILMI Extension for Auto Configuration
    -- ATM LES AAL2 Profile
    -- In the case where an AAL2LESProfileEntry contains parameter(s)
    -- which is/are set to a value that is/are not supported by the AAL2
    -- entity in the ATU-R, the user-side IME must raise an
    -- atmfAtmServiceConfFail trap towards the network-side IME. The
    -- atmfAtmServiceConfFailReason should be 'unsupportedAAL' and
    -- the atmfAtmServiceConfFailOID must point to the
    -- atmfAAL2LESProfileEntry that contains the unsupported
    -- parameter(s).
    ------------------------------------------------------------------
    atmfAAL2LESProfileTable OBJECT-TYPE
        SYNTAX SEQUENCE OF atmfAAL2LESProfileEntry
        MAX-ACCESS not-accessible
        STATUS current
        DESCRIPTION
            "The ATM Forum ILMI Auto Configuration Extension AAL2 Profile
            Information. This table contains AAL2 parameters that are
            specific to the ATM LES AAL 2 application. These parameters
            are taken from af-vmna-0145.000"
        ::= { atmfAutoConfigGroup 8 }
    atmfAAL2LESProfileEntry OBJECT-TYPE
        SYNTAX atmfAAL2LESProfileEntry
        MAX-ACCESS not-accessible
        STATUS current
        DESCRIPTION
            "An atmfAAL2LESProfileEntry provides AAL2 parameters of
            operation for LES applications to be used in addition to
            those provided in the Common AAL2 Profile Table. These together
            provide complete configuration of AAL2 for PVCs that support
            LES using AAl2 as defined in af-vmoa-0145.000."
        INDEX { atmfAAL2ProfileIndex }
        ::= { atmfAAL2LESProfileTable 1 }
    atmfAAL2LESProfileEntry ::= SEQUENCE {
        atmfAAL2LesAppId            INTEGER,
        atmfAAL2CpsCIDLowerLimit INTEGER,
        atmfAAL2CpsCIDUpperLimit INTEGER,
        atmfAAL2CpsOptimisation INTEGER
        }
    atmfAAL2LesAppId OBJECT-TYPE
        SYNTAX INTEGER
        MAX-ACCESS read-only
        STATUS current
        DESCRIPTION
            " The application identifier specifies protocol combinations
            to be used on AAL2 channels between IWFs, i.e. it implicitly
            configures the use of I.366.1 or I.366.2 for bearer and
            signaling AAL2 channels. The value of this object should be
            one of those values given in the administered list of AppIDs
            for LES in section 5 of the ATM Forum document of well-known
            addresses and assigned codes which can be located at
            http://www.atmforum.com/atmforum/specs/public_assigned_codes.pdf."
        ::= { atmfAAL2LESProfileEntry 1 }
    atmfAAL2CpsCIDLowerLimit OBJECT-TYPE
        SYNTAX INTEGER (16..223)
        MAX-ACCESS read-only
        STATUS current
        DESCRIPTION
            "The minimum value the CID can take for AAL2 bearer channels
            and ISDN-D channels."
        DEFVAL { 16 }
        ::= { atmfAAL2LESProfileEntry 2 }
    atmfAAL2CpsCIDUpperLimit OBJECT-TYPE
        SYNTAX INTEGER (16..223)
        MAX-ACCESS read-only
        STATUS current
        DESCRIPTION
            " The maximum value the CID can take for AAL2 bearer channels
            and ISDN-D channels."
        DEFVAL { 223 }
        ::= { atmfAAL2LESProfileEntry 3 }
    aal2CpsOptimisation OBJECT-TYPE
        SYNTAX INTEGER {
        singleCpsPacketPerCpsPduNoOverlap(1),
        multipleCpsPacketsPerCpsPduWithOverlap(2)
        }
        MAX-ACCESS read-only
        STATUS current
        DESCRIPTION
            "This object refers to the mode of operation of the CPS on the
            CP-IWF The value of this object imposes a restriction on the
            CPS-SDU length and hence must override the value of
            aal2CpsMaxSDULength.
            singleCpsPacketPerCpsPduNoOverlap -A single CPS Packet is contained
            within a CPS-PDU and no overlap can occur into the next CPS-PDU.
            If this option is selected, then Timer_CU is not applicable.
            Also Max CPS-SDU size must be less than or equal to 44.
            multipleCpsPacketsPerCpsPduWithOverlap - Multiple CPS Packets are
            contained within a CPS-PDU and overlap can occur into the next
            CPS-PDU. If this option is selected, then Timer_CU is applicable.
            Also Max CPS-SDU size must be less than or equal to 64."
        DEFVAL { singleCpsPacketPerCpsPduNoOverlap }
        ::= { atmfAAL2LESProfileEntry 4 }
    ------------------------------------------------------------------
    -- ATM Forum ILMI Extension for Auto Configuration
    -- atmfAtmServicePhyMacIdentifier
    ------------------------------------------------------------------
    atmfAtmServiceConnInfoExtensionTable OBJECT-TYPE
        SYNTAX SEQUENCE OF atmfAtmServiceConnInfoExtensionEntry
        MAX-ACCESS not-accessible
        STATUS current
            DESCRIPTION
            "The ATM Forum ILMI Auto Configuration Extension ATM
            Service Connection Information. "
        ::= { atmfAutoConfigGroup 9 }
    atmfAtmServiceConnInfoExtensionEntry OBJECT-TYPE
        SYNTAX atmfAtmServiceConnInfoExtensionEntry
        MAX-ACCESS not-accessible
        STATUS current
        DESCRIPTION
            "An entry in the service connection information extension table
            provides additional elements that help describe the ATM connection
            that provides a service across an ATM interface. The connection
            is identified by port and VPI/VCI value."
        AUGMENTS { atmfAtmServiceConnInfoEntry }
        ::= { atmfAtmServiceConnInfoExtensionTable 1 }
    atmfAtmServiceConnInfoExtensionEntry ::= SEQUENCE {
        atmfAtmServicePhyMacIdentifier INTEGER
        }
    atmfAtmServicePhyMacIdentifier OBJECT-TYPE
        SYNTAX INTEGER
        MAX-ACCESS read-only
        STATUS optional
        DESCRIPTION
            " When the physical and/or MAC layer has more than one
            PHY-connection or MAC-connection, this object is used to
            select the PHY- or MAC-connection to be bound to the PVC.
            The semantics of the value of this object is PHY and/or
            MAC specific. This semantics generally shall be specified
            with the PHY or MAC. However, the semantics for the two
            PHY/MAC specifications which have been identified as having
            multiple connections is provided here for convenience:
            When the physical layer is dual latency ADSL, the PhyMacIdentifier
            selects the latency path to be bound to each direction of
            transmission for the PVC. The value of the PhyMacIdentifier
            shall be as follows:
            default = 0
            upstream and downstream both interleaved path = 1
            upstream and downstream both fast path = 2
            upstream interleaved path, downstream fast path = 3
            upstream fast path, downstream interleaved path = 4
            The 'default' value shall be used for single latency ADSL
            PHYs.
            When the physical and MAC layers are IEEE 802.14, the
            PhyMacIdentifier specifies the 802.14 Local Identifier for the PVC"
        ::= { atmfAtmServiceConnInfoExtensionEntry 1 }
    ------------------------------------------------------------------
    -- ATM Forum ILMI Extension for Auto Configuration
    -- Layer 2 and Layer 3 Protocol ID
    ------------------------------------------------------------------
    atmfAtmServiceTypeExtensionTable OBJECT-TYPE
        SYNTAX SEQUENCE OF atmfAtmServiceTypeExtensionEntry
        MAX-ACCESS not-accessible
        STATUS current
        DESCRIPTION
            "The ATM Forum ILMI Auto Configuration Extension ATM
            Service Type Extension Information. "
        ::= { atmfAutoConfigGroup 10 }
    atmfAtmServiceTypeExtensionEntry OBJECT-TYPE
        SYNTAX atmfAtmServiceTypeExtensionEntry
        MAX-ACCESS not-accessible
        STATUS current
        DESCRIPTION
            "An entry in the service type extension table describes additional
            information about a service that may be associated with individual
            ATM connections for the purpose of auto-configuration. This
            information describes the Client Protocol ID's associated with a
            particular service."
        AUGMENTS { atmfAtmServiceTypeEntry }
        ::= { atmfAtmServiceTypeExtensionTable 1 }
    atmfAtmServiceTypeExtensionEntry ::= SEQUENCE {
        atmfAtmServiceLayer2ProtocolID OCTET STRING,
        atmfAtmServiceLayer3ProtocolID OCTET STRING
        }
    atmfAtmServiceLayer2ProtocolID OBJECT-TYPE
        SYNTAX OCTET STRING
        MAX-ACCESS read-only
        STATUS current
        DESCRIPTION
            "This object shall be used to select the user plane layer 2
            protocol (if any) to be used above the AAL. The first octet
            of this object shall be encoded as follows. Bits 5-7 (i.e.
            the three most significant bits) shall be set to 0; any other
            values shall be ignored. Bits 0-4 (i.e. the five least significant
            bits) shall be encoded as shown in the entry for 'User information
            layer 2 protocol (octet 6)' in Table 4-10/Q.2931. However, if no
            user plane layer 2 protocol is present above the AAL, then the
            first (and only) octet shall be encoded as '0b00000000'. If the
            encoding of the first octet requires subsequent octets, then bit 7
            (i.e., the most significant bit) of each of these octets shall be
            set to 0; however, if it is set to 1, it shall be ignored. Bits 0-6
            shall be encoded according to table 4-10/Q.2931. If more than one
            subsequent octet is needed, then octets shall appear in the order
            shown in figure 4-16/Q.2931."
        ::= { atmfAtmServiceTypeExtensionEntry 1 }
    atmfAtmServiceLayer3ProtocolID OBJECT-TYPE
        SYNTAX OCTET STRING
        MAX-ACCESS read-only
        STATUS current
        DESCRIPTION
            "This object shall be used to select a user plane layer 3 protocol
            (or user plane layer 2 bridging). The first octet of this object
            shall be encoded as follows. Bits 5-7 (i.e., the three most
            significant bits) shall be set to 0; any other values shall be
            ignored. Bits 0-4 (i.e., the five least significant bits) shall be
            encoded as shown in the entry for 'User information layer 3
            protocol (octet 7)' in Table 4-10/Q.2931. However, if no user plane
            layer 3 protocol is specified, then the first (and only) octet
            shall be encoded as '0b00000000'.
            a) If ISO TR9577 network layer protocol identification is to be
            used, then the first octet shall be encoded to indicate 'ISO/IEC
            TR9577'. In this case, either:
            i) the user plane layer 3 protocol is to be selected in the
            management plane. The second octet of this object shall
            contain the ISO/IEC TR9577 Initial Protocol Identifier (IPI).
            - For layer 3 protocols for which ISO/IEC has assigned a
            Network Layer Protocol Identifier (NLPID), then this NLPID
            shall be used as the IPI, and the length of the octet
            string shall be 2.
            - For layer 3 protocols for which ISO/IEC has not assigned
            an NLPID, the IPI shall be encoded to indicate 'IEEE
            802.1a SNAP identifier' (see Annex D of ISO/IEC 9577). The
            following five octets (octets 3 through 7) of this object
            
            shall then contain a SNAP identifier, which consists of a
            3-octet organization unique identifier (OUI) and a 2-octet
            protocol identifier (PID). This SNAP coding shall be used
            only if ISO/IEC has not assigned a Network Layer Protocol
            Identifier for the layer 3 or layer 2 protocol. The octet
            string shall thus be 7 octets long.
            - If an IME wishes to indicate that bridged LAN frames are
            to be carried in the user plane then the IPI shall be
            encoded to indicate 'IEEE 802.1a SNAP identifier'. The
            following five octets of this object shall contain a SNAP
            identifier, which indicates the bridged protocol.
            For consistency with SIG 4.0, use of the ISO/IEC subsequent
            protocol identifier (SPI) is not recommended but not explicitly
            prohibited as one can envision scenarios where it has utility.
            or
            ii) the user plane layer 3 protocol is to be selected using
            network layer protocol identification in the user plane. The
            octet-string shall be one octet long. The first octet(s) of
            each layer 3 protocol data unit shall contain layer 3
            protocol identification according to ISO/IEC TR9577.
            b)If bits 0-4 of the first octet of the octet string are set to any
            value other than 'ISO/IEC TR9577', then any subsequent octets shall
            be encoded as follows. Bit 7 (i.e., the most significant bit) of
            each of these octets shall be set to 0; however, if it is set to 1,
            it shall be ignored. Bits 0-6 shall be encoded according to the
            codings for octet 7a, octet 7b and octet 7c specified in table 4-
            10/Q.2931. If more than one subsequent octet is needed, then octets
            shall appear in the order shown in figure 4-16/Q.2931."
        ::= { atmfAtmServiceTypeExtensionEntry 2}
    ------------------------------------------------------------------
    -- ATM Forum ILMI Extension for Auto Configuration
    -- AAL5 Profile Extension Table
    -- This extension is required for supporting AAL2 trunking
    ------------------------------------------------------------------
    atmfAAL5ProfileExtensionTable OBJECT-TYPE
        SYNTAX SEQUENCE OF atmfAAL5ProfileExtensionEntry
        MAX-ACCESS not-accessible
        STATUS current
        DESCRIPTION
            "Additional parameters for the AAL5 Profile are stored in this
            table."
        ::= { atmfAutoConfigGroup 11 }
    atmfAAL5ProfileExtensionEntry OBJECT-TYPE
        SYNTAX atmfAAL5ProfileExtensionEntry
        MAX-ACCESS not-accessible
        STATUS current
        DESCRIPTION
            "An entry in this table augments an entry in the
            atmfAAL5ProfileTable"
        AUGMENTS { atmfAAL5ProfileEntry }
        ::= { atmfAAL5ProfileExtensionTable 1 }
    atmfAAL5ProfileExtensionEntry ::= SEQUENCE {
        atmfAAL5Vcci INTEGER
        }
    atmfAAL5Vcci OBJECT-TYPE
        SYNTAX INTEGER
        MAX-ACCESS read-only
        STATUS current
        DESCRIPTION
            "This object's value is only applicable if the AAL5 VCC is
            carrying CCS for AAL2 narrowband calls."
        ::= { atmfAAL5ProfileExtensionEntry 1 }
    atmfAtmServiceConfFailReason OBJECT-TYPE
        SYNTAX INTEGER {
            UnsupportedClientProtocol (1),
            UnsupportedServiceCategory (2),
            UnsupportedAAL (3),
            InvalidVPIVCIValue (4),
            TooManyPVCs (5),
            IncompleteConfigurationInformation (6),
            InconsistentConfigurationInformation (7)
            }
        MAX-ACCESS read-only
        STATUS current
        DESCRIPTION
            "The reason for the failure to configure the PVC at the ATU-R"
        ::= { atmfAutoConfigGroup 12 }
    atmfAtmServiceConfFailOID OBJECT-TYPE
        SYNTAX RowPointer
        ACCESS read-only
        STATUS current
        DESCRIPTION
        " "
        ::= { atmfAutoConfigGroup 13 }
    
    

 
 
 
 -- The Address Registration Admin Group
 --
 -- The Address Registration Admin Table is mandatory for all IMEs.
 
      atmfAddressRegistrationAdminTable OBJECT-TYPE
              SYNTAX SEQUENCE OF AtmfAddressRegistrationAdminEntry
              ACCESS not-accessible
              STATUS mandatory
              DESCRIPTION
                      "A table of Address Registration administrative
                      information for the ATM Interface."
              ::= { atmfAddressRegistrationAdminGroup 1 }
 
      atmfAddressRegistrationAdminEntry OBJECT-TYPE
              SYNTAX AtmfAddressRegistrationAdminEntry
              ACCESS not-accessible
              STATUS mandatory
              DESCRIPTION
                      "An entry in the table, containing Address
                      Registration administrative information for the ATM
                      Interface."
              INDEX { atmfAddressRegistrationAdminIndex }
              ::= { atmfAddressRegistrationAdminTable 1 }
      
      AtmfAddressRegistrationAdminEntry ::=
              SEQUENCE {
                      atmfAddressRegistrationAdminIndex       INTEGER,
                      atmfAddressRegistrationAdminStatus      INTEGER
              }
      
      atmfAddressRegistrationAdminIndex OBJECT-TYPE
              SYNTAX INTEGER (0..2147483647)
              ACCESS read-only                                     
         STATUS mandatory                                     
         DESCRIPTION                                          
              "The value of 0 which has the special meaning of     
              identifying the ATM Interface over which this message
              was received."                                       
         ::= { atmfAddressRegistrationAdminEntry 1 }          
 
      atmfAddressRegistrationAdminStatus OBJECT-TYPE
              SYNTAX INTEGER { supported(1), unsupported(2) }      
         ACCESS read-only                                     
         STATUS mandatory                                     
         DESCRIPTION                                          
              "An indication of whether or not Address Registration
              is supported on this ATM Interface. Supported(1)     
              indicates that this ATM Interface supports address   
              registration. Unsupported(2) indicates that this ATM 
              Interface does not support address registration."    
         ::= { atmfAddressRegistrationAdminEntry 2 }          
 
 



-- The ATM Layer Group
-- This group is mandatory for all ATM Interfaces.
--
-- ATM-layer specific information for the ATM Interface.
        
        atmfAtmLayerTable OBJECT-TYPE
                SYNTAX SEQUENCE OF AtmfAtmLayerEntry
                ACCESS not-accessible
                STATUS mandatory
                DESCRIPTION
                        "A table of ATM layer status and parameter information
                        for the ATM Interface."
                ::= { atmfAtmLayerGroup 1 }
        
        atmfAtmLayerEntry OBJECT-TYPE
                SYNTAX AtmfAtmLayerEntry
                ACCESS not-accessible
                STATUS mandatory
                DESCRIPTION
                        "An entry in the table, containing information about
                        the ATM layer of an ATM Interface."
                INDEX { atmfAtmLayerIndex }
                ::= { atmfAtmLayerTable 1 }

        AtmfAtmLayerEntry ::=
                SEQUENCE {
                        atmfAtmLayerIndex                       INTEGER,
                        atmfAtmLayerMaxVPCs                     INTEGER,
                        atmfAtmLayerMaxVCCs                     INTEGER,
                        atmfAtmLayerConfiguredVPCs      INTEGER,
                        atmfAtmLayerConfiguredVCCs      INTEGER,
                        atmfAtmLayerMaxVpiBits          INTEGER,
                        atmfAtmLayerMaxVciBits          INTEGER,
                        atmfAtmLayerUniType                     INTEGER,        
                        atmfAtmLayerUniVersion          INTEGER,
                        atmfAtmLayerDeviceType          INTEGER,
                        atmfAtmLayerIlmiVersion         INTEGER,
                        atmfAtmLayerNniSigVersion       INTEGER,
                        atmfAtmLayerMaxSvpcVpi          INTEGER,
                        atmfAtmLayerMaxSvccVpi          INTEGER,
                        atmfAtmLayerMinSvccVci          INTEGER
                }

        atmfAtmLayerIndex OBJECT-TYPE
                SYNTAX INTEGER (0..2147483647)
                ACCESS read-only
                STATUS mandatory
                DESCRIPTION
                        "The value of 0 which has the special meaning of
                        identifying the ATM Interface over which this message
                        was received."
                ::= { atmfAtmLayerEntry 1 }

        atmfAtmLayerMaxVPCs OBJECT-TYPE
                SYNTAX INTEGER (0..4096)
                ACCESS read-only
                STATUS mandatory
                DESCRIPTION
                        "The maximum number of switched and permanent VPCs
                        supported on this ATM Interface. For virtual interfaces
                        (i.e. Virtual Path Connections), the maximum number of VPCs
                        PNNI may communicate over is set to zero."
                ::= { atmfAtmLayerEntry 2 }

        atmfAtmLayerMaxVCCs OBJECT-TYPE
                SYNTAX INTEGER (0..268435456)
                ACCESS read-only
                STATUS mandatory
                DESCRIPTION
                        "The maximum number of switched and permanent VCCs
                        supported on this ATM Interface."
                ::= { atmfAtmLayerEntry 3 }
        
        atmfAtmLayerConfiguredVPCs OBJECT-TYPE
                SYNTAX INTEGER (0..4096)
                ACCESS read-only
                STATUS mandatory
                DESCRIPTION
                        "The number of permanent VPCs configured for use on
                        this ATM Interface. For virtual interfaces (i.e. Virtual Path
                        Connections used by PNNI), the maximum number of VPCs
                        is set to zero."
                ::= { atmfAtmLayerEntry 4 }
        
        atmfAtmLayerConfiguredVCCs OBJECT-TYPE
                SYNTAX INTEGER (0.. 268435456)
                ACCESS read-only
                STATUS mandatory
                DESCRIPTION
                        "The number of permanent VCCs configured for use on
                        this ATM Interface."
                ::= { atmfAtmLayerEntry 5 }
        
        atmfAtmLayerMaxVpiBits OBJECT-TYPE
                SYNTAX INTEGER (0..12)
                ACCESS read-only
                STATUS mandatory
        DESCRIPTION
                "The maximum number of active VPI bits on this ATM Interface.
                For virtual interfaces (i.e. Virtual Path Connections used by PNNI),
                this value has no meaning and is set to zero."
        ::= { atmfAtmLayerEntry 6 }

        atmfAtmLayerMaxVciBits OBJECT-TYPE
                SYNTAX INTEGER (0..16)
                ACCESS read-only
                STATUS mandatory
                DESCRIPTION
                        "The maximum number of active VCI bits on this ATM Interface."
                ::= { atmfAtmLayerEntry 7 }
        
        atmfAtmLayerUniType OBJECT-TYPE
                SYNTAX INTEGER { public(1), private(2) }
                ACCESS read-only
                STATUS mandatory
                DESCRIPTION             
                        "The type of the ATM device, either public or private."
                ::= { atmfAtmLayerEntry 8 }

        atmfAtmLayerUniVersion OBJECT-TYPE
                SYNTAX INTEGER {
                        version2point0(1),
                        version3point0(2),
                        version3point1(3),
                        version4point0(4),
                        unsupported(5)
                }
                ACCESS read-only
                STATUS mandatory
                DESCRIPTION
                        "An indication of the latest version of the ATM Forum UNI
                        Signalling Specification that is supported on this ATM
                        Interface. If this value is not present, a version of the UNI
                        earlier than 3.1 is supported.
                        If the peer IME value of this object is the same as,
                        or later than the local IME value, then the version
                        corresponding to the local IME value should be
                        attempted. Otherwise, if the peer IME value of this
                        object is earlier, and supported locally, then the
                        local IME should attempt the version corresponding to
                        the peer IME value. Otherwise, compatibility of the
                        two IMEs cannot be assumed."
                ::= { atmfAtmLayerEntry 9 }

        atmfAtmLayerDeviceType OBJECT-TYPE
                SYNTAX INTEGER { user(1), node(2) }
                ACCESS read-only
                STATUS mandatory
                DESCRIPTION
                        "This object determines the type of the ATM device. This
                        object is used in automatic ATM Interface-Type determination
                        procedure such that a correct operational ATM
                        Interface-type can be determined. An ATM End System
                        shall take the value of user(1), and an ATM network
                        node shall take the value of node(2)."
                ::= { atmfAtmLayerEntry 10 }
        
        atmfAtmLayerIlmiVersion OBJECT-TYPE
                SYNTAX INTEGER { unsupported(1), version4point0(2) }
                ACCESS read-only
                STATUS mandatory
                DESCRIPTION
                        "An indication of the latest version of the ATM Forum
                        ILMI Specification that is supported on this ATM Interface.
                        If the peer IME value of this object is the same as,
                        or later than the local IME value, then the version
                        corresponding to the local IME value should be
                        attempted. Otherwise, if the peer IME value of this
                        object is earlier, and supported locally, then the
                        local IME should attempt the version corresponding to
                        the peer IME value. Otherwise, compatibility of the
                        two IMEs cannot be assumed.
                        If this object is not present, a version of the ILMI earlier
                        than 4.0 is supported."
                ::= { atmfAtmLayerEntry 11 }

        atmfAtmLayerNniSigVersion OBJECT-TYPE           
                SYNTAX INTEGER { unsupported(1), iisp(2),
                                                pnniVersion1point0(3) }
                ACCESS read-only
                STATUS mandatory
                DESCRIPTION
                        "An indication of the latest version of the ATM Forum
                        PNNI Signalling Specification that is supported on this
                        ATM Interface. Note that the PNNI routing version is not
                        determined through ILMI.
                        If the peer IME value of this object is the same as,
                        or later than the local IME value, then the version
                        corresponding to the local IME value should be
                        attempted. Otherwise, if the peer IME value of this
                        object is earlier, and supported locally, then the
                        local IME should attempt the version corresponding to
                        the peer IME value. Otherwise, compatibility of the
                        two IMEs cannot be assumed."
                ::= { atmfAtmLayerEntry 12 }
        
        atmfAtmLayerMaxSvpcVpi OBJECT-TYPE
                SYNTAX INTEGER (0..4096)
                ACCESS read-only
                STATUS mandatory
                DESCRIPTION
                        "The maximum VPI that the signalling stack on the ATM
                        interface is configured to support for allocation to
                        switched virtual path connections."
                ::= { atmfAtmLayerEntry 13 }
        
        atmfAtmLayerMaxSvccVpi OBJECT-TYPE
                SYNTAX INTEGER (0..4096)
                ACCESS read-only
                STATUS mandatory
                DESCRIPTION
                        "The maximum VPI that the signalling stack on the ATM
                        interface is configured to support for allocation to
                        switched virtual channel connections."
                ::= { atmfAtmLayerEntry 14 }

        atmfAtmLayerMinSvccVci OBJECT-TYPE
                SYNTAX INTEGER (0..65536)
                ACCESS read-only
                STATUS mandatory
                DESCRIPTION
                        "This is the minimum VCI value that the
                        signalling stack is configured to support for
                        allocation to switched virtual channel connections. The same
                        value applies to all SVCC VPI values for which the
                        signalling stack is configured."
                ::= { atmfAtmLayerEntry 15 }




END

 




ATM-ZHONGXING-BGS10-MIB DEFINITIONS ::= BEGIN
        
--The root of the path.
        
IMPORTS
        MODULE-IDENTITY,OBJECT-TYPE,NOTIFICATION-TYPE,enterprises,Integer32,
        Unsigned32,TimeTicks,Counter32,IpAddress,Gauge32
                                                FROM SNMPv2-SMI
        AtmAddr                                 FROM ATM-TC-MIB
        ifIndex,ifOperStatus                    FROM IF-MIB
        atmInterfaceConfEntry                   FROM ATM-MIB 
        atmfPhysicalGroup                       FROM ATM-FORUM-TC-MIB
           atmfAtmServiceTypeEntry,
    atmfAtmServiceConnInfoEntry,
    atmfAAL1ProfileEntry,
    atmfAAL34ProfileEntry,
    atmfAAL5ProfileEntry ,
        atmfAAL1ProfileIndex,atmfAtmServiceVpi,
        atmfAtmServiceVci,atmfAtmServicePortIndex,
        atmfAtmServiceTypeIndex,atmfAAL5ProfileIndex,
        atmfAAL34ProfileIndex                   FROM ATM-FORUM-MIB   
        entPhysicalContainedIn, entPhysicalParentRelPos,  
        entPhysicalClass                        FROM ENTITY-MIB                         
        atmfM4TrapAlarmSeverity,atmfM4PlugInUnitEntry,
        atmfM4PlugInUnitAvailStatus,atmfM4PlugInUnitOperStatus,
        atmfM4VpUpcNpcCurrEntry,atmfM4VcUpcNpcCurrEntry,
        atmfM4TcProtoCurrEntry                  FROM ATM-FORUM-SNMP-M4-MIB
        entPhysicalIndex                        FROM ENTITY-MIB                                                                                     
        alarmValue,alarmRisingThreshold,alarmFallingThreshold
                                                FROM RFC1271-MIB
        TEXTUAL-CONVENTION,RowStatus            FROM SNMPv2-TC
        ifIndex                                 FROM IF-MIB
        atmfM4AlarmSevTrapId                    FROM ATM-FORUM-SNMP-M4-MIB
        adslLineEntry                           FROM  ADSL-LINE-MIB
        hdsl2ShdslSpanConfEntry                 FROM  HDSL2-SHDSL-LINE-MIB;
        
zhongxing MODULE-IDENTITY 
        LAST-UPDATED    "9905171300+0800"
        ORGANIZATION    "ATM Working Group,Zhongxing Telecom. Co."
        CONTACT-INFO    "
                                        ATM Data & Network Management Group,
                                        ATM Working Group,
                                        Nanjing Research Institute,
                                        Zhongxing Telecom. Co.
                                        Phone: 86 25 4826606 331
                                        Fax: 86 25 4806481
                                        Email:njzxj@public1.ptt.js.cn"
                                         
        DESCRIPTION             "The Module for Zhongxing ATM products--ZXBGS10(and its 
                                        successors)."
        REVISION                "9909021505+0800"
        DESCRIPTION             "The lastest Modification to the Port table."
                ::= { enterprises 3092}
--The type for zte S100 MIB.

DisplayString   ::=  TEXTUAL-CONVENTION
          STATUS    current
          DESCRIPTION
               "This data type is used to model textual information taken from
               the NVT ASCII character set. By convention,objects with this 
               syntax are declared as having SIZE(0...64)."
          SYNTAX    OCTET STRING
                        
--The path for zhongxing ATM.
        
zhongxingatm    OBJECT IDENTIFIER       ::= { zhongxing 2}
        
--The path for ZXBGS10 and its successors.

zxbgs10mib                      OBJECT IDENTIFIER       ::= { zhongxingatm 1}

--The Performance management MIB
bgs10PmMib              OBJECT IDENTIFIER       ::= { zxbgs10mib 31}
zxbgs10Traps            OBJECT IDENTIFIER ::= { zhongxingatm 2 }
zxDslam             OBJECT IDENTIFIER   ::= { zhongxingatm 3}
zxDslamTraps                    OBJECT IDENTIFIER ::= { zhongxingatm 4 }


--Data type for zhongxing ATM MIB.

UShort  ::=  TEXTUAL-CONVENTION
        STATUS          current
        DESCRIPTION
                "The 16-bit unsigned short integer."
        SYNTAX          INTEGER (0..65535)
        
UChar   ::= TEXTUAL-CONVENTION
        STATUS          current
        DESCRIPTION
                "The 8-bit unsigned integer."
        SYNTAX  INTEGER (0..255)
                
UCHAR   ::= TEXTUAL-CONVENTION
        STATUS          current
        DESCRIPTION
                "The 8-bit unsigned integer."
        SYNTAX  INTEGER (0..255)
        



--the zxDslam Mib 

--zxDslamMibDataLoadTable
zxDslamMibDataLoadTable         OBJECT-TYPE
        SYNTAX          SEQUENCE OF ZxDslamMibDataLoadEntry
        MAX-ACCESS      not-accessible
        STATUS          current
        DESCRIPTION
        "This table provides one row for each mib-table.
         Each row contains the action parameters for that mib-table"
        ::= { zxDslam 1 }

zxDslamMibDataLoadEntry OBJECT-TYPE
        SYNTAX          ZxDslamMibDataLoadEntry
        MAX-ACCESS      not-accessible
        STATUS          current
        DESCRIPTION
                "An entry in the zxDslamMibDataLoadEntry."
        INDEX {         zxDslamMibTableId       
                }
        ::= { zxDslamMibDataLoadTable 1 }

ZxDslamMibDataLoadEntry ::=
      SEQUENCE {
        zxDslamMibRowStatus         INTEGER,
        zxDslamMibTableId          INTEGER,
        zxDslamMibTableLastChange  TimeTicks,
        zxDslamMibLoadExecute      INTEGER,
        zxDslamMibLoadExecuteStatus   INTEGER,
        zxDslamMibTableModifyFlag     INTEGER
      }
    zxDslamMibRowStatus OBJECT-TYPE
       SYNTAX INTEGER 
       MAX-ACCESS read-write
        STATUS current
       DESCRIPTION
           " "      
    ::= { zxDslamMibDataLoadEntry 1 } 
        
zxDslamMibTableId       OBJECT-TYPE
        SYNTAX          INTEGER
        MAX-ACCESS      read-write
        STATUS          current
        DESCRIPTION
                " the index of the entry,each one represent a mib table" 
        ::= {  zxDslamMibDataLoadEntry 2 }
zxDslamMibTableLastChange       OBJECT-TYPE
        SYNTAX          TimeTicks
        MAX-ACCESS      read-write
        STATUS          current
        DESCRIPTION
               "The value of sysUpTime at the time of the last
               creation or deletion of an entry in the zxDslamMibDataLoadTable.  If
               the number of entries has been unchanged since the
               last re-initialization of the local network management
               subsystem, then this object contains a zero value."
        ::= {  zxDslamMibDataLoadEntry 3 }
    zxDslamMibLoadExecute OBJECT-TYPE
        SYNTAX INTEGER {
               noop(1),         -- no operation
               download(2),     -- Application, Boot, or Configuration
               upload(3) ,       -- Configuration only
               synchronize(4)      -- Application data  
        }
        MAX-ACCESS read-write
        STATUS current
        DESCRIPTION
            "Execute file download or upload procedure.  A SET of this
             object starts the load procedure.  Note that the Application
             and Boot images can only be downloaded.  The NVM Configuration
             file can be uploaded and downloaded.  A GET of this object
             will return the status of the executed operation. 
             Use 'zxDslamMibLoadExecuteStatus' to determine the status of
             the executed load." 
     ::= { zxDslamMibDataLoadEntry 4 }

     zxDslamMibLoadExecuteStatus OBJECT-TYPE
        SYNTAX INTEGER {
               notStarted(1),       -- download has not yet started
               inProgress(2),       -- download has not yet finished
               success(3),          -- download has finished successfully
               errorConnection(4),  -- download cannot connect
               errorFilename(5),    -- download has bad image path/filename
               errorFault(6) ,       -- download has fault condition on device
               errorUsername(7),    -- 
               errorUserPassword(8) --
        }
        MAX-ACCESS read-write
        STATUS current
        DESCRIPTION
            "Provides status on the execute file load progress."
     ::= { zxDslamMibDataLoadEntry 5 }
     
     zxDslamMibTableModifyFlag   OBJECT-TYPE    
     SYNTAX      INTEGER {
                    modify(1),            -- the table has been changed
                    unmodify(0)
        }
       MAX-ACCESS  read-write
       STATUS      current
       DESCRIPTION
               "If the table has been changed since the
               last SYN-DATA."
    ::= { zxDslamMibDataLoadEntry 6 } 
      
    
    zxDslamCommonLoadFtpTable       OBJECT-TYPE
          SYNTAX          SEQUENCE OF ZxDslamCommonLoadFtpEntry
          MAX-ACCESS      not-accessible
          STATUS          current
          DESCRIPTION
          "This table provides infomation of ftp Common."
       ::= { zxDslam 2 }
    zxDslamCommonLoadFtpEntry       OBJECT-TYPE
            SYNTAX          ZxDslamCommonLoadFtpEntry
            MAX-ACCESS      not-accessible
            STATUS          current
            DESCRIPTION
                     "An entry in the zxDslamCommonLoadFtpEntry."
            INDEX {         zxDslamCommonLoadRowStatus       
                    }
            ::= { zxDslamCommonLoadFtpTable 1 }
    
    ZxDslamCommonLoadFtpEntry ::=
          SEQUENCE {
            zxDslamCommonLoadRowStatus         INTEGER,
            zxDslamCommonLoadFtpAddress        IpAddress,
            zxDslamCommonLoadFtpFilePath       DisplayString,
            zxDslamCommonLoadFtpUserName       DisplayString,
            zxDslamCommonLoadFtpUserPassword   DisplayString,
            zxDslamCommonLoadFtpFileName       DisplayString,
            zxDslamCommonLoadStoreDataExecuteStatus      INTEGER
            
          }

    zxDslamCommonLoadRowStatus OBJECT-TYPE
        SYNTAX INTEGER
        MAX-ACCESS read-write
        STATUS current
        DESCRIPTION
            "
             " 
   ::= { zxDslamCommonLoadFtpEntry 1 }
    
    
    
    zxDslamCommonLoadFtpAddress OBJECT-TYPE
        SYNTAX IpAddress
        MAX-ACCESS read-write
        STATUS current
        DESCRIPTION
            "
             The IP Address for the TFTP server used for downloading
             and/or uploading files." 
   ::= { zxDslamCommonLoadFtpEntry 2 }

    zxDslamCommonLoadFtpFilePath OBJECT-TYPE
        SYNTAX DisplayString (SIZE (1..64))
        MAX-ACCESS read-write
        STATUS current
        DESCRIPTION
            "
             The TFTP File Path."
    ::= { zxDslamCommonLoadFtpEntry 3 }
    
        
    zxDslamCommonLoadFtpUserName OBJECT-TYPE
        SYNTAX DisplayString (SIZE (1..64))
        MAX-ACCESS read-write
        STATUS current
        DESCRIPTION
            "The TFTP username."
    ::= { zxDslamCommonLoadFtpEntry 4 }
    
    zxDslamCommonLoadFtpUserPassword OBJECT-TYPE
        SYNTAX DisplayString (SIZE (1..64))
        MAX-ACCESS read-write
        STATUS current
        DESCRIPTION
            "
             The TFTP User Password."
    ::= { zxDslamCommonLoadFtpEntry 5 }

    zxDslamCommonLoadFtpFileName OBJECT-TYPE
        SYNTAX DisplayString (SIZE (1..64))
        MAX-ACCESS read-write
        STATUS current
        DESCRIPTION
            "
             The TFTP file path and name."
    ::= { zxDslamCommonLoadFtpEntry 6 }


    zxDslamCommonLoadStoreDataExecuteStatus OBJECT-TYPE
        SYNTAX INTEGER { 
                Notstarted        (1),
                Inprogress        (2),
                Success           (3),
                Masterfailed      (4),
                Slavefailed       (5),
                Allfailed         (6)}
        MAX-ACCESS read-write
        STATUS current
        DESCRIPTION
            " save flash operatioanl status."
    ::= { zxDslamCommonLoadFtpEntry 7 }


--  zxDslamModuleSoftwareLoadTable
    zxDslamModuleSoftwareLoadTable  OBJECT-TYPE
      SYNTAX          SEQUENCE OF ZxDslamModuleSoftwareLoadEntry
      MAX-ACCESS      not-accessible
      STATUS          current
      DESCRIPTION
      "This table provides one row for each card type.
       Each row contains the action parameters for that kind of card"
     ::= { zxDslam 3 }
     
     zxDslamModuleSoftwareLoadEntry OBJECT-TYPE
      SYNTAX          ZxDslamModuleSoftwareLoadEntry
      MAX-ACCESS      not-accessible
      STATUS          current
      DESCRIPTION     "An entry in the zxDslamModuleSoftwareLoadTable."
      INDEX           { zxDslamModuleType }
     ::= { zxDslamModuleSoftwareLoadTable 1 }
    
    
     ZxDslamModuleSoftwareLoadEntry ::=
       SEQUENCE {
        zxDslamModuleRowStatus                             INTEGER,
        zxDslamModuleType                                  INTEGER,
        zxDslamModuleSoftwareLoadExecute                   INTEGER,
        zxDslamModuleSoftwareLoadExecuteStatus             INTEGER
      }
      
      zxDslamModuleRowStatus    OBJECT-TYPE
       SYNTAX INTEGER 
       MAX-ACCESS not-accessible 
       STATUS current
       DESCRIPTION
           " the index of the entry,each one represent a  module"      
        ::= { zxDslamModuleSoftwareLoadEntry 1 }         
      
      zxDslamModuleType OBJECT-TYPE
       SYNTAX INTEGER {
                UNKNOWN(0),  
                CORE   (1),   
                WANB   (2),   
                WANA   (3),   
                POWER  (4),  
                ATUCC  (5),  
                ATUCB  (6),  
                OTHER  (7), 
                COREA  (8), 
                COREC  (9),  
                WANA1  (10), 
                WANAD  (11), 
                WANE   (12),  
                LAN    (13),   
                ATUCD  (14), 
                ATUCE  (15), 
                ATUCF  (16), 
                ATUCH  (18), 
                ATUCI  (19), 
                IMAA   (20),  
                COREA2 (21),
                COREB2 (22),
                COREC2 (23),
                COREA3 (24),
                COREB3 (25),
                COREC3 (26),
                IMAB   (27),  
                LANAA  (28), 
                LANAB  (29), 
                LANAC  (30), 
                LANAD  (31), 
                LANBA  (32), 
                LANBB  (33), 
                LANCA  (34), 
                LANCB  (35), 
                LANCC  (36), 
                LANCD  (37), 
                LANDA  (38), 
                LANDB  (39), 
                
                STUCA  (40), --   SA          
                ATUGI  (41), --   GI          
                ATUGA  (17), --   ATU GA          
                ATUGB  (44), --   ATU GB          
                STUCB  (45), --   ATU SB          
                VTUCA  (46), --   ATU VA          
                VTUCB  (47), --   ATU VB          
                
                LNP    (67), --   lINE PROTECT P         
                LNR    (68), --   LINE CONNECT R         
                COREM  (69), --   CORE CARD M           
                CORES  (43), --   CORE CARD S           
                WAND   (70), --   WAN CARD D     
                GEIA   (71), --   GE CARD A       
                WANF   (72), --   WAN CARD F       
                WANFS  (73), --   WAN CARD SUB CARD FS  
                WANFM  (74), --   WAN CARD SUB CARD FM  
                WANFL  (75), --   WAN CARD SUB CARD FL  
                WANC   (76), --   WAN CARD C       
                WANAB  (77), --   WAN CARD AB      
                WANAS  (78), --   WAN CARD SUB CARD AS  
                WANAM  (79), --   WAN CARD SUB CARD AM  
                WANAL  (80), --   WAN CARD SUB CARD AL  
                WANB1  (42), --   WAN CARD B1      
                WANB   (2 ), --   WAN CARD B       
                
                IMAA   (20), --   N*E1 INTERFACE CARD 
                IMAB   (27), --   N*E1 INTERFACE CARD 
                IMAD   (81), --   N*E1 SUB CARD 
                E1A    (82), --   16*E1 INTERFACE CARD 
                IMAX   (83), --   8*E1 INTERFACE CARD 
                E1X    (84), --   8*E1 INTERFACE CARD 
                E1B    (85)  --   16*E1 INTERFACE CARD 
                }
       MAX-ACCESS not-accessible 
       STATUS current
       DESCRIPTION
           " the index of the entry,each one represent a  module"      
    ::= { zxDslamModuleSoftwareLoadEntry 2 }         
             
    zxDslamModuleSoftwareLoadExecute OBJECT-TYPE
        SYNTAX INTEGER {
               noop(1),         -- no operation
               download(2),     -- Application, Boot, or Configuration
               upload(3)
              }
        MAX-ACCESS read-write
        STATUS current
        DESCRIPTION
            "Execute file download or upload procedure.  A SET of this
             object starts the load procedure.  Note that the Application
             and Boot images can only be downloaded.  The NVM Configuration
             file can be uploaded and downloaded.  A GET of this object
             will return the status of the executed operation. 
             Use 'zxDslamMibLoadExecuteStatus' to determine the status of
             the executed load." 
     ::= { zxDslamModuleSoftwareLoadEntry 3 }

     zxDslamModuleSoftwareLoadExecuteStatus OBJECT-TYPE
        SYNTAX INTEGER {
               notStarted(1),       -- download has not yet started
               inProgress(2),       -- download has not yet finished
               success(3),          -- download has finished successfully
               errorConnection(4),  -- download cannot connect
               errorFilename(5),    -- download has bad image path/filename
               errorFault(6),        -- download has fault condition on device
               errorUsername(7) ,    -- 
               errorUserPassword(8) --
        }
        MAX-ACCESS read-only 
        STATUS current
        DESCRIPTION
            "Provides status on the execute file load progress."
     ::= { zxDslamModuleSoftwareLoadEntry 4 }


-- zxDslamAdslLinePerfStatisticTable

zxDslamAdslLinePerfStatisticTable OBJECT-TYPE
        SYNTAX SEQUENCE OF ZxDslamAdslLinePerfStatisticEntry
        MAX-ACCESS      not-accessible
        STATUS          current
        DESCRIPTION
         "This table provides one row for each adsl interface.
          Each row contains the perf statistic parameters for this adsl line"
     ::= { zxDslam 4 }

     zxDslamAdslLinePerfStatisticEntry  OBJECT-TYPE
       SYNTAX      ZxDslamAdslLinePerfStatisticEntry
       MAX-ACCESS  not-accessible
       STATUS      current
       DESCRIPTION
               "An entry containing additional performance management information
               applicable to a adsl line interface."
       AUGMENTS    { adslLineEntry }
     ::= { zxDslamAdslLinePerfStatisticTable 1 }

     
     ZxDslamAdslLinePerfStatisticEntry ::=
          SEQUENCE {
             zxDslamAdslLinePerfStatisticRowStatus   INTEGER,
             zxDslamAdslLinePerfStatisticTableIdList INTEGER,
             zxDslamAdslLinePerfStatisticAction      INTEGER
          }
     zxDslamAdslLinePerfStatisticRowStatus   OBJECT-TYPE
         SYNTAX   INTEGER
         MAX-ACCESS  read-write
         STATUS      current
         DESCRIPTION
               "" 
     ::= { zxDslamAdslLinePerfStatisticEntry 1 }                
          
     zxDslamAdslLinePerfStatisticTableIdList   OBJECT-TYPE
         SYNTAX   INTEGER
                     {
                      atucPhysTable(0),
                      aturPhysTable(1),            
                      atucChanTable(2),
                      aturChanTable(3),            
                      atucPerfDataTable(4),      
                      aturPerfDataTable(5),      
                      atucIntervalTable(6),        
                      aturIntervalTable(7) ,       
                      atucChanPerfDataTable(8),
                      aturChanPerfDataTable(9),    
                      atucChanIntervalTable(10) ,   
                      aturChanintervalTable(11)
                     }
         MAX-ACCESS  read-write
         STATUS      current
         DESCRIPTION
               "bitmap for perf statistic object table" 
     ::= { zxDslamAdslLinePerfStatisticEntry 2 }              
     
     zxDslamAdslLinePerfStatisticAction   OBJECT-TYPE   
        SYNTAX INTEGER{
                    noop(2),         -- no operation
                    on(1),      
                    off(0)
                 }
       MAX-ACCESS  read-write
         STATUS      current
         DESCRIPTION
               "bitmap for perf statistic object table" 
     ::= { zxDslamAdslLinePerfStatisticEntry 3 }     

--  zxDslamShdslLinePerfStatisticTable
zxDslamShdslLinePerfStatisticTable OBJECT-TYPE
        SYNTAX SEQUENCE OF ZxDslamShdslLinePerfStatisticEntry
        MAX-ACCESS      not-accessible
        STATUS          current
        DESCRIPTION
         "This table provides one row for each Shdsl interface.
          Each row contains the perf statistic parameters for this Shdsl line"
     ::= { zxDslam 5 }
     
     zxDslamShdslLinePerfStatisticEntry  OBJECT-TYPE
       SYNTAX      ZxDslamShdslLinePerfStatisticEntry
       MAX-ACCESS  not-accessible
       STATUS      current
       DESCRIPTION
               "An entry containing additional performance management information
               applicable to a Shdsl line interface."
       AUGMENTS    { hdsl2ShdslSpanConfEntry }
     ::= { zxDslamShdslLinePerfStatisticTable 1 }
       
     ZxDslamShdslLinePerfStatisticEntry ::=
          SEQUENCE {
             zxDslamShdslLinePerfStatisticRowStatus   INTEGER,
             zxDslamShdslLinePerfStatisticTableIdList INTEGER,
             zxDslamShdslLinePerfStatisticAction      INTEGER
          }
     zxDslamShdslLinePerfStatisticRowStatus   OBJECT-TYPE
         SYNTAX   INTEGER
         MAX-ACCESS  read-write
         STATUS      current
         DESCRIPTION
               "" 
     ::= { zxDslamShdslLinePerfStatisticEntry 1 }                
     zxDslamShdslLinePerfStatisticTableIdList   OBJECT-TYPE
         SYNTAX   INTEGER
               {
               hdsl2ShdslSpanStatusTable(0),
               hdsl2ShdslInventoryTable(1),
               hdsl2ShdslEndpointCurrTable(2),
               hdsl2Shdsl15MinIntervalTable(3),
               hdsl2Shdsl1DayIntervalTable(4)
               }
         MAX-ACCESS  read-write
         STATUS      current
         DESCRIPTION
               "bitmap for perf statistic object table" 
     ::= { zxDslamShdslLinePerfStatisticEntry 2 }              
     
     zxDslamShdslLinePerfStatisticAction   OBJECT-TYPE   
        SYNTAX INTEGER{
                    noop(2),         -- no operation
                    on(1),      
                    off(0)
                 }
       MAX-ACCESS  read-write
       STATUS      current
       DESCRIPTION
               "bitmap for perf statistic object table" 
     ::= { zxDslamShdslLinePerfStatisticEntry 3 }     

--  zxDslamimaGroupStatCurTable
zxDslamimaGroupStatCurTable  OBJECT-TYPE
        SYNTAX SEQUENCE OF ZxDslamimaGroupStatCurEntry
        MAX-ACCESS      not-accessible
        STATUS          current
        DESCRIPTION
         ""
     ::= { zxDslam 6 }
     
     zxDslamimaGroupStatCurEntry  OBJECT-TYPE
       SYNTAX      ZxDslamimaGroupStatCurEntry
       MAX-ACCESS  not-accessible
       STATUS      current
       DESCRIPTION
               ""
      INDEX           { zxDslamimaGroupStatCurRowStatus  }
     ::= { zxDslamimaGroupStatCurTable 1 }
       
     ZxDslamimaGroupStatCurEntry ::=
          SEQUENCE {
             zxDslamimaGroupStatCurRowStatus                            UChar,
             zxDslamimaGroupStatCurTxDiscardedCells             Unsigned32,
             zxDslamimaGroupStatCurimaGroupTxCells              Unsigned32,
             zxDslamimaGroupStatCurTxFillerCells        Unsigned32,
             zxDslamimaGroupStatCurimaGroupRxCells                      Unsigned32,
             zxDslamimaGroupStatCurRxDroppedCells       Unsigned32,
             zxDslamimaGroupStatCurRxFilleredCells          Unsigned32,
             zxDslamimaGroupStatCurRxFillerCells        Unsigned32
          }
          
     zxDslamimaGroupStatCurRowStatus   OBJECT-TYPE
         SYNTAX   UChar
         MAX-ACCESS  read-write
         STATUS      current
         DESCRIPTION
               "" 
     ::= { zxDslamimaGroupStatCurEntry 1 }   
     zxDslamimaGroupStatCurTxDiscardedCells   OBJECT-TYPE
         SYNTAX   Unsigned32
         MAX-ACCESS  read-write
         STATUS      current
         DESCRIPTION
               "" 
     ::= { zxDslamimaGroupStatCurEntry 2 }   
     zxDslamimaGroupStatCurimaGroupTxCells  OBJECT-TYPE
         SYNTAX   Unsigned32
         MAX-ACCESS  read-write
         STATUS      current
         DESCRIPTION
               "" 
     ::= { zxDslamimaGroupStatCurEntry 3 }   
     zxDslamimaGroupStatCurTxFillerCells   OBJECT-TYPE
         SYNTAX   Unsigned32
         MAX-ACCESS  read-write
         STATUS      current
         DESCRIPTION
               "" 
     ::= { zxDslamimaGroupStatCurEntry 4 }   
     zxDslamimaGroupStatCurimaGroupRxCells   OBJECT-TYPE
         SYNTAX   Unsigned32
         MAX-ACCESS  read-write
         STATUS      current
         DESCRIPTION
               "" 
     ::= { zxDslamimaGroupStatCurEntry 5 }   
     zxDslamimaGroupStatCurRxDroppedCells   OBJECT-TYPE
         SYNTAX   Unsigned32
         MAX-ACCESS  read-write
         STATUS      current
         DESCRIPTION
               "" 
     ::= { zxDslamimaGroupStatCurEntry 6 }   
     zxDslamimaGroupStatCurRxFilleredCells   OBJECT-TYPE
         SYNTAX   Unsigned32
         MAX-ACCESS  read-write
         STATUS      current
         DESCRIPTION
               "" 
     ::= { zxDslamimaGroupStatCurEntry 7 }
     zxDslamimaGroupStatCurRxFillerCells   OBJECT-TYPE
         SYNTAX   Unsigned32
         MAX-ACCESS  read-write
         STATUS      current
         DESCRIPTION
               "" 
     ::= { zxDslamimaGroupStatCurEntry 8 }      

--  zxDslamimaLinkStatCurTable
zxDslamimaLinkStatCurTable   OBJECT-TYPE
        SYNTAX SEQUENCE OF ZxDslamimaLinkStatCurEntry
        MAX-ACCESS      not-accessible
        STATUS          current
        DESCRIPTION
         ""
     ::= { zxDslam 7 }
     
     zxDslamimaLinkStatCurEntry  OBJECT-TYPE
       SYNTAX      ZxDslamimaLinkStatCurEntry
       MAX-ACCESS  not-accessible
       STATUS      current
       DESCRIPTION
               ""
      INDEX           { zxDslamimaLinkStatCurRowStatus  }
     ::= { zxDslamimaLinkStatCurTable 1 }
       
     ZxDslamimaLinkStatCurEntry ::=
          SEQUENCE {
             zxDslamimaLinkStatCurRowStatus                     UChar,
             zxDslamimaLinkStatCurimaLinkTxUserCells                    Unsigned32,
             zxDslamimaLinkStatCurimaLinkTxStuffCells           Unsigned32,
             zxDslamimaLinkStatCurimaLinkRxUserCells            Unsigned32,
             zxDslamimaLinkStatCurimaLinkRxStuffCells           Unsigned32,
             zxDslamimaLinkStatCurimaLinkRxFilteredCells        Unsigned32,
             zxDslamimaLinkStatCurimaLinkRxDroppedCells         Unsigned32,
             zxDslamimaLinkStatCurimaLinkRxOifAnomalies         Unsigned32,
             zxDslamimaLinkStatCurimaLinkRxIcpViolations        Unsigned32,
             zxDslamimaLinkStatCurimaLinkRxIcpCells         Unsigned32,
             zxDslamimaLinkStatCurimaLinkRxFillerCells          Unsigned32,
             zxDslamimaLinkStatCurimaLinkRxHcsErrs              Unsigned32
          }
          
     zxDslamimaLinkStatCurRowStatus   OBJECT-TYPE
         SYNTAX   UChar
         MAX-ACCESS  read-write
         STATUS      current
         DESCRIPTION
               "" 
     ::= { zxDslamimaLinkStatCurEntry 1 }   
     zxDslamimaLinkStatCurimaLinkTxUserCells   OBJECT-TYPE
         SYNTAX   Unsigned32
         MAX-ACCESS  read-write
         STATUS      current
         DESCRIPTION
               "" 
     ::= { zxDslamimaLinkStatCurEntry 2 }      
     zxDslamimaLinkStatCurimaLinkTxStuffCells   OBJECT-TYPE
         SYNTAX   Unsigned32
         MAX-ACCESS  read-write
         STATUS      current
         DESCRIPTION
               "" 
     ::= { zxDslamimaLinkStatCurEntry 3 }      
     zxDslamimaLinkStatCurimaLinkRxUserCells   OBJECT-TYPE
         SYNTAX   Unsigned32
         MAX-ACCESS  read-write
         STATUS      current
         DESCRIPTION
               "" 
     ::= { zxDslamimaLinkStatCurEntry 4 }      
     zxDslamimaLinkStatCurimaLinkRxStuffCells   OBJECT-TYPE
         SYNTAX   Unsigned32
         MAX-ACCESS  read-write
         STATUS      current
         DESCRIPTION
               "" 
     ::= { zxDslamimaLinkStatCurEntry 5 }      
     zxDslamimaLinkStatCurimaLinkRxFilteredCells   OBJECT-TYPE
         SYNTAX   Unsigned32
         MAX-ACCESS  read-write
         STATUS      current
         DESCRIPTION
               "" 
     ::= { zxDslamimaLinkStatCurEntry 6 }      
     zxDslamimaLinkStatCurimaLinkRxDroppedCells   OBJECT-TYPE
         SYNTAX   Unsigned32
         MAX-ACCESS  read-write
         STATUS      current
         DESCRIPTION
               "" 
     ::= { zxDslamimaLinkStatCurEntry 7 }      
     zxDslamimaLinkStatCurimaLinkRxOifAnomalies   OBJECT-TYPE
         SYNTAX   Unsigned32
         MAX-ACCESS  read-write
         STATUS      current
         DESCRIPTION
               "" 
     ::= { zxDslamimaLinkStatCurEntry 8 }      
     zxDslamimaLinkStatCurimaLinkRxIcpViolations   OBJECT-TYPE
         SYNTAX   Unsigned32
         MAX-ACCESS  read-write
         STATUS      current
         DESCRIPTION
               "" 
     ::= { zxDslamimaLinkStatCurEntry 9 }      
     zxDslamimaLinkStatCurimaLinkRxIcpCells   OBJECT-TYPE
         SYNTAX   Unsigned32
         MAX-ACCESS  read-write
         STATUS      current
         DESCRIPTION
               "" 
     ::= { zxDslamimaLinkStatCurEntry 10 }      
     zxDslamimaLinkStatCurimaLinkRxFillerCells   OBJECT-TYPE
         SYNTAX   Unsigned32
         MAX-ACCESS  read-write
         STATUS      current
         DESCRIPTION
               "" 
     ::= { zxDslamimaLinkStatCurEntry 11 }      
     zxDslamimaLinkStatCurimaLinkRxHcsErrs   OBJECT-TYPE
         SYNTAX   Unsigned32
         MAX-ACCESS  read-write
         STATUS      current
         DESCRIPTION
               "" 
     ::= { zxDslamimaLinkStatCurEntry 12 }      
     
        
--end of zhongxing mib.


        
-- The Physical Port Table
        atmfPortTable OBJECT-TYPE
                SYNTAX SEQUENCE OF AtmfPortEntry
                ACCESS not-accessible
                STATUS mandatory
                DESCRIPTION
                        "A table of physical layer status and parameter
                        information for the ATM Interface physical interface."
                ::= { atmfPhysicalGroup 1 }
 
        atmfPortEntry OBJECT-TYPE
                SYNTAX AtmfPortEntry
                ACCESS not-accessible
                STATUS mandatory
                DESCRIPTION
                        "An entry in the table, containing information about
                        the physical layer of an ATM Interface."
                INDEX { atmfPortIndex }
                ::= { atmfPortTable 1 }
 
        AtmfPortEntry ::=
                SEQUENCE {
                        atmfPortIndex                           INTEGER,
--                        atmfPortAddress                         AtmAddress,
                        atmfPortTransmissionType        OBJECT IDENTIFIER,
                        atmfPortMediaType                       OBJECT IDENTIFIER,
                        atmfPortOperStatus                      INTEGER
 --                     atmfPortSpecific                        OBJECT IDENTIFIER,
 --                     atmfPortMyIfName                        DisplayString,
 --                     atmfPortMyIfIdentifier          INTEGER
                }
 
        atmfPortIndex OBJECT-TYPE
                SYNTAX INTEGER (0..2147483647)
                ACCESS read-only
                STATUS mandatory
                DESCRIPTION
                        "The value of 0 which has the special meaning of
                        identifying the ATM Interface over which this message
                        was received."
                ::= { atmfPortEntry 1 }
 
--     atmfPortAddress OBJECT-TYPE
--             SYNTAX AtmAddress
--             ACCESS read-only
--             STATUS obsolete
--             DESCRIPTION
--                     "This object should not be implemented except as
--                     required for backward compatibility with version 2.0
--                     of the UNI specification. The Address Group, defined
--                     in theAddress Registration MIB should be used instead."
--             ::= { atmfPortEntry 2 }

     atmfPortTransmissionType OBJECT-TYPE
             SYNTAX OBJECT IDENTIFIER
             ACCESS read-only
             STATUS deprecated
             DESCRIPTION
                     "This object should not be implemented except as
                     required for backward compatibility with version 3.1
                     of the UNI specification. Appropriate Network Management
                     MIBs should be used instead."
             ::= { atmfPortEntry 3 }

     atmfPortMediaType OBJECT-TYPE
             SYNTAX OBJECT IDENTIFIER
             ACCESS read-only
             STATUS deprecated
             DESCRIPTION
                     "This object should not be implemented except as
                     required for backward compatibility with version 3.1
                     of the UNI specification. Appropriate Network Management
                     MIBs should be used instead."
             ::= { atmfPortEntry 4 }

     atmfPortOperStatus OBJECT-TYPE
             SYNTAX INTEGER {
                     other(1),
                     inService(2),
                     outOfService(3),
                     loopBack(4)
             }
             ACCESS read-only
             STATUS deprecated
             DESCRIPTION
                     "This object should not be implemented except as
                     required for backward compatibility with version 3.1
                     of the UNI specification. Appropriate Network Management
                     MIBs should be used instead."
             ::= { atmfPortEntry 5 }
     
 --     atmfPortSpecific OBJECT-TYPE
 --             SYNTAX OBJECT IDENTIFIER
 --             ACCESS read-only
 --             STATUS deprecated
 --             DESCRIPTION
 --                     "This object should not be implemented except as
 --                     required for backward compatibility with version 3.1
 --                     of the UNI specification. Appropriate Network Management
 --                     MIBs should be used instead."
 --             ::= { atmfPortEntry 6 }
 --
 --     atmfPortMyIfName OBJECT-TYPE
 --             SYNTAX DisplayString
 --             ACCESS read-only
 --             STATUS mandatory
 --             DESCRIPTION
 --                     "A textual name of this interface. If this system is
 --                     manageable through SNMP, and supports the object
 --                     ifName, the value of this object must be identical
 --                     with that of ifName for the ifEntry of the lowest       
 --                     level physical interface for this port. This interface
 --                     must be uniquely named on this system to distinguish
 --                     parallel links with a neighboring system. If this
 --                     interface does not have a textual name, the value of
 --                     this object is a zero length string."
 --             ::= { atmfPortEntry 7 }
 --
 --     atmfPortMyIfIdentifier OBJECT-TYPE
 --             SYNTAX INTEGER (0..2147483647)
 --             ACCESS read-only
 --             STATUS mandatory
 --             DESCRIPTION
 --                     "A unique value for each ATM interface. The scheme used to
 --                     number the ATM interfaces on an ATM device is
 --                     implementation specific. One way to generate this value is
 --                     to use the ifIndex that an SNMP manager would use to
 --                     identify the port. This interface must be uniquely numbered
 --                     on this system to distinguish parallel links with a
 --                     neighboring system."
 --             ::= { atmfPortEntry 8 }
 
 -- Note: The typical IME will support only one of the following two objects
 
 --             atmfMyIpNmAddress OBJECT-TYPE
 --                     SYNTAX IpAddress
 --                     ACCESS read-only
 --                     STATUS mandatory
 --                     DESCRIPTION
 --                             "An IP Address to which a Network Management Station
 --                             can send Network Management protocol messages, e.g. SNMP
 --                             messages to UDP port 161, in order to access network
 --                             management information concerning the operation of the
 --                             ATM device local to this IME. If this object is supported,
 --                             but the Network Management Agent has not been configured with
 --                             an IP Address, the IME should return 0.0.0.0."
 --                     ::= { atmfPhysicalGroup 2 }
 --
 --             atmfMyOsiNmNsapAddress OBJECT-TYPE
 --                     SYNTAX ClnpAddress
 --                     ACCESS read-only
 --                     STATUS mandatory
 --                     DESCRIPTION
 --                             "An NSAP Address to which a Network Management Station
 --                             can send Network Management protocol messages in order
 --                             to access network management information concerning
 --                             the operation of the ATM device local to this IME.
 --                             If this object is supported,
 --                             but the Network Management Agent has not been configured with
 --                             an NSAP Address, the IME should return 0.0.0.0"
 --                     ::= { atmfPhysicalGroup 3 }
 --
 --             atmfMySystemIdentifier OBJECT-TYPE
 --                     SYNTAX OCTET STRING (SIZE (6))
 --                     ACCESS read-only
 --                     STATUS mandatory
 --                     DESCRIPTION
 --                             "A 48 bit identifier, taken from the IEEE universally
 --                             administered MAC address space, which uniquely
 --                             identifies the ATM device local to this IME."
 --                     ::= { atmfPhysicalGroup 4 }
 --     



bgs10PortTable  OBJECT-TYPE
        SYNTAX          SEQUENCE OF BGS10PortEntry
        MAX-ACCESS      not-accessible
        STATUS          current
        DESCRIPTION
                "The Port configuration table extensions.This table augments
                the Port table in af-ilmi-0065.00."
        ::= { zxbgs10mib 18 }

bgs10PortEntry  OBJECT-TYPE
        SYNTAX          BGS10PortEntry
        MAX-ACCESS      not-accessible
        STATUS          current
        DESCRIPTION
                "Additional columns for the Port table entry."
         AUGMENTS { atmfPortEntry }
        ::= { bgs10PortTable 1 }

BGS10PortEntry ::=
        SEQUENCE { 
                bgs10PortRType                          UChar,
                bgs10PortSpeed                          Unsigned32,
                bgs10PortAisRdiActionFlag       UChar,          
                bgs10PortSDHActionFlag          UChar,
                bgs10PortUniFlag                        BITS,
                bgs10PortAdminStatus            BITS,
                bgs10PortObserve                        BITS,
                bgs10PortLoopFlag                       BITS,
                bgs10PortLoopEnable                     BITS,
                bgs10PortTransmissionType       INTEGER,
                bgs10PortMediaType                      INTEGER,
                bgs10PortRowStatus              RowStatus,
                bgs10Portfeeflag                INTEGER,
                bgs10PortChipSet                INTEGER,
                bgs10PortatmfOperStatus         UShort,
                bgs10Portd                      UChar,
                bgs10PortShapingFlag            UShort,
                bgs10PortNMSAdminStatus     UShort,
                bgs10PortAPSLogicPort       UShort,
                bgs10PortAPSLogicPortStatus UShort,
                bgs10PortUsedPortSpeed      INTEGER
                
        }  
        
bgs10PortRType  OBJECT-TYPE
        SYNTAX          UChar
        MAX-ACCESS      read-create
        STATUS          current
        DESCRIPTION
                "The remote port type."
        ::= {  bgs10PortEntry 2 }
        
bgs10PortSpeed  OBJECT-TYPE
        SYNTAX          Unsigned32
        MAX-ACCESS      read-create
        STATUS          current
        DESCRIPTION
                "The speed ."
        ::= { bgs10PortEntry 3 }

bgs10PortAisRdiActionFlag       OBJECT-TYPE
        SYNTAX          UChar
        MAX-ACCESS      read-create
        STATUS          current
        DESCRIPTION
                "the AID and RDI action flag."
        ::= { bgs10PortEntry 4 }
        
bgs10PortSDHActionFlag          OBJECT-TYPE
        SYNTAX          UChar
        MAX-ACCESS      read-create
        STATUS          current
        DESCRIPTION
                "the SDH action flag."
        ::= { bgs10PortEntry 5 }

bgs10PortUniFlag                OBJECT-TYPE
        SYNTAX          BITS { uni(0),
                                           nni(1)
                                        }       
        MAX-ACCESS      read-create
        STATUS          current
        DESCRIPTION
                "."
        ::= { bgs10PortEntry 6 }
        
bgs10PortAdminStatus    OBJECT-TYPE
        SYNTAX          BITS { unlock(0),
                                           lock(1)
                                        }       
        MAX-ACCESS      read-create
        STATUS          current
        DESCRIPTION
                "."
        ::= {   bgs10PortEntry 7 }

bgs10PortObserve                OBJECT-TYPE
        SYNTAX          BITS { disable(0),
                                           enble(1)
                                        }       
        MAX-ACCESS      read-create
        STATUS          current
        DESCRIPTION
                "."
        ::= {   bgs10PortEntry 8 }
        
bgs10PortLoopFlag       OBJECT-TYPE
        SYNTAX          BITS { inner-loop(0),
                                           outer-loop(1)
                                        }       
        MAX-ACCESS      read-create
        STATUS          current
        DESCRIPTION
                "."
        ::= {   bgs10PortEntry 9 }
        
bgs10PortLoopEnable     OBJECT-TYPE
        SYNTAX          BITS { disactive(0),
                                           active(1)
                                        }       
        MAX-ACCESS      read-create
        STATUS          current
        DESCRIPTION
                "."
        ::= {   bgs10PortEntry 10 }

bgs10PortTransmissionType       OBJECT-TYPE
        SYNTAX          INTEGER { atmfUnknownType (1),
                                                atmfSonetSTS3c (2),
                                                atmfDs3 (3),
                                                atmf4B5B (4),
                                                atmf8B10B (5),
                                                atmfSonetSTS12c (6),
                                                atmfE3 (7),
                                                atmfT1 (8),
                                                atmfE1 (9)
                                        }
        MAX-ACCESS      read-create
        STATUS          current
        DESCRIPTION
                "The transmission type ,refeneced to the ATH formum's port table.."
        ::= {   bgs10PortEntry 11 }
        
bgs10PortMediaType              OBJECT-TYPE
        SYNTAX          INTEGER { atmfMediaUnknownType (1),
                                                atmfMediaCoaxCable (2),
                                                atmfMediaSingleMode (3),
                                                atmfMediaMultiMode (4),
                                                atmfMediaStp (5),
                                                atmfMediaUtp (6)
                                        }
        MAX-ACCESS      read-create
        STATUS          current
        DESCRIPTION
                "The mdeia type ,refeneced the ATH formum's port table."
        ::= {   bgs10PortEntry 12 }

bgs10PortRowStatus              OBJECT-TYPE
        SYNTAX          RowStatus
        MAX-ACCESS      read-create
        STATUS          current
        DESCRIPTION
                "The mdeia type ,refeneced the ATH formum's port table."
        ::= {   bgs10PortEntry 13 }
        
bgs10Portfeeflag                OBJECT-TYPE
        SYNTAX          INTEGER
        MAX-ACCESS      read-create
        STATUS          current
        DESCRIPTION
                "   "
        ::= {   bgs10PortEntry 14 }
bgs10PortChipSet                OBJECT-TYPE
        SYNTAX          INTEGER
        MAX-ACCESS      read-create
        STATUS          current
        DESCRIPTION
                "   "
        ::= {   bgs10PortEntry 15 }
bgs10PortatmfOperStatus         OBJECT-TYPE
        SYNTAX          UShort
        MAX-ACCESS      read-create
        STATUS          current
        DESCRIPTION
                "   "
        ::= {   bgs10PortEntry 16 }
bgs10Portd              OBJECT-TYPE
        SYNTAX          UChar
        MAX-ACCESS      read-create
        STATUS          current
        DESCRIPTION
                "   "
        ::= {   bgs10PortEntry 17 }
bgs10PortShapingFlag    OBJECT-TYPE
        SYNTAX          UShort
        MAX-ACCESS      read-create
        STATUS          current
        DESCRIPTION
                "   "
        ::= {   bgs10PortEntry 18 }
        
bgs10PortNMSAdminStatus     OBJECT-TYPE
    SYNTAX      UShort
    MAX-ACCESS  read-create
    STATUS      current
    DESCRIPTION
        " BT ADD  "
    ::= {   bgs10PortEntry 19 }
        
bgs10PortAPSLogicPort       OBJECT-TYPE
    SYNTAX      UShort
    MAX-ACCESS  read-create
    STATUS      current
    DESCRIPTION
        " bt add  "
    ::= {   bgs10PortEntry 20 }

bgs10PortAPSLogicPortStatus     OBJECT-TYPE
    SYNTAX      UShort
    MAX-ACCESS  read-create
    STATUS      current
    DESCRIPTION
        " bt add  "
    ::= {   bgs10PortEntry 21 }

bgs10PortUsedPortSpeed  OBJECT-TYPE
    SYNTAX      UShort
    MAX-ACCESS  read-create
    STATUS      current
    DESCRIPTION
        " bt add  "
    ::= {   bgs10PortEntry 22 }






zxDslamAPSPortTable OBJECT-TYPE
    SYNTAX SEQUENCE OF ZxDslamAPSPortEntry
    MAX-ACCESS not-accessible
    STATUS current
    DESCRIPTION
    "The APS 1+1   port Information. "
    ::= { zxDslam 16 }
    
zxDslamAPSPortEntry OBJECT-TYPE
    SYNTAX ZxDslamAPSPortEntry
    MAX-ACCESS not-accessible
    STATUS current
    DESCRIPTION
    "An entry in the APS port table . "
    INDEX { APSPort }
    ::= { zxDslamAPSPortTable 1 }
    
ZxDslamAPSPortEntry ::= SEQUENCE {
    APSPortRowStatus                UCHAR,     
    APSPort                         UCHAR,
    APSLogicPort                    UShort,
    APSPortStatus                   UShort
    }                                     

APSPortRowStatus OBJECT-TYPE             
    SYNTAX  UCHAR                         
    MAX-ACCESS read-write                 
    STATUS current                        
    DESCRIPTION
    " "
    ::= { zxDslamAPSPortEntry 1 }   

APSPort OBJECT-TYPE             
    SYNTAX  UCHAR                         
    MAX-ACCESS read-write                 
    STATUS current                        
    DESCRIPTION
    " "
    ::= { zxDslamAPSPortEntry 2 }

APSLogicPort OBJECT-TYPE             
    SYNTAX  UCHAR                         
    MAX-ACCESS read-write                 
    STATUS current                        
    DESCRIPTION
    " "
    ::= { zxDslamAPSPortEntry 3 }
APSPortStatus OBJECT-TYPE             
    SYNTAX  UCHAR                         
    MAX-ACCESS read-write                 
    STATUS current                        
    DESCRIPTION
    " 0:working end,1:protect end "
    ::= { zxDslamAPSPortEntry 4 }
                                          




--The Route Group       
bgs10RouteMIB           OBJECT IDENTIFIER   ::= { zxbgs10mib 3}
    
-- Defintion of objects for route set table.
    
bgs10RouteTable OBJECT-TYPE
    SYNTAX      SEQUENCE OF BGS10RouteEntry
    MAX-ACCESS  not-accessible
    STATUS      current
    DESCRIPTION
        "A list of the route information."
    ::= { bgs10RouteMIB 1}
        
bgs10RouteEntry OBJECT-TYPE
    SYNTAX      BGS10RouteEntry
    MAX-ACCESS  not-accessible
    STATUS      current
    DESCRIPTION
        "An entry to the table."
    INDEX   { bgs10RouteAtmAddress }
    ::= { bgs10RouteTable 1}
        
BGS10RouteEntry ::=
    SEQUENCE {
        bgs10RouteRowStatus         INTEGER,
        bgs10RouteAtmAddressStatus  INTEGER,
        bgs10RouteOperateStatus     INTEGER,
        bgs10RouteNodeNum           UChar,
        bgs10RouteAtmAddress        OCTET STRING,
        bgs10RouteServiceType       INTEGER,
        bgs10RouteRouteSet          UShort,
        bgs10RouteModule            UChar,
        bgs10RouteLength            UChar,
        bgs10RouteServicePID        OCTET STRING(SIZE(4)),
        bgs10RouteDefaultAddrFlag   INTEGER,
        bgs10RouteAddressPlan       INTEGER,
        bgs10RouteAlternateRouteDirect UShort,
        bgs10RouteAlternateRouteTwo UShort,
        bgs10RouteAlternateRouteThree UShort,
        bgs10RouteCurRouteSet       UShort,
        bgs10RouteRouteDirect       UShort,
        bgs10RouteRouteTwo          UShort,
        bgs10RouteRouteThree        UShort
        }
    
bgs10RouteRowStatus OBJECT-TYPE
    SYNTAX      INTEGER
    MAX-ACCESS  read-create
    STATUS      current
    DESCRIPTION 
        "the conteptual row."
    ::= { bgs10RouteEntry 1}
        
bgs10RouteAtmAddressStatus      OBJECT-TYPE
    SYNTAX      INTEGER
    MAX-ACCESS  read-create
    STATUS      current
    DESCRIPTION
        "the status of the ATM address: 0--IISP configure address,1--ILMI."
    ::= { bgs10RouteEntry 2}
        
bgs10RouteOperateStatus     OBJECT-TYPE
    SYNTAX      INTEGER {   up(0),
                            down(1)
                        }
    MAX-ACCESS  read-create
    STATUS      current
    DESCRIPTION
        "the node operate status."
    ::= { bgs10RouteEntry 3}
    
bgs10RouteNodeNum       OBJECT-TYPE
    SYNTAX      UChar
    MAX-ACCESS  read-create
    STATUS      current
    DESCRIPTION
        "the Node Number."
    ::= { bgs10RouteEntry 4}
    
bgs10RouteAtmAddress        OBJECT-TYPE
    SYNTAX      OCTET STRING(SIZE(20))
    MAX-ACCESS  read-create
    STATUS      current
    DESCRIPTION
        "the ATM address."
    ::= { bgs10RouteEntry 5}
    
bgs10RouteServiceType       OBJECT-TYPE
    SYNTAX      INTEGER
    MAX-ACCESS  read-create
    STATUS      current
    DESCRIPTION
        "Route No.4."
    ::= { bgs10RouteEntry 6}    
        
bgs10RouteRouteSet      OBJECT-TYPE
    SYNTAX      UShort
    MAX-ACCESS  read-create
    STATUS      current
    DESCRIPTION
        "RouteSet."
    ::= { bgs10RouteEntry 7}

bgs10RouteModule        OBJECT-TYPE
    SYNTAX      UChar
    MAX-ACCESS  read-create
    STATUS      current
    DESCRIPTION
        "Module No.."
    ::= { bgs10RouteEntry 8}
    
bgs10RouteLength        OBJECT-TYPE
    SYNTAX      UChar
    MAX-ACCESS  read-create
    STATUS      current
    DESCRIPTION
        "route's length."
    ::= { bgs10RouteEntry 9}
    
bgs10RouteServicePID    OBJECT-TYPE
    SYNTAX      OCTET STRING(SIZE(4))
    MAX-ACCESS  read-create
    STATUS      current
    DESCRIPTION
        "Service's PID."
    ::= { bgs10RouteEntry 10}
    
bgs10RouteDefaultAddrFlag       OBJECT-TYPE
    SYNTAX      INTEGER{ default(0),
                         no-default(1)
                       }
    MAX-ACCESS  read-create
    STATUS      current
    DESCRIPTION
        "Address's default flag."
    ::= { bgs10RouteEntry 11}
    
bgs10RouteAddressPlan   OBJECT-TYPE
    SYNTAX      INTEGER{ unknown(0),
                         isdn(1),
                         nsap(2),
                         private(9),
                         reversed(15)
                       }
    MAX-ACCESS  read-create
    STATUS      current
    DESCRIPTION
        "Address's default flag."
    ::= { bgs10RouteEntry 12}
    
bgs10RouteAlternateRouteDirect      OBJECT-TYPE
    SYNTAX      UShort
    MAX-ACCESS  read-create
    STATUS      current
    DESCRIPTION
            "alternate_route_direct."
    ::= { bgs10RouteEntry 13}
    
bgs10RouteAlternateRouteTwo         OBJECT-TYPE
    SYNTAX      UShort
    MAX-ACCESS  read-create
    STATUS      current
    DESCRIPTION
            "alternate_route_two."
    ::= { bgs10RouteEntry 14}

bgs10RouteAlternateRouteThree       OBJECT-TYPE
    SYNTAX      UShort
    MAX-ACCESS  read-create
    STATUS      current
    DESCRIPTION
            "alternate_route_three."
    ::= { bgs10RouteEntry 15}
    
bgs10RouteCurRouteSet              OBJECT-TYPE
    SYNTAX      UShort
    MAX-ACCESS  read-create
    STATUS      current
    DESCRIPTION
            "CurRouteSet."
    ::= { bgs10RouteEntry 16}
    
bgs10RouteRouteDirect       OBJECT-TYPE
    SYNTAX      UShort
    MAX-ACCESS  read-create
    STATUS      current
    DESCRIPTION
            "route_direct."
    ::= { bgs10RouteEntry 17}
    
bgs10RouteRouteTwo      OBJECT-TYPE
    SYNTAX      UShort
    MAX-ACCESS  read-create
    STATUS      current
    DESCRIPTION
            "route_two."
    ::= { bgs10RouteEntry 18}
    
bgs10RouteRouteThree        OBJECT-TYPE
    SYNTAX      UShort
    MAX-ACCESS  read-create
    STATUS      current
    DESCRIPTION
            "route_three."
    ::= { bgs10RouteEntry 19}   
        
        
--the PVC table 
bgs10Pvc                OBJECT IDENTIFIER   ::= { zxbgs10mib 10}
        
bgs10PvcTable   OBJECT-TYPE
    SYNTAX      SEQUENCE OF BGS10PvcEntry
    MAX-ACCESS  not-accessible
    STATUS      current
    DESCRIPTION
        "A list of PVC configure information entries."
    ::= { bgs10Pvc 1}
    
bgs10PvcEntry   OBJECT-TYPE
    SYNTAX      BGS10PvcEntry
    MAX-ACCESS  not-accessible
    STATUS      current
    DESCRIPTION
        "An entry in the table."
    INDEX { bgs10PvcLModule,
            bgs10PvcLPort,
            bgs10PvcLVpi,
            bgs10PvcLVci,
            bgs10PvcHModule,
            bgs10PvcHPort,
            bgs10PvcHVpi,
            bgs10PvcHVci            
        }
    ::= { bgs10PvcTable 1}
    
BGS10PvcEntry ::=
    SEQUENCE {
        bgs10PvcRowStatus               RowStatus,
        bgs10PvcLVpi                    INTEGER,
        bgs10PvcL2HtrafficDescrType     INTEGER,
        bgs10PvcLModule                 INTEGER,
        bgs10PvcHModule                 INTEGER,
        bgs10PvcHPort                   INTEGER,
        bgs10PvcLPort                   INTEGER,
        bgs10PvcHVpi                    INTEGER,
        bgs10PvcL2HtrafficQosClass      INTEGER,
        bgs10PvcH2LtrafficDescrType     INTEGER,
        bgs10PvcH2LtrafficQosClass      INTEGER,
        bgs10PvcPvcAdminStatus          INTEGER,
        bgs10PvcConnectStruct           INTEGER,
        bgs10PvcServiceCategory         INTEGER,
        bgs10PvcPvcOperStatus           INTEGER,
        bgs10PvcLCPType                 INTEGER,
        bgs10PvcHCPType                 INTEGER,
        bgs10PvcConnectType             INTEGER,
        bgs10PvcUse                     INTEGER,
        bgs10PvcHVci                    INTEGER,
        bgs10PvcLVci                    INTEGER,
        bgs10PvcLAtmAddress             AtmAddr,
        bgs10PvcL2HtrafficDescrParam1   Unsigned32,
        bgs10PvcL2HtrafficDescrParam2   Unsigned32,
        bgs10PvcL2HtrafficDescrParam3   Unsigned32,
        bgs10PvcL2HtrafficDescrParam4   Unsigned32,
        bgs10PvcL2HtrafficDescrParam5   Unsigned32,
        bgs10PvcHAtmAddress             AtmAddr,
        bgs10PvcH2LtrafficDescrParam1   Unsigned32,
        bgs10PvcH2LtrafficDescrParam2   Unsigned32,
        bgs10PvcH2LtrafficDescrParam3   Unsigned32,
        bgs10PvcH2LtrafficDescrParam4   Unsigned32,
        bgs10PvcH2LtrafficDescrParam5   Unsigned32,
        bgs10PvcPMPconnectTag           UShort,
        bgs10PvcCrossconnectIdentifier  UShort,
        bgs10PvcCatchRM                 BITS,
        bgs10PvcAllowEFC                BITS,
        bgs10PvcEPDFlag                 BITS,
        bgs10PvcFeeGleanFlag            BITS,
        bgs10PvcPmodule                 Unsigned32,
        bgs10PvcPVCType                 Unsigned32,
        bgs10PvcManualControl           Unsigned32,
        bgs10PvcPport                   Unsigned32,
        bgs10PvcPSwitchType             Unsigned32,
        bgs10PvcPvcPOperStatus          Unsigned32,
        bgs10PvcPVPI                    Unsigned32,
        bgs10PvcOperatingMode           Unsigned32,
        bgs10PvcPCPType                 Unsigned32,
        bgs10PvcPVCI                    UShort,
        bgs10PvcPAtmAddress             AtmAddr,
        bgs10PvcGroupid                 UShort,
        bgs10PvcAlarmStatus             UShort,
        bgs10PvcPolicing                UCHAR,
        bgs10PvcPacketType              UCHAR,
        bgs10PvcPCSInd                  UCHAR,
        bgs10PvcSpecialIndex            UShort,
        bgs10PvcReNeindex               UCHAR,
        bgs10PvcReMoindex               UCHAR,
        bgs10PvcRePoindex               UCHAR,
        bgs10PvcH2LServiceCategory          UCHAR,
        bgs10PvcPVCName                 OCTET STRING(SIZE(20)),
        bgs10PvcLShapingFlag             UCHAR,
        bgs10PvcHShapingFlag             UCHAR
    }
    
bgs10PvcRowStatus   OBJECT-TYPE
    SYNTAX      RowStatus
    MAX-ACCESS  read-create
    STATUS      current
    DESCRIPTION
        "."
    ::= { bgs10PvcEntry 1}
    
bgs10PvcLVpi    OBJECT-TYPE
    SYNTAX      INTEGER
    MAX-ACCESS  read-create
    STATUS      current
    DESCRIPTION
        "VPI connection's VPI."
    ::= { bgs10PvcEntry 2}
    
bgs10PvcL2HtrafficDescrType OBJECT-TYPE
    SYNTAX      INTEGER
    MAX-ACCESS  read-create
    STATUS      current
    DESCRIPTION
        "."
    ::= { bgs10PvcEntry 3}
    
bgs10PvcLModule     OBJECT-TYPE
    SYNTAX      INTEGER
    MAX-ACCESS  read-create
    STATUS      current
    DESCRIPTION
        "."
    ::= { bgs10PvcEntry 4}
    
bgs10PvcHModule OBJECT-TYPE
    SYNTAX      INTEGER
    MAX-ACCESS  read-create
    STATUS      current
    DESCRIPTION
        "."
    ::= { bgs10PvcEntry 5}
    
bgs10PvcHPort   OBJECT-TYPE
    SYNTAX      INTEGER
    MAX-ACCESS  read-create
    STATUS      current
    DESCRIPTION
        "."
    ::= { bgs10PvcEntry 6}
    
bgs10PvcLPort   OBJECT-TYPE
    SYNTAX      INTEGER
    MAX-ACCESS  read-create
    STATUS      current
    DESCRIPTION
        "."
    ::= { bgs10PvcEntry 7}
    
bgs10PvcHVpi    OBJECT-TYPE
    SYNTAX      INTEGER
    MAX-ACCESS  read-create
    STATUS      current
    DESCRIPTION
        "."
    ::= { bgs10PvcEntry 8}
    
bgs10PvcL2HtrafficQosClass  OBJECT-TYPE
    SYNTAX      INTEGER
    MAX-ACCESS  read-create
    STATUS      current
    DESCRIPTION
        "."
    ::= { bgs10PvcEntry 9}
    
bgs10PvcH2LtrafficDescrType OBJECT-TYPE
    SYNTAX      INTEGER
    MAX-ACCESS  read-create
    STATUS      current
    DESCRIPTION
        "."
    ::= { bgs10PvcEntry 10}
    
bgs10PvcH2LtrafficQosClass  OBJECT-TYPE
    SYNTAX      INTEGER
    MAX-ACCESS  read-create
    STATUS      current
    DESCRIPTION
        "."
    ::= { bgs10PvcEntry 11}
    
bgs10PvcPvcAdminStatus  OBJECT-TYPE
    SYNTAX      INTEGER
    MAX-ACCESS  read-create
    STATUS      current
    DESCRIPTION
        "."
    ::= { bgs10PvcEntry 12}
    
bgs10PvcConnectStruct   OBJECT-TYPE
    SYNTAX      INTEGER {   singp2p(0),
                            bip2p(1),
                            singp2mp(2),
                            singmp2p(3),
                            mp2mp(4),
                            bip2mp(5)}
    MAX-ACCESS  read-create
    STATUS      current
    DESCRIPTION
        "Pvc Connection type:
        --singal directional point to point(0)
        --bi-directional point to point (1)
        --singal directional point to multi-points (2)
        --singal directional multi-points to point (3)
        --multi-points to multi-points (4)
        --bi-dirctional point to multi-points (5)."
    ::= { bgs10PvcEntry 13}
    
bgs10PvcServiceCategory OBJECT-TYPE
    SYNTAX      INTEGER
    MAX-ACCESS  read-create
    STATUS      current
    DESCRIPTION
        "."
    ::= { bgs10PvcEntry 14}
    
bgs10PvcPvcOperStatus   OBJECT-TYPE
    SYNTAX      INTEGER
    MAX-ACCESS  read-only
    STATUS      current
    DESCRIPTION
        "."
    ::= { bgs10PvcEntry 15}
    
bgs10PvcLCPType OBJECT-TYPE
    SYNTAX      INTEGER {   segEndPtNo(0),
                            segEndPtYes(1),
                            vpcConnectionEndPoint(2)
                        }
    MAX-ACCESS  read-create
    STATUS      current
    DESCRIPTION
        "."
    ::= { bgs10PvcEntry 16}
    
bgs10PvcHCPType OBJECT-TYPE
    SYNTAX      INTEGER {   segEndPtNo(0),
                            segEndPtYes(1),
                            vpcConnectionEndPoint(2)
                        }
    MAX-ACCESS  read-create
    STATUS      current
    DESCRIPTION
        "."
    ::= { bgs10PvcEntry 17}
    
bgs10PvcConnectType OBJECT-TYPE
    SYNTAX      INTEGER
    MAX-ACCESS  read-create
    STATUS      current
    DESCRIPTION
        "."
    ::= { bgs10PvcEntry 18}
    
bgs10PvcUse OBJECT-TYPE
    SYNTAX      INTEGER {   general(0),
                            configureDirectVCC(1),
                            controlDirectVCC(2),
                            controlDistributeVCC(3),
                            dataDirectVCC(4),
                            multicastSendVCC(5),
                            mulitcastForwardVCC(6)}
    MAX-ACCESS  read-create
    STATUS      current
    DESCRIPTION
        "."
    ::= { bgs10PvcEntry 19}

bgs10PvcHVci    OBJECT-TYPE
    SYNTAX      INTEGER
    MAX-ACCESS  read-create
    STATUS      current
    DESCRIPTION
        "."
    ::= { bgs10PvcEntry 20}
    
bgs10PvcLVci    OBJECT-TYPE
    SYNTAX      INTEGER
    MAX-ACCESS  read-create
    STATUS      current
    DESCRIPTION
        "."
    ::= { bgs10PvcEntry 21}     
    
bgs10PvcLAtmAddress OBJECT-TYPE
    SYNTAX      AtmAddr
    MAX-ACCESS  read-create
    STATUS      current
    DESCRIPTION
        "."
    ::= { bgs10PvcEntry 22}
                
bgs10PvcL2HtrafficDescrParam1   OBJECT-TYPE
    SYNTAX      Unsigned32
    MAX-ACCESS  read-create
    STATUS      current
    DESCRIPTION
        "."
    ::= { bgs10PvcEntry 23}
    
bgs10PvcL2HtrafficDescrParam2   OBJECT-TYPE
    SYNTAX      Unsigned32
    MAX-ACCESS  read-create
    STATUS      current
    DESCRIPTION
        "."
    ::= { bgs10PvcEntry 24}
    
bgs10PvcL2HtrafficDescrParam3   OBJECT-TYPE
    SYNTAX      Unsigned32
    MAX-ACCESS  read-create
    STATUS      current
    DESCRIPTION
        "."
    ::= { bgs10PvcEntry 25}
    
bgs10PvcL2HtrafficDescrParam4   OBJECT-TYPE
    SYNTAX      Unsigned32
    MAX-ACCESS  read-create
    STATUS      current
    DESCRIPTION
        "."
    ::= { bgs10PvcEntry 26}
    
bgs10PvcL2HtrafficDescrParam5   OBJECT-TYPE
    SYNTAX      Unsigned32
    MAX-ACCESS  read-create
    STATUS      current
    DESCRIPTION
        "."
    ::= { bgs10PvcEntry 27}
    
bgs10PvcHAtmAddress OBJECT-TYPE
    SYNTAX      AtmAddr
    MAX-ACCESS  read-create
    STATUS      current
    DESCRIPTION
        "."
    ::= { bgs10PvcEntry 28}
    
bgs10PvcH2LtrafficDescrParam1   OBJECT-TYPE
    SYNTAX      Unsigned32
    MAX-ACCESS  read-create
    STATUS      current
    DESCRIPTION
        "."
    ::= { bgs10PvcEntry 29}
    
bgs10PvcH2LtrafficDescrParam2   OBJECT-TYPE
    SYNTAX      Unsigned32
    MAX-ACCESS  read-create
    STATUS      current
    DESCRIPTION
        "."
    ::= { bgs10PvcEntry 30}
    
bgs10PvcH2LtrafficDescrParam3   OBJECT-TYPE
    SYNTAX      Unsigned32
    MAX-ACCESS  read-create
    STATUS      current
    DESCRIPTION
        "."
    ::= { bgs10PvcEntry 31}
    
bgs10PvcH2LtrafficDescrParam4   OBJECT-TYPE
    SYNTAX      Unsigned32
    MAX-ACCESS  read-create
    STATUS      current
    DESCRIPTION
        "."
    ::= { bgs10PvcEntry 32}
    
bgs10PvcH2LtrafficDescrParam5   OBJECT-TYPE
    SYNTAX      Unsigned32
    MAX-ACCESS  read-create
    STATUS      current
    DESCRIPTION
        "."
    ::= { bgs10PvcEntry 33} 
    
bgs10PvcPMPconnectTag   OBJECT-TYPE
    SYNTAX      UShort
    MAX-ACCESS  read-only
    STATUS      current
    DESCRIPTION
        "the PMP connection tag."
    ::= { bgs10PvcEntry 34 }
    
bgs10PvcCrossconnectIdentifier  OBJECT-TYPE
    SYNTAX      UShort
    MAX-ACCESS  read-only
    STATUS      current
    DESCRIPTION
        "the cross connection identifier."
    ::= { bgs10PvcEntry 35 } 
    
bgs10PvcCatchRM OBJECT-TYPE
    SYNTAX      BITS { not-catch(0),
                       catch(1)
                     }
    MAX-ACCESS  read-only
    STATUS      current
    DESCRIPTION
        "."
    ::= { bgs10PvcEntry 36 } 
    
bgs10PvcAllowEFC    OBJECT-TYPE
    SYNTAX      BITS { not-allow(0),
                       allow(1)
                     }
    MAX-ACCESS  read-only
    STATUS      current
    DESCRIPTION
        "."
    ::= { bgs10PvcEntry 37 } 
    
bgs10PvcEPDFlag     OBJECT-TYPE
    SYNTAX      BITS { not-set(0),
                       set(1)
                     }
    MAX-ACCESS  read-only
    STATUS      current
    DESCRIPTION
        "."
    ::= { bgs10PvcEntry 38 } 
    
bgs10PvcFeeGleanFlag    OBJECT-TYPE
    SYNTAX      BITS { not-glean(0),
                       glean(1)
                     }
    MAX-ACCESS  read-only
    STATUS      current
    DESCRIPTION
        "."
    ::= { bgs10PvcEntry 39 } 

bgs10PvcPmodule OBJECT-TYPE
    SYNTAX      Unsigned32
    MAX-ACCESS  read-only
    STATUS      current
    DESCRIPTION
        "."
    ::= { bgs10PvcEntry 40 }

bgs10PvcPVCType OBJECT-TYPE
    SYNTAX      Unsigned32
    MAX-ACCESS  read-only
    STATUS      current
    DESCRIPTION
        "."
    ::= { bgs10PvcEntry 41 }

bgs10PvcManualControl   OBJECT-TYPE
    SYNTAX      Unsigned32
    MAX-ACCESS  read-only
    STATUS      current
    DESCRIPTION
        "."
    ::= { bgs10PvcEntry 42 }

bgs10PvcPport   OBJECT-TYPE
    SYNTAX      Unsigned32
    MAX-ACCESS  read-only
    STATUS      current
    DESCRIPTION
        "."
    ::= { bgs10PvcEntry 43 }

bgs10PvcPSwitchType OBJECT-TYPE
    SYNTAX      Unsigned32
    MAX-ACCESS  read-only
    STATUS      current
    DESCRIPTION
        "."
    ::= { bgs10PvcEntry 44 }

bgs10PvcPvcPOperStatus  OBJECT-TYPE
    SYNTAX      Unsigned32
    MAX-ACCESS  read-only
    STATUS      current
    DESCRIPTION
        "."
    ::= { bgs10PvcEntry 45 }

bgs10PvcPVPI    OBJECT-TYPE
    SYNTAX      Unsigned32
    MAX-ACCESS  read-only
    STATUS      current
    DESCRIPTION
        "."
    ::= { bgs10PvcEntry 46 }

bgs10PvcOperatingMode   OBJECT-TYPE
    SYNTAX      Unsigned32
    MAX-ACCESS  read-only
    STATUS      current
    DESCRIPTION
        "."
    ::= { bgs10PvcEntry 47 }

bgs10PvcPCPType OBJECT-TYPE
    SYNTAX      Unsigned32
    MAX-ACCESS  read-only
    STATUS      current
    DESCRIPTION
        "."
    ::= { bgs10PvcEntry 48 }

bgs10PvcPVCI    OBJECT-TYPE
    SYNTAX      UShort
    MAX-ACCESS  read-only
    STATUS      current
    DESCRIPTION
        "."
    ::= { bgs10PvcEntry 49 }

bgs10PvcPAtmAddress OBJECT-TYPE
    SYNTAX      AtmAddr
    MAX-ACCESS  read-only
    STATUS      current
    DESCRIPTION
        "."
    ::= { bgs10PvcEntry 50 }

bgs10PvcGroupid OBJECT-TYPE
    SYNTAX      UShort
    MAX-ACCESS  read-only
    STATUS      current
    DESCRIPTION
        "."
    ::= { bgs10PvcEntry 51 }
    
bgs10PvcAlarmStatus OBJECT-TYPE
    SYNTAX      UShort
    MAX-ACCESS  read-only
    STATUS      current
    DESCRIPTION
        "."
    ::= { bgs10PvcEntry 52 }
    
bgs10PvcPolicing    OBJECT-TYPE 
    SYNTAX      UCHAR
    MAX-ACCESS  read-only
    STATUS      current
    DESCRIPTION
        "."
    ::= { bgs10PvcEntry 53 }

bgs10PvcPacketType  OBJECT-TYPE 
    SYNTAX      UCHAR
    MAX-ACCESS  read-only
    STATUS      current
    DESCRIPTION
        "."
    ::= { bgs10PvcEntry 54 }

bgs10PvcPCSInd  OBJECT-TYPE 
    SYNTAX      UCHAR
    MAX-ACCESS  read-only
    STATUS      current
    DESCRIPTION
        "."
    ::= { bgs10PvcEntry 55 }
    
bgs10PvcSpecialIndex  OBJECT-TYPE   
    SYNTAX      UShort
    MAX-ACCESS  read-only
    STATUS      current
    DESCRIPTION
        "."
    ::= { bgs10PvcEntry 56 }

bgs10PvcReNeindex  OBJECT-TYPE  
    SYNTAX      UCHAR
    MAX-ACCESS  read-only
    STATUS      current
    DESCRIPTION
        "."
    ::= { bgs10PvcEntry 57 }

bgs10PvcReMoindex  OBJECT-TYPE  
    SYNTAX      UCHAR
    MAX-ACCESS  read-only
    STATUS      current
    DESCRIPTION
        "."
    ::= { bgs10PvcEntry 58 }

bgs10PvcRePoindex  OBJECT-TYPE  
    SYNTAX      UCHAR
    MAX-ACCESS  read-only
    STATUS      current
    DESCRIPTION
        "."
    ::= { bgs10PvcEntry 59 }
bgs10PvcH2LServiceCategory  OBJECT-TYPE 
    SYNTAX      UCHAR
    MAX-ACCESS  read-only
    STATUS      current
    DESCRIPTION
        "."
    ::= { bgs10PvcEntry 60 }
bgs10PvcPVCName  OBJECT-TYPE    
    SYNTAX      OCTET STRING(SIZE(20))
    MAX-ACCESS  read-only
    STATUS      current
    DESCRIPTION
        "."
    ::= { bgs10PvcEntry 61 }
bgs10PvcLShapingFlag  OBJECT-TYPE    
    SYNTAX      UCHAR
    MAX-ACCESS  read-only
    STATUS      current
    DESCRIPTION
        "0: off   1: on  "
    ::= { bgs10PvcEntry 62 }

bgs10PvcHShapingFlag  OBJECT-TYPE    
    SYNTAX      UCHAR
    MAX-ACCESS  read-only
    STATUS      current
    DESCRIPTION
        "0: off   1: on  "
    ::= { bgs10PvcEntry 63 }



--the switcher table for perfermance management
bgs10PmLoopBackTable    OBJECT-TYPE
        SYNTAX          SEQUENCE OF BGS10PmLoopBackEntry
        MAX-ACCESS      not-accessible
        STATUS          current
        DESCRIPTION
                "the table for loop-back action of the perfermance management."
        ::= { bgs10PmMib 1}
        
bgs10PmLoopBackEntry    OBJECT-TYPE
        SYNTAX          BGS10PmLoopBackEntry
        MAX-ACCESS      not-accessible
        STATUS          current
        DESCRIPTION
                "THE ENTRY TO THE PM loop-back test."
        INDEX { bgs10PmLoopBackModule,
                        bgs10PmLoopBackPerfPort,
                        bgs10PmLoopBackVPI,
                        bgs10PmLoopBackVCI
                        }
        ::= { bgs10PmLoopBackTable 1 }
        
BGS10PmLoopBackEntry    ::=
        SEQUENCE {      
                bgs10PmLoopBackRowStatus                RowStatus,
                bgs10PmLoopBackTestType                 UChar,
                bgs10PmLoopBackModule                   UChar,
                bgs10PmLoopBackPerfPort                 UShort,
                bgs10PmLoopBackTestIndex                UShort,
                bgs10PmLoopBackVPI                              UShort,
                bgs10PmLoopBackVCI                              UShort,
                bgs10PmLoopBackTestNumber               UShort,
                bgs10PmLoopBackID                               OCTET STRING,
                bgs10PmLoopBackLoopBackActionFlag
                                                                                INTEGER,
                bgs10PmLoopBackPMActionFlag             INTEGER,
                bgs10PmLoopBackTestResult               UCHAR
        }
        
bgs10PmLoopBackRowStatus        OBJECT-TYPE
        SYNTAX          RowStatus
        MAX-ACCESS      read-create
        STATUS          current
        DESCRIPTION
                "the row status of the switcher table."
        ::= { bgs10PmLoopBackEntry 1 }
        
bgs10PmLoopBackTestType         OBJECT-TYPE
        SYNTAX          UChar
        MAX-ACCESS      read-create
        STATUS          current
        DESCRIPTION
                "the test type includes :F4 end-to-end/segment-to-segment,F5 end-to-end/
        segment-to-segment."
        ::= { bgs10PmLoopBackEntry 2 }
        
bgs10PmLoopBackModule   OBJECT-TYPE
        SYNTAX          UChar
        MAX-ACCESS      read-create
        STATUS          current
        DESCRIPTION
                "the tested Mpdule."
        ::= { bgs10PmLoopBackEntry 3 }
        
bgs10PmLoopBackPerfPort OBJECT-TYPE
        SYNTAX          UShort
        MAX-ACCESS      read-create
        STATUS          current
        DESCRIPTION
                "the tested port."
        ::= { bgs10PmLoopBackEntry 4 }
        
bgs10PmLoopBackTestIndex        OBJECT-TYPE
        SYNTAX          UShort
        MAX-ACCESS      read-create
        STATUS          current
        DESCRIPTION
                "the test index."
        ::= { bgs10PmLoopBackEntry 5 }
        
bgs10PmLoopBackVPI              OBJECT-TYPE
        SYNTAX          UShort
        MAX-ACCESS      read-create
        STATUS          current
        DESCRIPTION
                "the test VPI."
        ::= { bgs10PmLoopBackEntry 6 }

bgs10PmLoopBackVCI              OBJECT-TYPE
        SYNTAX          UShort
        MAX-ACCESS      read-create
        STATUS          current
        DESCRIPTION
                "the test VCI."
        ::= { bgs10PmLoopBackEntry 7 }
        
bgs10PmLoopBackTestNumber OBJECT-TYPE
        SYNTAX          UShort
        MAX-ACCESS      read-create
        STATUS          current
        DESCRIPTION
                "the numbers of the loopback test."
        ::= { bgs10PmLoopBackEntry 8 }
        
bgs10PmLoopBackID       OBJECT-TYPE
        SYNTAX          OCTET STRING(SIZE(13))
        MAX-ACCESS      read-create
        STATUS          current
        DESCRIPTION
                "the loop back ID."
        ::= { bgs10PmLoopBackEntry 9 }
        
bgs10PmLoopBackLoopBackActionFlag       OBJECT-TYPE
        SYNTAX          INTEGER { down(0),
                                                up(1),
                                                close(2)
                                                }
        MAX-ACCESS      read-create
        STATUS          current
        DESCRIPTION
                "the loop-bakc action flag."
        ::= { bgs10PmLoopBackEntry 10 }
        
bgs10PmLoopBackPMActionFlag             OBJECT-TYPE
        SYNTAX          INTEGER { down(0),
                                                up(1),
                                                close(2)
                                                }
        MAX-ACCESS      read-create
        STATUS          current
        DESCRIPTION
                " the perfermance management action flag."
         ::= { bgs10PmLoopBackEntry 11 }
         
bgs10PmLoopBackTestResult               OBJECT-TYPE
        SYNTAX          UCHAR   
        MAX-ACCESS      read-create
        STATUS          current
        DESCRIPTION
                " the OAM Test result."
         ::= { bgs10PmLoopBackEntry 12 }
         
--The ZXBGS10 interface Configuration extensions.

bgs10IfConfigureTable   OBJECT-TYPE
        SYNTAX          SEQUENCE OF BGS10IfConfigureEntry
        MAX-ACCESS      not-accessible
        STATUS          current
        DESCRIPTION
                "The ZXBGS10 ATM interface configuration table extensions.This table 
                augments the atm interface configuration table in RFC 1695."
        ::= { zxbgs10mib 20 }
        
bgs10IfConfigureEntry   OBJECT-TYPE
        SYNTAX          BGS10IfConfigureEntry
        MAX-ACCESS      not-accessible
        STATUS          current
        DESCRIPTION     
                "Additional columns for the ATM interface configuration table entry."
        AUGMENTS        { atmInterfaceConfEntry }
        ::= { bgs10IfConfigureTable 1}
        
BGS10IfConfigureEntry   ::=
        SEQUENCE {
                bgs10IfConfigurePort            UChar,
                bgs10IfConfigureAdminState      UChar,
                bgs10IfConfigureOperState       UChar,
                bgs10IfConfigureSigVpi          INTEGER,
                bgs10IfConfigInterfaceSigVci    UShort,
                bgs10IfConfigInterfaceType      UShort,
                bgs10IfConfigilmiIMEType        UShort
        }
        
bgs10IfConfigurePort    OBJECT-TYPE
        SYNTAX          UChar
        MAX-ACCESS      read-write
        STATUS          current
        DESCRIPTION
                "The Port Number."
        ::= { bgs10IfConfigureEntry     1 }

bgs10IfConfigureAdminState      OBJECT-TYPE
        SYNTAX          UChar
        MAX-ACCESS      read-write
        STATUS          current
        DESCRIPTION
                "A control object to indicate the administratively desired state of the 
        interface configuration."
        ::= { bgs10IfConfigureEntry     2 }

bgs10IfConfigureOperState       OBJECT-TYPE
        SYNTAX          UChar
        MAX-ACCESS      read-only
        STATUS          current
        DESCRIPTION
                "A status object to indicate the operational state of the interface 
        configuration."
        ::= { bgs10IfConfigureEntry     3 }
        
bgs10IfConfigureSigVpi          OBJECT-TYPE
        SYNTAX          INTEGER
        MAX-ACCESS      read-only
        STATUS          current
        DESCRIPTION
                ""
        ::= { bgs10IfConfigureEntry     4 }
bgs10IfConfigInterfaceSigVci            OBJECT-TYPE
        SYNTAX          UShort
        MAX-ACCESS      read-only
        STATUS          current
        DESCRIPTION
                ""
        ::= { bgs10IfConfigureEntry     5 }
bgs10IfConfigInterfaceType              OBJECT-TYPE
        SYNTAX          UShort
        MAX-ACCESS      read-only
        STATUS          current
        DESCRIPTION
                ""
        ::= { bgs10IfConfigureEntry     6 }
bgs10IfConfigilmiIMEType                OBJECT-TYPE
        SYNTAX          UShort
        MAX-ACCESS      read-only
        STATUS          current
        DESCRIPTION
                ""
        ::= { bgs10IfConfigureEntry     7 }




--The Plug-in unit table
bgs10PlugInUnit     OBJECT IDENTIFIER   ::= { zxbgs10mib 32}
    
bgs10PlugInUnitTable    OBJECT-TYPE
    SYNTAX      SEQUENCE OF Bgs10PlugInUnitEntry
    MAX-ACCESS  not-accessible
    STATUS      current
    DESCRIPTION
        "the plug-in unittable."
    ::= { bgs10PlugInUnit 1 }
    
bgs10PlugInUnitEntry    OBJECT-TYPE
    SYNTAX      Bgs10PlugInUnitEntry
    MAX-ACCESS  not-accessible
    STATUS      current
    DESCRIPTION
        "the entry to the plug-in unit table."
    INDEX { entPhysicalIndex  }
    ::= { bgs10PlugInUnitTable 1 }
    
Bgs10PlugInUnitEntry    ::=
    SEQUENCE {
        bgs10PlugInUnitRowStatus        RowStatus,
        bgs10PlugInUnitMasterStatus     INTEGER,
        bgs10PlugInUnitEntPhysicalContainedIn
                                        INTEGER,
        bgs10PlugInUnitEthiVlanSwith        INTEGER,
        bgs10PlugInUnitCardType         INTEGER,
        bgs10PlugInUnitModule           INTEGER,
        bgs10PlugInUnitCardPosition     INTEGER,
        bgs10PlugInUnitPhysicalClass        INTEGER,
        bgs10PlugInUnitserbitmap        Unsigned32
    }
    
bgs10PlugInUnitRowStatus    OBJECT-TYPE
    SYNTAX      RowStatus
    MAX-ACCESS  read-create
    STATUS      current
    DESCRIPTION
        "the conceptual row status."
    ::= { bgs10PlugInUnitEntry 1 }
    
bgs10PlugInUnitMasterStatus OBJECT-TYPE
    SYNTAX      INTEGER { master(0),
                            slave(1)
                        }
    MAX-ACCESS  read-create
    STATUS      current
    DESCRIPTION
        "the Unit work status."
    ::= { bgs10PlugInUnitEntry 2 }
    
bgs10PlugInUnitEntPhysicalContainedIn   OBJECT-TYPE
    SYNTAX      INTEGER
    MAX-ACCESS  read-create
    STATUS      current
    DESCRIPTION
        "the physical contained position."
    ::= { bgs10PlugInUnitEntry 3 }
    
bgs10PlugInUnitEthiVlanSwith    OBJECT-TYPE
    SYNTAX      INTEGER
    MAX-ACCESS  read-create
    STATUS      current
    DESCRIPTION
        "the neighbor service card type."
    ::= { bgs10PlugInUnitEntry 4 }
    
bgs10PlugInUnitCardType     OBJECT-TYPE
    SYNTAX      INTEGER
    {
     UNKNOWN(0),  
     CORE   (1),   
     WANA   (3),   
     POWER  (4),  
     ATUCC  (5),  
     ATUCB  (6),  
     OTHER  (7), 
     COREA  (8), 
     COREC  (9),  
     WANA1  (10), 
     WANAD  (11), 
     WANE   (12),  
     LAN    (13),   
     ATUCD  (14), 
     ATUCE  (15), 
     ATUCF  (16), 
     ATUCH  (18), 
     ATUCI  (19), 
     IMAA   (20),  
     COREA2 (21),
     COREB2 (22),
     COREC2 (23),
     COREA3 (24),
     COREB3 (25),
     COREC3 (26),
     IMAB   (27),  
     LANAA  (28), 
     LANAB  (29), 
     LANAC  (30), 
     LANAD  (31), 
     LANBA  (32), 
     LANBB  (33), 
     LANCA  (34), 
     LANCB  (35), 
     LANCC  (36), 
     LANCD  (37), 
     LANDA  (38), 
     LANDB  (39)     
     }
    MAX-ACCESS  read-create
    STATUS      current
    DESCRIPTION
        "the card type."
    ::= { bgs10PlugInUnitEntry 5 }
        
bgs10PlugInUnitModule   OBJECT-TYPE
    SYNTAX      INTEGER
    MAX-ACCESS  read-create
    STATUS      current
    DESCRIPTION
        "the Module Number."
    ::= { bgs10PlugInUnitEntry 6 }
    
bgs10PlugInUnitCardPosition OBJECT-TYPE
    SYNTAX      INTEGER
    MAX-ACCESS  read-create
    STATUS      current
    DESCRIPTION
        " the card position."
    ::= { bgs10PlugInUnitEntry 7}

bgs10PlugInUnitPhysicalClass    OBJECT-TYPE
    SYNTAX      INTEGER
    MAX-ACCESS  read-create
    STATUS      current
    DESCRIPTION
        " the card phyical class."
    ::= { bgs10PlugInUnitEntry 8}
bgs10PlugInUnitserbitmap    OBJECT-TYPE
    SYNTAX      Unsigned32
    MAX-ACCESS  read-create
    STATUS      current
    DESCRIPTION
        " the card phyical class."
    ::= { bgs10PlugInUnitEntry 9}
    



--bgs10atmfM4PlugInUnitTable
bgs10atmfM4PlugInUnitTable      OBJECT-TYPE
        SYNTAX          SEQUENCE OF BGS10atmfM4PlugInUnitEntry
        MAX-ACCESS      not-accessible
        STATUS          current
        DESCRIPTION
        "."
        ::= { zxbgs10mib 110 }

bgs10atmfM4PlugInUnitEntry      OBJECT-TYPE
        SYNTAX          BGS10atmfM4PlugInUnitEntry
        MAX-ACCESS      not-accessible
        STATUS          current
        DESCRIPTION
                "."
    INDEX { entPhysicalIndex  }
        ::= { bgs10atmfM4PlugInUnitTable 1 }

BGS10atmfM4PlugInUnitEntry ::=
        SEQUENCE { 
                bgs10PatmfM4PlugInzxDslamCardPortNum            UChar,
                bgs10PatmfM4PlugInzxDslamCardDescr              OCTET STRING(SIZE(32)),
                bgs10PatmfM4PlugInverNum                        Unsigned32,
                bgs10PatmfM4PlugInhardver                       OCTET STRING(SIZE(17)),
                bgs10PatmfM4PlugInsoftver                       OCTET STRING(SIZE(17)),
                bgs10PatmfM4PlugInbuildtime                     OCTET STRING(SIZE(17)),
                bgs10PatmfM4PlugInbackupsoftver                 OCTET STRING(SIZE(17)),
                bgs10PatmfM4PlugInbackupbuildtime               OCTET STRING(SIZE(17)),
                bgs10PatmfM4PlugInzxDCardChipsOperStatus        UChar,
                bgs10PatmfM4PlugInzxDCardType                   UChar,  
                bgs10PatmfM4PlugInzxDCardOperStatus             UChar,
                bgs10PatmfM4PlugInfirewarever                   OCTET STRING(SIZE(16)),
                bgs10PatmfM4PlugInCardReleasePVC                UChar,
                bgs10PatmfM4PlugInCardEnablePort                UChar,
                bgs10PatmfM4PlugInCardSwitchVersion             UChar,
                bgs10PatmfM4PlugInCardLogicPortNum              UChar
                
        }  
        
bgs10PatmfM4PlugInzxDslamCardPortNum    OBJECT-TYPE
        SYNTAX          UChar
        MAX-ACCESS      read-create
        STATUS          current
        DESCRIPTION
                "The remote port type."
        ::= {  bgs10atmfM4PlugInUnitEntry 2 }
bgs10PatmfM4PlugInzxDslamCardDescr      OBJECT-TYPE
        SYNTAX          OCTET STRING(SIZE(32))
        MAX-ACCESS      read-create
        STATUS          current
        DESCRIPTION
                "The remote port type."
        ::= {  bgs10atmfM4PlugInUnitEntry 3 }
bgs10PatmfM4PlugInverNum        OBJECT-TYPE
        SYNTAX          Unsigned32
        MAX-ACCESS      read-create
        STATUS          current
        DESCRIPTION
                "The remote port type."
        ::= {  bgs10atmfM4PlugInUnitEntry 4 }
bgs10PatmfM4PlugInhardver       OBJECT-TYPE
        SYNTAX          OCTET STRING(SIZE(17))
        MAX-ACCESS      read-create
        STATUS          current
        DESCRIPTION
                "The remote port type."
        ::= {  bgs10atmfM4PlugInUnitEntry 5 }
bgs10PatmfM4PlugInsoftver       OBJECT-TYPE
        SYNTAX          OCTET STRING(SIZE(17))
        MAX-ACCESS      read-create
        STATUS          current
        DESCRIPTION
                "The remote port type."
        ::= {  bgs10atmfM4PlugInUnitEntry 6 }
bgs10PatmfM4PlugInbuildtime     OBJECT-TYPE
        SYNTAX          OCTET STRING(SIZE(17))
        MAX-ACCESS      read-create
        STATUS          current
        DESCRIPTION
                "The remote port type."
        ::= {  bgs10atmfM4PlugInUnitEntry 7 }
bgs10PatmfM4PlugInbackupsoftver         OBJECT-TYPE
        SYNTAX          OCTET STRING(SIZE(17))
        MAX-ACCESS      read-create
        STATUS          current
        DESCRIPTION
                "The remote port type."
        ::= {  bgs10atmfM4PlugInUnitEntry 8 }
bgs10PatmfM4PlugInbackupbuildtime       OBJECT-TYPE
        SYNTAX          OCTET STRING(SIZE(17))
        MAX-ACCESS      read-create
        STATUS          current
        DESCRIPTION
                "The remote port type."
        ::= {  bgs10atmfM4PlugInUnitEntry 9 }
bgs10PatmfM4PlugInzxDCardChipsOperStatus        OBJECT-TYPE
        SYNTAX          UChar
        MAX-ACCESS      read-create
        STATUS          current
        DESCRIPTION
                "The remote port type."
        ::= {  bgs10atmfM4PlugInUnitEntry 10 }
bgs10PatmfM4PlugInzxDCardType   OBJECT-TYPE
        SYNTAX          UChar
        MAX-ACCESS      read-create
        STATUS          current
        DESCRIPTION
                "The remote port type."
        ::= {  bgs10atmfM4PlugInUnitEntry 11 }
bgs10PatmfM4PlugInzxDCardOperStatus     OBJECT-TYPE
        SYNTAX          UChar
        MAX-ACCESS      read-create
        STATUS          current
        DESCRIPTION
                "The remote port type."
        ::= {  bgs10atmfM4PlugInUnitEntry 12 }  
bgs10PatmfM4PlugInfirewarever   OBJECT-TYPE
        SYNTAX          OCTET STRING(SIZE(16))
        MAX-ACCESS      read-create
        STATUS          current
        DESCRIPTION
                "The remote port type."
        ::= {  bgs10atmfM4PlugInUnitEntry 13 }  

bgs10PatmfM4PlugInCardReleasePVC    OBJECT-TYPE
    SYNTAX      UChar
    MAX-ACCESS  read-create
    STATUS      current
    DESCRIPTION
        "The remote port type."
    ::= {  bgs10atmfM4PlugInUnitEntry 14 }  

bgs10PatmfM4PlugInCardEnablePort    OBJECT-TYPE
    SYNTAX      UChar
    MAX-ACCESS  read-create
    STATUS      current
    DESCRIPTION
        "The remote port type."
    ::= {  bgs10atmfM4PlugInUnitEntry 15 }  

                                            
bgs10PatmfM4PlugInCardSwitchVersion     OBJECT-TYPE
    SYNTAX      UChar
    MAX-ACCESS  read-create
    STATUS      current
    DESCRIPTION
        "The remote port type."
    ::= {  bgs10atmfM4PlugInUnitEntry 16 }  


bgs10PatmfM4PlugInCardLogicPortNum  OBJECT-TYPE
    SYNTAX      UChar
    MAX-ACCESS  read-create
    STATUS      current
    DESCRIPTION
        "The remote port type."
    ::= {  bgs10atmfM4PlugInUnitEntry 17 }  



--dsx1ConfigTable
dsx1ConfigTable OBJECT-TYPE
        SYNTAX  SEQUENCE OF E1ConfEntry
        MAX-ACCESS      not-accessible
        STATUS  current
        DESCRIPTION
                "A table of T1/E1 switch port configuration information."
        ::= { zxbgs10mib 55 }

dsx1ConfigEntry OBJECT-TYPE
        SYNTAX  E1ConfEntry
        MAX-ACCESS      not-accessible
        STATUS  current
        DESCRIPTION
                "A table entry containing T1/E1 configuration information for each
                port. Not all RFC1406 configuration table variables are
                included, and some are modified."
        INDEX   { dsx1ConfModule, dsx1ConfPort }
        ::= { dsx1ConfigTable 1 }

E1ConfEntry ::=
        SEQUENCE {
                dsx1RowStatus                   RowStatus,
                dsx1ConfModule                  INTEGER,
                dsx1ConfPort                    INTEGER,
                dsx1ConfLineType                INTEGER,
                dsx1ConfLineCoding              INTEGER,
                dsx1ConfLoopbackConfig  INTEGER,
                dsx1ConfLineStatus              INTEGER,
        dsx1ConfSignalMode      INTEGER,
                dsx1ConfTxClockSource   INTEGER,
                dsx1ConfIdleCells               INTEGER,
                dsx1ConfRxScrambling    INTEGER,
                dsx1ConfTxScrambling    INTEGER,
                dsx1ConfChannelNumber   INTEGER,
                dsx1ConfChannelization  INTEGER
}

dsx1RowStatus OBJECT-TYPE
        SYNTAX  RowStatus
        MAX-ACCESS      read-write
        STATUS  current
        DESCRIPTION
                "."
        ::= { dsx1ConfigEntry 1 }

dsx1ConfModule OBJECT-TYPE
        SYNTAX  INTEGER
        MAX-ACCESS      read-write
        STATUS  current
        DESCRIPTION
                "The network module of this port."
        ::= { dsx1ConfigEntry 2 }

dsx1ConfPort OBJECT-TYPE
        SYNTAX  INTEGER
        MAX-ACCESS      read-write
        STATUS  current
        DESCRIPTION
                "The number of this port."
        ::= { dsx1ConfigEntry 3 }

dsx1ConfLineType OBJECT-TYPE
        SYNTAX  INTEGER {
                     other(1),
                     dsx1E1(4),
                     dsx1E1CRC(5),
                     dsx1E1MF(6),
                     dsx1E1CRCMF(7),
                     dsx1E1Unframed(9),
                     dsx1Unframed(8),
                     dsx1ESF(2),
                     dsx1D4(3)
                }
        MAX-ACCESS      read-write
        STATUS  current
        DESCRIPTION
                "This variable indicates the variety of E1 Line implementing
                this circuit. The type of circuit affects the number of bits
                per second that the circuit can reasonably carry, as well as
                the interpretation of the usage and error statistics. This
                variable is defined in the rfc1406 configuration table as
                dsx1LineType.

                According to rfc1406, the different values are:
                 dsx1ESF         Extended SuperFrame DS1 (T1.107)
                 dsx1D4          AT&T D4 format DS1 (T1.107)
                 dsx1E1          ITU-T Recommendation G.704
                                  (Table 4a)
                 dsx1E1-CRC      ITU-T Recommendation G.704
                                  (Table 4b)
                 dsxE1-MF        G.704 (Table 4a) with TS16
                                  multiframing enabled
                 dsx1E1-CRC-MF   G.704 (Table 4b) with TS16
                                  multiframing enabled
                 dsx1Unframed    DS1 with No Framing
                 dsx1E1Unframed  E1 with No Framing (G.703)"
        ::= { dsx1ConfigEntry 4 }

dsx1ConfLineCoding OBJECT-TYPE
        SYNTAX  INTEGER
        MAX-ACCESS      read-write
        STATUS  current
        DESCRIPTION
                "This variable describes the variety of Zero Code suppression
                used on this link, which in turn affects a number of its
                characteristics. e1AMI(3) refers to a mode wherein no zero
                code suppression is present and the line encoding does not
                solve the problem directly. In this application, the higher
                layer must provide data which meets or exceeds the pulse
                density re-quirements, such as inverting HDLC data. This
                variable is defined in the rfc1406 configuration table as
                dsx1LineCoding."
        ::= { dsx1ConfigEntry 5 }

dsx1ConfLoopbackConfig OBJECT-TYPE
        SYNTAX  INTEGER {
                      dsx1NoLoop(1),
                      dsx1PayloadLoop(2),
                      dsx1LineLoop(3),
                      dsx1OtherLoop(4),
                      dsx1InwardLoop(5),
                      dsx1DualLoop(6)
                }
        MAX-ACCESS      read-write
        STATUS  current
        DESCRIPTION
                "This variable represents the loopback configuration of the E1
                interface. This variable is defined in the rfc1406
                configuration table as dsx1LoopbackConfig, with slightly
                different values.

                e1NoLoop (1) means that the interface is not in a loopback
                state.

                e1LineLoop (2) means that cells that are processed by the
                receiving component are not written into the receive FIFO, but
                into the transmit FIFO for retransmission.

                e1PayloadLoop (3) means that the receive signal is looped back
                for retransmission after it has passed through the port's
                reframing function.

                e1DiagLoop (4) means that the transmit data stream is looped
                back to the receiver.

                e1OtherLoop (5) means that the interface is in a loopback that
                is not defined here."
        DEFVAL  { 1 }
        ::= { dsx1ConfigEntry 6 }

dsx1ConfLineStatus OBJECT-TYPE
        SYNTAX  INTEGER (1..65534)
        MAX-ACCESS      read-write
        STATUS  current
        DESCRIPTION
                "This variable indicates the Line Status of the interface. A
                similar object is defined in the rfc1406 configuration table as
                dsx1LineStatus. The variable contains loopback state
                information and failure state information. It is a bit map
                represented as a sum. The e1NoAlarm should be set if and only
                if no other flag is set.

                The various bit positions are:
      1     dsx1NoAlarm           No alarm present
      2     dsx1RcvFarEndLOF      Far end LOF (a.k.a., Yellow Alarm)
      4     dsx1XmtFarEndLOF      Near end sending LOF Indication
      8     dsx1RcvAIS            Far end sending AIS
     16     dsx1XmtAIS            Near end sending AIS
     32     dsx1LossOfFrame       Near end LOF (a.k.a., Red Alarm)
     64     dsx1LossOfSignal      Near end Loss Of Signal
    128     dsx1LoopbackState     Near end is looped
    256     dsx1T16AIS            E1 TS16 AIS
    512     dsx1RcvFarEndLOMF     Far End Sending TS16 LOMF
   1024     dsx1XmtFarEndLOMF     Near End Sending TS16 LOMF
   2048     dsx1RcvTestCode       Near End detects a test code
   4096     dsx1OtherFailure      any line status not defined here
   8192     dsx1UnavailSigState   Near End in Unavailable Signal
                                  State
  16384     dsx1NetEquipOOS       Carrier Equipment Out of Service
  32768     dsx1RcvPayloadAIS     DS2 Payload AIS
  65536     dsx1Ds2PerfThreshold  DS2 Performance Threshold
                                  Exceeded"
        ::= { dsx1ConfigEntry 7 }

     dsx1ConfSignalMode OBJECT-TYPE
          SYNTAX  INTEGER
          MAX-ACCESS  read-write
          STATUS  current
          DESCRIPTION
            "."
    ::= { dsx1ConfigEntry 8 }

dsx1ConfTxClockSource OBJECT-TYPE
        SYNTAX  INTEGER {
                     loopTiming(1),
                     localTiming(2),
                     throughTiming(3)
                }
        MAX-ACCESS      read-write
        STATUS  current
        DESCRIPTION
                "The source of the transmit clock. rxTiming(1) indicated that
                the recovered receive clock is used as the transmit clock.
                localTiming(2) indicates that a local source clock is used as
                the transmit clock. To determine which local source clock is
                used advise the ntGlobalClock in the netmodTimingTable for this
                netmod (refer to the Fore-Switch-MIB for more information)."
        DEFVAL  { 2 }
        ::= { dsx1ConfigEntry 9 }

dsx1ConfIdleCells OBJECT-TYPE
        SYNTAX  INTEGER {
                unassigned(1),
                idle(2)
                }
        MAX-ACCESS      read-write
        STATUS  current
        DESCRIPTION
                "This variable indicates the types of cells that should be sent
                in case there is no real data to send. According to the ATM
                Forum, Unassigned cells should be sent (octet 1-3 are 0's,
                octet 4 is 0000xxx0, where x is 'don't care'). According to the
                CCITT specifications, Idle cells should be sent (everything is
                '0' except for the CLP bit which is '1'). By default,
                unassigned cells are transmitted is case there is no data to
                send."
        DEFVAL  { 1 }
        ::= { dsx1ConfigEntry 10 }

     
dsx1ConfRxScrambling OBJECT-TYPE
        SYNTAX  INTEGER {
                descrambling(1),
                noDescrambling(2)
                }
        MAX-ACCESS  read-write
        STATUS  current
        DESCRIPTION
                "This variable indicates whether the information is being
                descrambled on receiving. It should be set the same as the
                transmitting side."
        DEFVAL { 1 }
        ::= { dsx1ConfigEntry 11 }

dsx1ConfTxScrambling OBJECT-TYPE
        SYNTAX  INTEGER {
                scrambling(1),
                noScrambling(2)
                }
        MAX-ACCESS  read-write
        STATUS  current
        DESCRIPTION
                "This variable indicates whether the information (48 octet
                payload) is being scrambled before transmitting. It should
                be set the same as the receiving side."
        DEFVAL { 1 }
        ::= { dsx1ConfigEntry 12 }

     dsx1ConfChannelNumber  OBJECT-TYPE
          SYNTAX      INTEGER (0..28)
          MAX-ACCESS  read-write
          STATUS      current
          DESCRIPTION
                 "This variable represents the channel number of
                 the DS1/E1 on its parent Ds2/E2 or DS3/E3.  A
                 value of 0 indicated this DS1/E1 does not have a
                 parent DS3/E3."

     ::= { dsx1ConfigEntry 13 }

     dsx1ConfChannelization  OBJECT-TYPE
          SYNTAX      INTEGER {
                         disabled(1),
                         enabledDs0(2)
                      }
          MAX-ACCESS  read-write
          STATUS      current
          DESCRIPTION
                 "Indicates whether this ds1/e1 is channelized or
                 unchannelized.  The value of enabledDs0 indicates
                 that this is a DS1 channelized into DS0s.  The
                 value of enabledDs1 indicated that this is a DS2
                 channelized into DS1s.  Setting this value will
                 cause the creation or deletion of entries in the
                 ifTable for the DS0s that are within the DS1."
     ::= { dsx1ConfigEntry 14 }

-- dsx3ConfigTable
dsx3ConfigTable OBJECT-TYPE
        SYNTAX  SEQUENCE OF E3ConfEntry
        MAX-ACCESS      not-accessible
        STATUS  current
        DESCRIPTION
                "A table of T3/E3 switch port configuration information."
        ::= { zxbgs10mib 56 }

dsx3ConfigEntry OBJECT-TYPE
        SYNTAX  E3ConfEntry
        MAX-ACCESS      not-accessible
        STATUS  current
        DESCRIPTION
                "A table entry containing T3/E3 configuration information for each
                port. Not all RFC1406 configuration table variables are
                included, and some are modified."
        INDEX   { 
                dsx3ConfModule, 
                dsx3ConfPort
                }
        ::= { dsx3ConfigTable 1 }

E3ConfEntry ::=
        SEQUENCE {
                dsx3RowStatus                   RowStatus,
                dsx3ConfModule                  INTEGER,
                dsx3ConfPort                    INTEGER,
                dsx3ConfLineType                INTEGER,
                dsx3ConfLineCoding              INTEGER,
                dsx3ConfLoopbackConfig  INTEGER,
                dsx3ConfLineStatus              INTEGER,
                dsx3ConfTxClockSource   INTEGER,
                dsx3ConfIdleCells               INTEGER,
                dsx3ConfRxScrambling    INTEGER,
                dsx3ConfTxScrambling    INTEGER,
                dsx3ConfChannelization  INTEGER,
                dsx3Ds1ForRemoteLoop    INTEGER
}

dsx3RowStatus OBJECT-TYPE
        SYNTAX  RowStatus
        MAX-ACCESS      read-write
        STATUS  current
        DESCRIPTION
                "."
        ::= { dsx3ConfigEntry 1 }

dsx3ConfModule OBJECT-TYPE
        SYNTAX  INTEGER
        MAX-ACCESS      read-write
        STATUS  current
        DESCRIPTION
                "The network module of this port."
        ::= { dsx3ConfigEntry 2 }

dsx3ConfPort OBJECT-TYPE
        SYNTAX  INTEGER
        MAX-ACCESS      read-write
        STATUS  current
        DESCRIPTION
                "The number of this port."
        ::= { dsx3ConfigEntry 3 }

dsx3ConfLineType OBJECT-TYPE
        SYNTAX  INTEGER {
                     e3other(6),
                     e3Framed(7),
                     e3Plcp(8),
                     dsx3ClearChannel(5),
                     dsx3other(1),
                     dsx3M23(2),
                     dsx3SYNTRAN(3),
                     dsx3CbitParity(4)
                }
          MAX-ACCESS  read-write
          STATUS  current
          DESCRIPTION
                 "This variable indicates the variety of DS3 C-bit
                 or E3 application implementing this interface. The
                 type of interface affects the interpretation of
                 the usage and error statistics.  The rate of DS3
                 is 44.736 Mbps and E3 is 34.368 Mbps.  The
                 dsx3ClearChannel value means that the C-bits are
                 not used except for sending/receiving AIS.
                 The values, in sequence, describe:

                 TITLE:            SPECIFICATION:
                 dsx3M23            ANSI T1.107-1988 [9]
                 dsx3SYNTRAN        ANSI T1.107-1988 [9]
                 dsx3CbitParity     ANSI T1.107a-1990 [9a]
                 dsx3ClearChannel   ANSI T1.102-1987 [8]
                 e3Framed           CCITT G.751 [12]
                 e3Plcp             ETSI T/NA(91)18 [13]."
          ::= { dsx3ConfigEntry 4 }

dsx3ConfLineCoding OBJECT-TYPE
          SYNTAX  INTEGER {
                     dsx3Other(1),
                     e3HDB3(3),
                     dsx3B3ZS(2)
                 }
          MAX-ACCESS  read-write
          STATUS  current
          DESCRIPTION
                 "This variable describes the variety of Zero Code
                 Suppression used on this interface, which in turn
                 affects a number of its characteristics.

                 dsx3B3ZS and e3HDB3 refer to the use of specified
                 patterns of normal bits and bipolar violations
                 which are used to replace sequences of zero bits
                 of a specified length."
          ::= { dsx3ConfigEntry 5 }

dsx3ConfLoopbackConfig OBJECT-TYPE
        SYNTAX  INTEGER {
                ds3NoLoop (1),
                ds3PayloadLoop (3),
                ds3LineLoop (5),
                ds3OtherLoop (6)
                }
        MAX-ACCESS      read-write
        STATUS  current
        DESCRIPTION
                "This variable represents the loopback configuration of the DS3
                interface. This variable is defined in the rfc1407
                configuration table as dsx3LoopbackConfig, with slightly
                different values.

                ds3NoLoop (1) means that the interface is not in a loopback
                state.

                ds3CellLoop (2) means that cells that are processed by the
                receiving component are not written into the receive FIFO, but
                into the transmit FIFO for retransmission.

                ds3PayloadLoop (3) means that the receive signal is looped back
                for retransmission after it has passed through the port's
                reframing function.

                ds3DiagLoop (4) means that the transmit data stream is looped
                back to the receiver.

                ds3LineLoop (5) is only supported on series B and later
                netmods.

                ds3OtherLoop (6) means that the interface is in a loopback that
                is not defined here."
        DEFVAL  { 1 }
        ::= { dsx3ConfigEntry 6 }

dsx3ConfLineStatus OBJECT-TYPE
          SYNTAX  INTEGER (1..4095)
          MAX-ACCESS  read-write
          STATUS  current
          DESCRIPTION
                 "This variable indicates the Line Status of the
                 interface.  It contains loopback state information
                 and failure state information.  The dsx3LineStatus
                 is a bit map represented as a sum, therefore, it
                 can represent multiple failures and a loopback
                 (see dsx3LoopbackConfig object for the type of
                 loopback) simultaneously.  The dsx3NoAlarm must be
                 set if and only if no other flag is set.

                 If the dsx3loopbackState bit is set, the loopback
                 in effect can be determined from the
                 dsx3loopbackConfig object.
       The various bit positions are:
        1     dsx3NoAlarm         No alarm present
        2     dsx3RcvRAIFailure   Receiving Yellow/Remote
                                  Alarm Indication
        4     dsx3XmitRAIAlarm    Transmitting Yellow/Remote
                                  Alarm Indication
        8     dsx3RcvAIS          Receiving AIS failure state
       16     dsx3XmitAIS         Transmitting AIS
       32     dsx3LOF             Receiving LOF failure state
       64     dsx3LOS             Receiving LOS failure state
      128     dsx3LoopbackState   Looping the received signal
      256     dsx3RcvTestCode     Receiving a Test Pattern
      512     dsx3OtherFailure    any line status not defined
                                  here
     1024     dsx3UnavailSigState Near End in Unavailable Signal
                                  State
     2048     dsx3NetEquipOOS     Carrier Equipment Out of Service"
     ::= { dsx3ConfigEntry 7 }

dsx3ConfTxClockSource OBJECT-TYPE
     SYNTAX  INTEGER {
                loopTiming(1),
                localTiming(2),
                throughTiming(3)
            }
     MAX-ACCESS  read-write
     STATUS  current
     DESCRIPTION
            "The source of Transmit Clock.

            loopTiming indicates that the recovered receive clock
            is used as the transmit clock.

            localTiming indicates that a local clock source is used
            or that an external clock is attached to the box
            containing the interface.

            throughTiming indicates that transmit clock is derived
            from the recovered receive clock of another DS3
            interface."
          ::= { dsx3ConfigEntry 8 }

dsx3ConfIdleCells OBJECT-TYPE
        SYNTAX  INTEGER {
                unassigned(1),
                idle(2)
                }
        MAX-ACCESS      read-write
        STATUS  current
        DESCRIPTION
                "This variable indicates the types of cells that should be sent
                in case there is no real data to send. According to the ATM
                Forum, Unassigned cells should be sent (octet 1-3 are 0's,
                octet 4 is 0000xxx0, where x is 'don't care'). According to the
                CCITT specifications, Idle cells should be sent (everything is
                '0' except for the CLP bit which is '1'). By default,
                unassigned cells are transmitted is case there is no data to
                send."
        DEFVAL  { 1 }
        ::= { dsx3ConfigEntry 9 }

dsx3ConfRxScrambling OBJECT-TYPE
        SYNTAX  INTEGER {
                descrambling(1),
                noDescrambling(2)
                }
        MAX-ACCESS      read-write
        STATUS  current
        DESCRIPTION
                "This variable indicates whether the information is being
                descrambled on receiving. It should be set the same as the
                transmitting side."
        DEFVAL  { 2 }
        ::= { dsx3ConfigEntry 10 }

dsx3ConfTxScrambling OBJECT-TYPE
        SYNTAX  INTEGER {
                scrambling(1),
                noScrambling(2)
                }
        MAX-ACCESS      read-write
        STATUS  current
        DESCRIPTION
                "This variable indicates whether the information (48 octet
                payload) is being scrambled before transmitting. It should be
                set the same as the receiving side."
        DEFVAL  { 2 }
        ::= { dsx3ConfigEntry 11 }

     dsx3ConfChannelization  OBJECT-TYPE
          SYNTAX      INTEGER {
                         disabled(1),
                         enabledDs1(2),
                         enabledDs2(3)
                      }
          MAX-ACCESS  read-write
          STATUS      current
          DESCRIPTION
                 "Indicates whether this ds3/e3 is channelized or
                 unchannelized.  The value of enabledDs1 indicates
                 that this is a DS3 channelized into DS1s.  The
                 value of enabledDs3 indicated that this is a DS3
                 channelized into DS2s.  Setting this object will
                 cause the creation or deletion of DS2 or DS1
                 entries in the ifTable.  "
     ::= { dsx3ConfigEntry 12 }

     dsx3Ds1ForRemoteLoop  OBJECT-TYPE
          SYNTAX      INTEGER (0..29)

          MAX-ACCESS  read-write
          STATUS      current
          DESCRIPTION
                 "Indicates which ds1/e1 on this ds3/e3 will be
                 indicated in the remote ds1 loopback request.  A
                 value of 0 means no DS1 will be looped.  A value
                 of 29 means all ds1s/e1s will be looped."
     ::= { dsx3ConfigEntry 13 }



-- bgs10SDHConfigTable
bgs10SDHConfigTable OBJECT-TYPE
        SYNTAX  SEQUENCE OF BGS10SDHConfigEntry
        MAX-ACCESS      not-accessible
        STATUS  current
        DESCRIPTION
                ""
        ::= { zxbgs10mib 60 }

bgs10SDHConfigEntry OBJECT-TYPE
        SYNTAX  BGS10SDHConfigEntry
        MAX-ACCESS      not-accessible
        STATUS  current
        DESCRIPTION
                "."
        INDEX   { 
                bgs10SDHSonetConfModule,
                bgs10SDHSonetConfPort
                }
        ::= { bgs10SDHConfigTable 1 }
        
BGS10SDHConfigEntry ::=
        SEQUENCE {
                bgs10SDHRowStatus               RowStatus,
                bgs10SDHSonetConfModule         UCHAR,
                bgs10SDHSonetConfPort           UCHAR,
                bgs10SDHMediumType              UCHAR,
                bgs10SDHLineType                UCHAR,
                bgs10SDHLineCodeing             UCHAR,
                bgs10SDHTxClockSource           UCHAR,
                bgs10SDHTxClockClass            UCHAR,
                bgs10SDHRxClockClass            UCHAR,
                bgs10SDHTxScrambling            UCHAR,
                bgs10SDHRxScrambling            UCHAR,
                bgs10SDHIdleUnassignedCells     UCHAR,
                bgs10SDHCellHead                INTEGER,
                bgs10SDHsonetConfLoopbackConfig UCHAR
}

bgs10SDHRowStatus OBJECT-TYPE
        SYNTAX  RowStatus
        MAX-ACCESS      read-write
        STATUS  current
        DESCRIPTION
                "."
        ::= { bgs10SDHConfigEntry 1 }

bgs10SDHSonetConfModule OBJECT-TYPE
        SYNTAX  UCHAR
        MAX-ACCESS      read-write
        STATUS  current
        DESCRIPTION
                "."
        ::= { bgs10SDHConfigEntry 2 }

bgs10SDHSonetConfPort OBJECT-TYPE
        SYNTAX  UCHAR
        MAX-ACCESS      read-write
        STATUS  current
        DESCRIPTION
                "."
        ::= { bgs10SDHConfigEntry 3 }

bgs10SDHMediumType OBJECT-TYPE
        SYNTAX  UCHAR
        MAX-ACCESS      read-write
        STATUS  current
        DESCRIPTION
                "."
        ::= { bgs10SDHConfigEntry 4 }

bgs10SDHLineType OBJECT-TYPE
        SYNTAX  UCHAR
        MAX-ACCESS      read-write
        STATUS  current
        DESCRIPTION
                "."
        ::= { bgs10SDHConfigEntry 5 }

bgs10SDHLineCodeing OBJECT-TYPE
        SYNTAX  UCHAR
        MAX-ACCESS      read-write
        STATUS  current
        DESCRIPTION
                "."
        ::= { bgs10SDHConfigEntry 6 }

bgs10SDHTxClockSource OBJECT-TYPE
        SYNTAX  UCHAR
        MAX-ACCESS      read-write
        STATUS  current
        DESCRIPTION
                "."
        ::= { bgs10SDHConfigEntry 7 }

bgs10SDHTxClockClass OBJECT-TYPE
        SYNTAX  UCHAR
        MAX-ACCESS      read-write
        STATUS  current
        DESCRIPTION
                "."
        ::= { bgs10SDHConfigEntry 8 }

bgs10SDHRxClockClass OBJECT-TYPE
        SYNTAX  UCHAR
        MAX-ACCESS      read-write
        STATUS  current
        DESCRIPTION
                "."
        ::= { bgs10SDHConfigEntry 9 }

bgs10SDHTxScrambling OBJECT-TYPE
        SYNTAX  UCHAR
        MAX-ACCESS      read-write
        STATUS  current
        DESCRIPTION
                "."
        ::= { bgs10SDHConfigEntry 10 }

bgs10SDHRxScrambling OBJECT-TYPE
        SYNTAX  UCHAR
        MAX-ACCESS      read-write
        STATUS  current
        DESCRIPTION
                "."
        ::= { bgs10SDHConfigEntry 11 }

bgs10SDHIdleUnassignedCells OBJECT-TYPE
        SYNTAX  UCHAR
        MAX-ACCESS      read-write
        STATUS  current
        DESCRIPTION
                "."
        ::= { bgs10SDHConfigEntry 12 }

bgs10SDHCellHead OBJECT-TYPE
        SYNTAX  INTEGER
        MAX-ACCESS      read-write
        STATUS  current
        DESCRIPTION
                "."
        ::= { bgs10SDHConfigEntry 13 }

bgs10SDHsonetConfLoopbackConfig OBJECT-TYPE
    SYNTAX   UCHAR
    MAX-ACCESS  read-write
    STATUS  current
    DESCRIPTION
        "."
    ::= { bgs10SDHConfigEntry 14 }



-- bgs10IMAGroupConfTable
bgs10IMAGroupConfTable OBJECT-TYPE
        SYNTAX  SEQUENCE OF BGS10IMAGroupConfEntry
        MAX-ACCESS      not-accessible
        STATUS  current
        DESCRIPTION
                ""
        ::= { zxbgs10mib 61 }

bgs10IMAGroupConfEntry OBJECT-TYPE
        SYNTAX  BGS10IMAGroupConfEntry
        MAX-ACCESS      not-accessible
        STATUS  current
        DESCRIPTION
                "."
        INDEX {
                bgs10ImaGroupBetaValue
                }
        ::= { bgs10IMAGroupConfTable 1 }
        
BGS10IMAGroupConfEntry ::=
        SEQUENCE {
                bgs10ImaGroupRowStatus                  RowStatus,
                bgs10ImaGroupBetaValue                  UCHAR,
                bgs10ImaGroupGammaValue                 UCHAR,
                bgs10ImaGroupAlphaValue                 UCHAR,
                bgs10ImaGroupMinNumTxLinks              UCHAR,
                bgs10ImaGroupNeTxClkMode                UCHAR,
                bgs10ImaGroupMinNumRxLinks              UCHAR,
                bgs10ImaGroupNumTxCfgLnks               UCHAR,
                bgs10ImaGroupNumRxCfgLnks               UCHAR,
                bgs10ImaGroupSymmetry                   UCHAR,
                bgs10ImaGroupTxFrameLength              UCHAR,
                bgs10ImaGroupTxTimingRefLink            UCHAR,
                bgs10ImaGroupTxImaId                    UCHAR,
                bgs10ImaGroupDiffDelayMax               UCHAR,
                bgs10ImaOamLabel                        UCHAR,
                bgs10GroupAdminStatus                   UCHAR,
                bgs10ImaGroupFlag                       UCHAR,
                bgs10StatisticsTime                     Unsigned32,
                bgs10ImaGroupNeState                    UCHAR,
                bgs10ImaAlarmType                       UCHAR,
                bgs10imaGroupVer                        UCHAR,
                bgs10ImaGroupM2SClkMode                 UCHAR,
                bgs10imaGroupLinkScramble               UCHAR                
}

bgs10ImaGroupRowStatus OBJECT-TYPE
        SYNTAX  RowStatus
        MAX-ACCESS      read-write
        STATUS  current
        DESCRIPTION
                "."
        ::= { bgs10IMAGroupConfEntry 1 }

bgs10ImaGroupBetaValue OBJECT-TYPE
        SYNTAX  UCHAR
        MAX-ACCESS      read-write
        STATUS  current
        DESCRIPTION
                "."
        ::= { bgs10IMAGroupConfEntry 2 }

bgs10ImaGroupGammaValue OBJECT-TYPE
        SYNTAX  UCHAR
        MAX-ACCESS      read-write
        STATUS  current
        DESCRIPTION
                "."
        ::= { bgs10IMAGroupConfEntry 3 }

bgs10ImaGroupAlphaValue OBJECT-TYPE
        SYNTAX  UCHAR
        MAX-ACCESS      read-write
        STATUS  current
        DESCRIPTION
                "."
        ::= { bgs10IMAGroupConfEntry 4 }

bgs10ImaGroupMinNumTxLinks OBJECT-TYPE
        SYNTAX  UCHAR
        MAX-ACCESS      read-write
        STATUS  current
        DESCRIPTION
                "."
        ::= { bgs10IMAGroupConfEntry 5 }

bgs10ImaGroupNeTxClkMode OBJECT-TYPE
        SYNTAX  UCHAR
        MAX-ACCESS      read-write
        STATUS  current
        DESCRIPTION
                "."
        ::= { bgs10IMAGroupConfEntry 6 }

bgs10ImaGroupMinNumRxLinks OBJECT-TYPE
        SYNTAX  UCHAR
        MAX-ACCESS      read-write
        STATUS  current
        DESCRIPTION
                "."
        ::= { bgs10IMAGroupConfEntry 7 }

bgs10ImaGroupNumTxCfgLnks OBJECT-TYPE
        SYNTAX  UCHAR
        MAX-ACCESS      read-write
        STATUS  current
        DESCRIPTION
                "."
        ::= { bgs10IMAGroupConfEntry 8 }

bgs10ImaGroupNumRxCfgLnks OBJECT-TYPE
        SYNTAX  UCHAR
        MAX-ACCESS      read-write
        STATUS  current
        DESCRIPTION
                "."
        ::= { bgs10IMAGroupConfEntry 9 }

bgs10ImaGroupSymmetry OBJECT-TYPE
        SYNTAX  UCHAR
        MAX-ACCESS      read-write
        STATUS  current
        DESCRIPTION
                "."
        ::= { bgs10IMAGroupConfEntry 10 }

bgs10ImaGroupTxFrameLength OBJECT-TYPE
        SYNTAX  UCHAR
        MAX-ACCESS      read-write
        STATUS  current
        DESCRIPTION
                "."
        ::= { bgs10IMAGroupConfEntry 11 }

bgs10ImaGroupTxTimingRefLink OBJECT-TYPE
        SYNTAX  UCHAR
        MAX-ACCESS      read-write
        STATUS  current
        DESCRIPTION
                "."
        ::= { bgs10IMAGroupConfEntry 12 }

bgs10ImaGroupTxImaId OBJECT-TYPE
        SYNTAX  UCHAR
        MAX-ACCESS      read-write
        STATUS  current
        DESCRIPTION
                "."
        ::= { bgs10IMAGroupConfEntry 13 }

bgs10ImaGroupDiffDelayMax OBJECT-TYPE
        SYNTAX  UCHAR
        MAX-ACCESS      read-write
        STATUS  current
        DESCRIPTION
                "."
        ::= { bgs10IMAGroupConfEntry 14 }

bgs10ImaOamLabel OBJECT-TYPE
        SYNTAX  UCHAR
        MAX-ACCESS      read-write
        STATUS  current
        DESCRIPTION
                "."
        ::= { bgs10IMAGroupConfEntry 15 }

bgs10GroupAdminStatus OBJECT-TYPE
        SYNTAX  UCHAR
        MAX-ACCESS      read-write
        STATUS  current
        DESCRIPTION
                "."
        ::= { bgs10IMAGroupConfEntry 16 }

bgs10ImaGroupFlag OBJECT-TYPE
        SYNTAX  UCHAR
        MAX-ACCESS      read-write
        STATUS  current
        DESCRIPTION
                "."
        ::= { bgs10IMAGroupConfEntry 17 }

bgs10StatisticsTime OBJECT-TYPE
        SYNTAX  Unsigned32
        MAX-ACCESS      read-write
        STATUS  current
        DESCRIPTION
                "."
        ::= { bgs10IMAGroupConfEntry 18 }

bgs10ImaGroupNeState OBJECT-TYPE
        SYNTAX  UCHAR
        MAX-ACCESS      read-write
        STATUS  current
        DESCRIPTION
                "."
        ::= { bgs10IMAGroupConfEntry 19 }

bgs10ImaAlarmType OBJECT-TYPE
        SYNTAX  UCHAR
        MAX-ACCESS      read-write
        STATUS  current
        DESCRIPTION
                "."
        ::= { bgs10IMAGroupConfEntry 20 }

bgs10imaGroupVer OBJECT-TYPE
    SYNTAX  UCHAR
    MAX-ACCESS  read-write
    STATUS  current
    DESCRIPTION
        "."
    ::= { bgs10IMAGroupConfEntry 21 }
    
bgs10ImaGroupM2SClkMode OBJECT-TYPE
    SYNTAX  UCHAR
    MAX-ACCESS  read-write
    STATUS  current
    DESCRIPTION
        "."
    ::= { bgs10IMAGroupConfEntry 22 }
bgs10imaGroupLinkScramble   OBJECT-TYPE
    SYNTAX      UCHAR
    MAX-ACCESS  read-write
    STATUS  current
    DESCRIPTION
        "."
    ::= { bgs10IMAGroupConfEntry 23 }   


-- bgs10IMALinkConfTable
bgs10IMALinkConfTable OBJECT-TYPE
        SYNTAX  SEQUENCE OF BGS10IMALinkConfEntry
        MAX-ACCESS      not-accessible
        STATUS  current
        DESCRIPTION
                ""
        ::= { zxbgs10mib 62 }

bgs10IMALinkConfEntry OBJECT-TYPE
        SYNTAX  BGS10IMALinkConfEntry
        MAX-ACCESS      not-accessible
        STATUS  current
        DESCRIPTION
                "."
        INDEX {
                bgs10ImaLinkTxLid
                }
        ::= { bgs10IMALinkConfTable 1 }
        
BGS10IMALinkConfEntry ::=
        SEQUENCE {
                bgs10ImaLinkRowStatus                   RowStatus,
                bgs10ImaLinkTxLid                       UCHAR,
                bgs10ImaLinkTxStat                      UCHAR,
                bgs10ImaLinkRxStat                      UCHAR,
                bgs10ImaLinkGroupIndex                  UCHAR,
                bgs10ImaLinkFlag                        UCHAR,
                bgs10ImaLinkStatisticsTime              Unsigned32,
                bgs10imaLinkNeTxAdminStatus             UCHAR,
                bgs10imaLinkNeRxAdminStatus             UCHAR,
                bgs10imaLinkd                           UCHAR
}

bgs10ImaLinkRowStatus OBJECT-TYPE
        SYNTAX  RowStatus
        MAX-ACCESS      read-write
        STATUS  current
        DESCRIPTION
                "."
        ::= { bgs10IMALinkConfEntry 1 }

bgs10ImaLinkTxLid OBJECT-TYPE
        SYNTAX          UCHAR
        MAX-ACCESS      read-write
        STATUS  current
        DESCRIPTION
                "."
        ::= { bgs10IMALinkConfEntry 2 }

bgs10ImaLinkTxStat OBJECT-TYPE
        SYNTAX          UCHAR
        MAX-ACCESS      read-write
        STATUS  current
        DESCRIPTION
                "."
        ::= { bgs10IMALinkConfEntry 3 }

bgs10ImaLinkRxStat OBJECT-TYPE
        SYNTAX          UCHAR
        MAX-ACCESS      read-write
        STATUS  current
        DESCRIPTION
                "."
        ::= { bgs10IMALinkConfEntry 4 }

bgs10ImaLinkGroupIndex OBJECT-TYPE
        SYNTAX          UCHAR
        MAX-ACCESS      read-write
        STATUS  current
        DESCRIPTION
                "."
        ::= { bgs10IMALinkConfEntry 5 }

bgs10ImaLinkFlag OBJECT-TYPE
        SYNTAX          UCHAR
        MAX-ACCESS      read-write
        STATUS  current
        DESCRIPTION
                "."
        ::= { bgs10IMALinkConfEntry 6 }

bgs10ImaLinkStatisticsTime OBJECT-TYPE
        SYNTAX          Unsigned32
        MAX-ACCESS      read-write
        STATUS  current
        DESCRIPTION
                "."
        ::= { bgs10IMALinkConfEntry 7 }

bgs10imaLinkNeTxAdminStatus OBJECT-TYPE
        SYNTAX          UCHAR
        MAX-ACCESS      read-write
        STATUS  current
        DESCRIPTION
                "."
        ::= { bgs10IMALinkConfEntry 8 }

bgs10imaLinkNeRxAdminStatus     OBJECT-TYPE
        SYNTAX          UCHAR
        MAX-ACCESS      read-write
        STATUS  current
        DESCRIPTION
                "."
        ::= { bgs10IMALinkConfEntry 9 }

bgs10imaLinkd   OBJECT-TYPE
    SYNTAX      UCHAR
    MAX-ACCESS  read-write
    STATUS  current
    DESCRIPTION
        "."
    ::= { bgs10IMALinkConfEntry 10 }


-- ATM perfromance mgmt
        
--The TC adapter supplyment
bgs10TcProtoCurTable    OBJECT-TYPE
        SYNTAX          SEQUENCE OF ZXB10TCProtocolEntry
        MAX-ACCESS      not-accessible
        STATUS          current
        DESCRIPTION
                "the plug-in unittable."
        ::= { zxbgs10mib 34 }
        
bgs10TcProtoCurEntry    OBJECT-TYPE
        SYNTAX          ZXB10TCProtocolEntry
        MAX-ACCESS      not-accessible
        STATUS          current
        DESCRIPTION
                "the entry to the TC protocol table."
    INDEX { ifIndex }           
--      AUGMENTS { atmfM4TcProtoCurrEntry }
        ::= { bgs10TcProtoCurTable 1 }
        
ZXB10TCProtocolEntry    ::=
        SEQUENCE {
                zxb10TcProCurPerfModule         UCHAR,
                zxb10TcProCurPerfPort           UCHAR,
                zxb10TcProCurSectionbip8        Gauge32,
                zxb10TcProCurLinebip8           Gauge32,
                zxb10TcProCurLinefebe           Gauge32, 
                zxb10TcProCurPathbip24          Gauge32,
                zxb10TcProCurPathfebe           Gauge32,
                zxb10TcProCurCorrecthcs         Gauge32,
                zxb10TcProCurRxCell                     Gauge32,
                zxb10TcProCurTxCell                     Gauge32
        }

zxb10TcProCurPerfModule         OBJECT-TYPE
        SYNTAX          UCHAR
        MAX-ACCESS      read-only
        STATUS          current
        DESCRIPTION
                "."
        ::= { bgs10TcProtoCurEntry 1 }
        
zxb10TcProCurPerfPort           OBJECT-TYPE
        SYNTAX          UCHAR
        MAX-ACCESS      read-only
        STATUS          current
        DESCRIPTION
                "."
        ::= { bgs10TcProtoCurEntry 2 }
                
zxb10TcProCurSectionbip8        OBJECT-TYPE
        SYNTAX          Gauge32
        MAX-ACCESS      read-only
        STATUS          current
        DESCRIPTION
                "."
        ::= { bgs10TcProtoCurEntry 3 }
        
zxb10TcProCurLinebip8           OBJECT-TYPE
        SYNTAX          Gauge32
        MAX-ACCESS      read-only
        STATUS          current
        DESCRIPTION
                "."
        ::= { bgs10TcProtoCurEntry 4 }
        
        
zxb10TcProCurLinefebe           OBJECT-TYPE
        SYNTAX          Gauge32
        MAX-ACCESS      read-only
        STATUS          current
        DESCRIPTION
                "."
        ::= { bgs10TcProtoCurEntry 5 }
        
zxb10TcProCurPathbip24          OBJECT-TYPE
        SYNTAX          Gauge32
        MAX-ACCESS      read-only
        STATUS          current
        DESCRIPTION
                "."
        ::= { bgs10TcProtoCurEntry 6 }
        
zxb10TcProCurPathfebe           OBJECT-TYPE
        SYNTAX          Gauge32
        MAX-ACCESS      read-only
        STATUS          current
        DESCRIPTION
                "."
        ::= { bgs10TcProtoCurEntry 7 }
        
zxb10TcProCurCorrecthcs         OBJECT-TYPE
        SYNTAX          Gauge32
        MAX-ACCESS      read-only
        STATUS          current
        DESCRIPTION
                "."
        ::= { bgs10TcProtoCurEntry 8 }
        
zxb10TcProCurRxCell                     OBJECT-TYPE
        SYNTAX          Gauge32
        MAX-ACCESS      read-only
        STATUS          current
        DESCRIPTION
                "."
        ::= { bgs10TcProtoCurEntry 9 }
        
zxb10TcProCurTxCell                     OBJECT-TYPE
        SYNTAX          Gauge32
        MAX-ACCESS      read-only
        STATUS          current
        DESCRIPTION
                "."
        ::= { bgs10TcProtoCurEntry 10 }
        
--The supplement to VP UPC/NPC          
bgs10VpUpcNpcCurrTable  OBJECT-TYPE
        SYNTAX          SEQUENCE OF ZXB10VpUpcNpcEntry
        MAX-ACCESS      not-accessible
        STATUS          current
        DESCRIPTION
                "the plug-in unittable."
        ::= { zxbgs10mib 35 }
        
bgs10VpUpcNpcCurEntry   OBJECT-TYPE
        SYNTAX          ZXB10VpUpcNpcEntry
        MAX-ACCESS      not-accessible
        STATUS          current
        DESCRIPTION
                "the entry to the TC protocol table."
                    INDEX { ifIndex }
--      AUGMENTS { atmfM4VpUpcNpcCurrEntry }
        ::= { bgs10VpUpcNpcCurrTable 1 }
        
ZXB10VpUpcNpcEntry      ::=
        SEQUENCE {
                zxb10VpUpcNpcCurPassTagedCell           Gauge32,
                zxb10VpUpcNpcCurIfIndex                         UShort,
                zxb10VpUpcNpcCurVpi                                     UShort
        }

zxb10VpUpcNpcCurPassTagedCell           OBJECT-TYPE
        SYNTAX          Gauge32
        MAX-ACCESS      read-only
        STATUS          current
        DESCRIPTION
                "."
        ::= { bgs10VpUpcNpcCurEntry 1 }
        
zxb10VpUpcNpcCurIfIndex OBJECT-TYPE
        SYNTAX          UShort
        MAX-ACCESS      read-only
        STATUS          current
        DESCRIPTION
                "Interface Interface."
        ::= { bgs10VpUpcNpcCurEntry 2 }
        
zxb10VpUpcNpcCurVpi     OBJECT-TYPE
        SYNTAX          UShort
        MAX-ACCESS      read-only
        STATUS          current
        DESCRIPTION
                "Current VPI."
        ::= { bgs10VpUpcNpcCurEntry 3 }


--The congest table.
bgs10CongestTable               OBJECT IDENTIFIER       ::= { zxbgs10mib 36 }

bgs10CongRowStatus      OBJECT-TYPE
        SYNTAX          UCHAR
        MAX-ACCESS      read-only
        STATUS          current
        DESCRIPTION
                "."
        ::= { bgs10CongestTable 1 }
        
bgs10Congperfmodule     OBJECT-TYPE
        SYNTAX          UCHAR
        MAX-ACCESS      read-only
        STATUS          current
        DESCRIPTION
                "."
        ::= { bgs10CongestTable 2 }
        
bgs10Congperftype       OBJECT-TYPE
        SYNTAX          UCHAR
        MAX-ACCESS      read-only
        STATUS          current
        DESCRIPTION
                "."
        ::= { bgs10CongestTable 3 }   
        
bgs10Congincellqueue    OBJECT-TYPE
        SYNTAX          Unsigned32
        MAX-ACCESS      read-only
        STATUS          current
        DESCRIPTION
                "."
        ::= { bgs10CongestTable 4 }
        
bgs10Congoutcellqueue   OBJECT-TYPE
        SYNTAX          Unsigned32
        MAX-ACCESS      read-only
        STATUS          current
        DESCRIPTION
                "."
        ::= { bgs10CongestTable 5 }
        
bgs10Congtime   OBJECT-TYPE
        SYNTAX          Unsigned32
        MAX-ACCESS      read-only
        STATUS          current
        DESCRIPTION
                "."
        ::= { bgs10CongestTable 6 }
        
bgs10Congperfspace      OBJECT-TYPE
        SYNTAX          Unsigned32
        MAX-ACCESS      read-only
        STATUS          current
        DESCRIPTION
                "."
        ::= { bgs10CongestTable 7 }
        
--The supplement to VC UPC/NPC          
bgs10VcUpcNpcCurrTable  OBJECT-TYPE
        SYNTAX          SEQUENCE OF ZXB10VcUpcNpcEntry
        MAX-ACCESS      not-accessible
        STATUS          current
        DESCRIPTION
                "the plug-in unittable."
        ::= { zxbgs10mib 37 }
        
bgs10VcUpcNpcCurEntry   OBJECT-TYPE
        SYNTAX          ZXB10VcUpcNpcEntry
        MAX-ACCESS      not-accessible
        STATUS          current
        DESCRIPTION
                "the entry to the TC protocol table."
    INDEX { ifIndex }           
--      AUGMENTS { atmfM4VcUpcNpcCurrEntry }
        ::= { bgs10VcUpcNpcCurrTable 1 }
        
ZXB10VcUpcNpcEntry      ::=
        SEQUENCE {
                zxb10VcUpcNpcCurPassTagedCell           Gauge32,
                zxb10VcUpcNpcCurIfIndex                         UShort,
                zxb10VcUpcNpcCurVpi                                     UShort,
                zxb10VcUpcNpcCurVci                                     UShort
        }

zxb10VcUpcNpcCurPassTagedCell           OBJECT-TYPE
        SYNTAX          Gauge32
        MAX-ACCESS      read-only
        STATUS          current
        DESCRIPTION
                "current passed taged cells."
        ::= { bgs10VcUpcNpcCurEntry 1 }
        
zxb10VcUpcNpcCurIfIndex OBJECT-TYPE
        SYNTAX          UShort
        MAX-ACCESS      read-only
        STATUS          current
        DESCRIPTION
                "Interface Interface."
        ::= { bgs10VcUpcNpcCurEntry 2 }
        
zxb10VcUpcNpcCurVpi     OBJECT-TYPE
        SYNTAX          UShort
        MAX-ACCESS      read-only
        STATUS          current
        DESCRIPTION
                "Current VPI."
        ::= { bgs10VcUpcNpcCurEntry 3 }

zxb10VcUpcNpcCurVci     OBJECT-TYPE
        SYNTAX          UShort
        MAX-ACCESS      read-only
        STATUS          current
        DESCRIPTION
                "Current VCI."
        ::= { bgs10VcUpcNpcCurEntry 4 }

--Man-Machine Language MIB
bgs10MMLResultTable OBJECT-TYPE
    SYNTAX      SEQUENCE OF BGS10MMLResultEntry
    MAX-ACCESS  not-accessible
    STATUS      current
    DESCRIPTION
        "A list of Man-Machine language."
    ::= { zxbgs10mib 8}
        
bgs10MMLResultEntry OBJECT-TYPE
    SYNTAX      BGS10MMLResultEntry
    MAX-ACCESS  not-accessible
    STATUS      current
    DESCRIPTION
        "An entry in the table."
    INDEX { bgs10MessageNo  }
    ::= { bgs10MMLResultTable 1}
    
BGS10MMLResultEntry ::=
    SEQUENCE {
        bgs10MMLResultRowStatus     RowStatus,
        bgs10MMLResultErrNumber     UShort
        }
        
bgs10MMLResultRowStatus OBJECT-TYPE
    SYNTAX      RowStatus
    MAX-ACCESS  read-create
    STATUS      current
    DESCRIPTION
        "row status."
    ::= { bgs10MMLResultEntry 1}
    
bgs10MMLResultErrNumber     OBJECT-TYPE
    SYNTAX      UShort
    MAX-ACCESS  read-create
    STATUS      current
    DESCRIPTION
        "row status."
    ::= { bgs10MMLResultEntry 2}

--This Node is specially for Index
bgs10MIBIndex           OBJECT IDENTIFIER   ::= { zxbgs10mib 9}

bgs10MessageNo  OBJECT-TYPE
    SYNTAX      INTEGER
    MAX-ACCESS  not-accessible
    STATUS      current
    DESCRIPTION
        "For MML table."
    ::= { bgs10MIBIndex 1}
    
bgs10ModuleNo   OBJECT-TYPE
    SYNTAX      INTEGER
    MAX-ACCESS  read-only
    STATUS      current
    DESCRIPTION
        "The 8-bit unsigned integer."
    ::= { bgs10MIBIndex 2}
    
bgs10PortNo OBJECT-TYPE
    SYNTAX      INTEGER
    MAX-ACCESS  not-accessible
    STATUS      current
    DESCRIPTION
        "The 8-bit unsigned integer."
    ::= { bgs10MIBIndex 3}
    
bgs10DataViewNo OBJECT-TYPE
    SYNTAX      INTEGER
    MAX-ACCESS  not-accessible
    STATUS      current
    DESCRIPTION
        "The 8-bit unsigned integer."
    ::= { bgs10MIBIndex 4}
    
bgs10TotalPort  OBJECT-TYPE
    SYNTAX      INTEGER
    MAX-ACCESS  not-accessible
    STATUS      current
    DESCRIPTION
        "The integer."
    ::= { bgs10MIBIndex 5}

--bgs10NMSServer
bgs10NMSServer  OBJECT-TYPE
    SYNTAX      SEQUENCE OF BGS10NMSServerEntry
    MAX-ACCESS  not-accessible
    STATUS      current
    DESCRIPTION
        "."
    ::= { zxbgs10mib 54}
    
bgs10NMSServerEntry OBJECT-TYPE
    SYNTAX      BGS10NMSServerEntry
    MAX-ACCESS  not-accessible
    STATUS      current
    DESCRIPTION
        "An entry in the table."
    INDEX { 
        bgs10NMSServerIpAddress
        }
    ::= { bgs10NMSServer 1}
    
BGS10NMSServerEntry ::=
    SEQUENCE {
        bgs10NMSServerRowStatus             RowStatus,
        bgs10NMSServerIpAddress             IpAddress,
        bgs10NMSServersnmpversion           UChar
    }

bgs10NMSServerRowStatus OBJECT-TYPE 
    SYNTAX      RowStatus
    MAX-ACCESS  read-write
    STATUS      current
    DESCRIPTION
        ""
    ::= { bgs10NMSServerEntry 1}

bgs10NMSServerIpAddress OBJECT-TYPE 
    SYNTAX      IpAddress
    MAX-ACCESS  read-write
    STATUS      current
    DESCRIPTION
        ""
    ::= { bgs10NMSServerEntry 2}
bgs10NMSServersnmpversion OBJECT-TYPE 
    SYNTAX      UChar
    MAX-ACCESS  read-write
    STATUS      current
    DESCRIPTION
        ""
    ::= { bgs10NMSServerEntry 3}







--The Supplyment for M4 NE.
bgs10MIBObjects         OBJECT IDENTIFIER   ::= { zxbgs10mib 2}

bgs10MIBPortPerformanceTime OBJECT-TYPE 
    SYNTAX      Unsigned32
    MAX-ACCESS  read-write
    STATUS      current
    DESCRIPTION
        "The network element'port porformance's time.It is a supplyment to M4."
    ::= { bgs10MIBObjects 1}
    
bgs10MIBUpcPerformanceTime  OBJECT-TYPE 
    SYNTAX      Unsigned32
    MAX-ACCESS  read-write
    STATUS      current
    DESCRIPTION
        "The network element's UPC porformance's time.It is a supplyment to M4."
    ::= { bgs10MIBObjects 2}

bgs10MIBSVCViewPerformanceTime  OBJECT-TYPE 
    SYNTAX      Unsigned32
    MAX-ACCESS  read-write
    STATUS      current
    DESCRIPTION
        "The network element's SVC view porformance's time.It is a supplyment to M4."
    ::= { bgs10MIBObjects 3}
    
bgs10MIBSpecialMMLFlag  OBJECT-TYPE 
    SYNTAX      UChar
    MAX-ACCESS  read-write
    STATUS      current
    DESCRIPTION
        "The special man-machine command's flag."
    ::= { bgs10MIBObjects 4}
    
bgs10MIBClockBench8KHZ1Port OBJECT-TYPE 
    SYNTAX      UShort
    MAX-ACCESS  read-write
    STATUS      current
    DESCRIPTION
        "The port number of No.1 Clock bench 8-KHz."
    ::= { bgs10MIBObjects 5}

bgs10MIBClockBench8KHZ2Port OBJECT-TYPE 
    SYNTAX      UShort
    MAX-ACCESS  read-write
    STATUS      current
    DESCRIPTION
        "The port number of No.2 Clock bench 8-KHz."
    ::= { bgs10MIBObjects 6}
    
bgs10MIBAbsoluteDate    OBJECT-TYPE 
    SYNTAX      Unsigned32
    MAX-ACCESS  read-write
    STATUS      current
    DESCRIPTION
        "The NE's Absolute Date."
    ::= { bgs10MIBObjects 7}
        
bgs10MIBAbsoluteTime    OBJECT-TYPE 
    SYNTAX      Unsigned32
    MAX-ACCESS  read-write
    STATUS      current
    DESCRIPTION
        "The NE's Absolute Time."
    ::= { bgs10MIBObjects 8}
    
bgs10MIBMemoryStore     OBJECT-TYPE 
    SYNTAX      OCTET STRING(SIZE(40))
    MAX-ACCESS  read-write
    STATUS      current
    DESCRIPTION
        "."
    ::= { bgs10MIBObjects 9}
    
bgs10MIBClockBench19MHZPort OBJECT-TYPE 
    SYNTAX      UShort
    MAX-ACCESS  read-write
    STATUS      current
    DESCRIPTION
        "."
    ::= { bgs10MIBObjects 10}
    
bgs10MIBMemoryLoad      OBJECT-TYPE 
    SYNTAX      OCTET STRING(SIZE(40))
    MAX-ACCESS  read-write
    STATUS      current
    DESCRIPTION
        "."
    ::= { bgs10MIBObjects 11}

bgs10MIBwIfindex        OBJECT-TYPE 
    SYNTAX      UShort
    MAX-ACCESS  read-write
    STATUS      current
    DESCRIPTION
        "."
    ::= { bgs10MIBObjects 12}

bgs10MIBILMISwitch      OBJECT-TYPE 
    SYNTAX      UCHAR
    MAX-ACCESS  read-write
    STATUS      current
    DESCRIPTION
        "."
    ::= { bgs10MIBObjects 13}
cliCommandSwitch        OBJECT-TYPE 
    SYNTAX      UCHAR
    MAX-ACCESS  read-write
    STATUS      current
    DESCRIPTION
        "."
    ::= { bgs10MIBObjects 14}




--The Route Group       
bgs10RouteMIB           OBJECT IDENTIFIER   ::= { zxbgs10mib 3}
    
-- Defintion of objects for route set table.
    
bgs10RouteTable OBJECT-TYPE
    SYNTAX      SEQUENCE OF BGS10RouteEntry
    MAX-ACCESS  not-accessible
    STATUS      current
    DESCRIPTION
        "A list of the route information."
    ::= { bgs10RouteMIB 1}
        
bgs10RouteEntry OBJECT-TYPE
    SYNTAX      BGS10RouteEntry
    MAX-ACCESS  not-accessible
    STATUS      current
    DESCRIPTION
        "An entry to the table."
    INDEX   { bgs10RouteAtmAddress }
    ::= { bgs10RouteTable 1}
        
BGS10RouteEntry ::=
    SEQUENCE {
        bgs10RouteRowStatus         INTEGER,
        bgs10RouteAtmAddressStatus  INTEGER,
        bgs10RouteOperateStatus     INTEGER,
        bgs10RouteNodeNum           UChar,
        bgs10RouteAtmAddress        OCTET STRING,
        bgs10RouteServiceType       INTEGER,
        bgs10RouteRouteSet          UShort,
        bgs10RouteModule            UChar,
        bgs10RouteLength            UChar,
        bgs10RouteServicePID        OCTET STRING(SIZE(4)),
        bgs10RouteDefaultAddrFlag   INTEGER,
        bgs10RouteAddressPlan       INTEGER,
        bgs10RouteAlternateRouteDirect UShort,
        bgs10RouteAlternateRouteTwo UShort,
        bgs10RouteAlternateRouteThree UShort,
        bgs10RouteCurRouteSet       UShort,
        bgs10RouteRouteDirect       UShort,
        bgs10RouteRouteTwo          UShort,
        bgs10RouteRouteThree        UShort
        }
    
bgs10RouteRowStatus OBJECT-TYPE
    SYNTAX      INTEGER
    MAX-ACCESS  read-create
    STATUS      current
    DESCRIPTION 
        "the conteptual row."
    ::= { bgs10RouteEntry 1}
        
bgs10RouteAtmAddressStatus      OBJECT-TYPE
    SYNTAX      INTEGER
    MAX-ACCESS  read-create
    STATUS      current
    DESCRIPTION
        "the status of the ATM address: 0--IISP configure address,1--ILMI."
    ::= { bgs10RouteEntry 2}
        
bgs10RouteOperateStatus     OBJECT-TYPE
    SYNTAX      INTEGER {   up(0),
                            down(1)
                        }
    MAX-ACCESS  read-create
    STATUS      current
    DESCRIPTION
        "the node operate status."
    ::= { bgs10RouteEntry 3}
    
bgs10RouteNodeNum       OBJECT-TYPE
    SYNTAX      UChar
    MAX-ACCESS  read-create
    STATUS      current
    DESCRIPTION
        "the Node Number."
    ::= { bgs10RouteEntry 4}
    
bgs10RouteAtmAddress        OBJECT-TYPE
    SYNTAX      OCTET STRING(SIZE(20))
    MAX-ACCESS  read-create
    STATUS      current
    DESCRIPTION
        "the ATM address."
    ::= { bgs10RouteEntry 5}
    
bgs10RouteServiceType       OBJECT-TYPE
    SYNTAX      INTEGER
    MAX-ACCESS  read-create
    STATUS      current
    DESCRIPTION
        "Route No.4."
    ::= { bgs10RouteEntry 6}    
        
bgs10RouteRouteSet      OBJECT-TYPE
    SYNTAX      UShort
    MAX-ACCESS  read-create
    STATUS      current
    DESCRIPTION
        "RouteSet."
    ::= { bgs10RouteEntry 7}

bgs10RouteModule        OBJECT-TYPE
    SYNTAX      UChar
    MAX-ACCESS  read-create
    STATUS      current
    DESCRIPTION
        "Module No.."
    ::= { bgs10RouteEntry 8}
    
bgs10RouteLength        OBJECT-TYPE
    SYNTAX      UChar
    MAX-ACCESS  read-create
    STATUS      current
    DESCRIPTION
        "route's length."
    ::= { bgs10RouteEntry 9}
    
bgs10RouteServicePID    OBJECT-TYPE
    SYNTAX      OCTET STRING(SIZE(4))
    MAX-ACCESS  read-create
    STATUS      current
    DESCRIPTION
        "Service's PID."
    ::= { bgs10RouteEntry 10}
    
bgs10RouteDefaultAddrFlag       OBJECT-TYPE
    SYNTAX      INTEGER{ default(0),
                         no-default(1)
                       }
    MAX-ACCESS  read-create
    STATUS      current
    DESCRIPTION
        "Address's default flag."
    ::= { bgs10RouteEntry 11}
    
bgs10RouteAddressPlan   OBJECT-TYPE
    SYNTAX      INTEGER{ unknown(0),
                         isdn(1),
                         nsap(2),
                         private(9),
                         reversed(15)
                       }
    MAX-ACCESS  read-create
    STATUS      current
    DESCRIPTION
        "Address's default flag."
    ::= { bgs10RouteEntry 12}
    
bgs10RouteAlternateRouteDirect      OBJECT-TYPE
    SYNTAX      UShort
    MAX-ACCESS  read-create
    STATUS      current
    DESCRIPTION
            "alternate_route_direct."
    ::= { bgs10RouteEntry 13}
    
bgs10RouteAlternateRouteTwo         OBJECT-TYPE
    SYNTAX      UShort
    MAX-ACCESS  read-create
    STATUS      current
    DESCRIPTION
            "alternate_route_two."
    ::= { bgs10RouteEntry 14}

bgs10RouteAlternateRouteThree       OBJECT-TYPE
    SYNTAX      UShort
    MAX-ACCESS  read-create
    STATUS      current
    DESCRIPTION
            "alternate_route_three."
    ::= { bgs10RouteEntry 15}
    
bgs10RouteCurRouteSet              OBJECT-TYPE
    SYNTAX      UShort
    MAX-ACCESS  read-create
    STATUS      current
    DESCRIPTION
            "CurRouteSet."
    ::= { bgs10RouteEntry 16}
    
bgs10RouteRouteDirect       OBJECT-TYPE
    SYNTAX      UShort
    MAX-ACCESS  read-create
    STATUS      current
    DESCRIPTION
            "route_direct."
    ::= { bgs10RouteEntry 17}
    
bgs10RouteRouteTwo      OBJECT-TYPE
    SYNTAX      UShort
    MAX-ACCESS  read-create
    STATUS      current
    DESCRIPTION
            "route_two."
    ::= { bgs10RouteEntry 18}
    
bgs10RouteRouteThree        OBJECT-TYPE
    SYNTAX      UShort
    MAX-ACCESS  read-create
    STATUS      current
    DESCRIPTION
            "route_three."
    ::= { bgs10RouteEntry 19}   







--  zxDslamTrafficGradeParamTable
zxDslamTrafficGradeParamTable    OBJECT-TYPE
        SYNTAX SEQUENCE OF ZxDslamTrafficGradeParamEntry
        MAX-ACCESS      not-accessible
        STATUS          current
        DESCRIPTION
         ""
     ::= { zxDslam 8 }

zxDslamTrafficGradeParamEntry  OBJECT-TYPE
       SYNTAX      ZxDslamTrafficGradeParamEntry
       MAX-ACCESS  not-accessible
       STATUS      current
       DESCRIPTION
               ""
      INDEX           {  zxDslamTrafficGradeParamRowStatus    }
     ::= { zxDslamTrafficGradeParamTable 1 }
       
ZxDslamTrafficGradeParamEntry ::=
          SEQUENCE {
            zxDslamTrafficGradeParamRowStatus       UChar,
            zxDslamTrafficGradeParamIngRate         Unsigned32,
            zxDslamTrafficGradeParamEgRate          Unsigned32
          }
     
zxDslamTrafficGradeParamRowStatus   OBJECT-TYPE
         SYNTAX   UChar
         MAX-ACCESS  read-write
         STATUS      current
         DESCRIPTION
               "" 
     ::= { zxDslamTrafficGradeParamEntry 1 }       
zxDslamTrafficGradeParamIngRate   OBJECT-TYPE
         SYNTAX   Unsigned32
         MAX-ACCESS  read-write
         STATUS      current
         DESCRIPTION
               "" 
     ::= { zxDslamTrafficGradeParamEntry 2 }       
zxDslamTrafficGradeParamEgRate   OBJECT-TYPE
         SYNTAX   Unsigned32
         MAX-ACCESS  read-write
         STATUS      current
         DESCRIPTION
               "" 
     ::= { zxDslamTrafficGradeParamEntry 3 }       

 zxDslamatmfAtmServiceTypeTable   OBJECT-TYPE
    SYNTAX SEQUENCE OF ZxDslamatmfAtmServiceTypeEntry
    MAX-ACCESS not-accessible
    STATUS current
    DESCRIPTION
    "The ATM Forum ILMI Auto Configuration Extension ATM
    Service Type Information. "
    ::= { zxDslam 9  }
 
 zxDslamatmfAtmServiceTypeEntry OBJECT-TYPE
    SYNTAX ZxDslamatmfAtmServiceTypeEntry
    MAX-ACCESS not-accessible
    STATUS current
    DESCRIPTION
    "An entry in the service type table describes the reference
    information about a service that may be associated with
    individual ATM connections for the purpose of auto-
    configuration. This information describe the name and sub-
    name of the service, the client layer protocol using the ATM
    service, the TM 4.0 service category, and the TM 4.0
    conformance definition."
    INDEX { ifIndex }
--     AUGMENTS { atmfAtmServiceTypeEntry   }
    ::= { zxDslamatmfAtmServiceTypeTable 1 }
        
 ZxDslamatmfAtmServiceTypeEntry ::= SEQUENCE {
    atmfAtmServiceTypeRowStatus     UCHAR
    }
 
 atmfAtmServiceTypeRowStatus OBJECT-TYPE
    SYNTAX UCHAR
    MAX-ACCESS read-only
    STATUS current
    DESCRIPTION  " "
    ::= { zxDslamatmfAtmServiceTypeEntry  1 }
 
    
 zxDslamatmfAtmServiceConnInfoTable  OBJECT-TYPE
    SYNTAX SEQUENCE OF ZxDslamatmfAtmServiceConnInfoEntry
    MAX-ACCESS not-accessible
    STATUS current
    DESCRIPTION
    "The ATM Forum ILMI Auto Configuration Extension ATM
    Service Connection Information. "
    ::= { zxDslam 10 }
    
 zxDslamatmfAtmServiceConnInfoEntry OBJECT-TYPE
    SYNTAX ZxDslamatmfAtmServiceConnInfoEntry 
    MAX-ACCESS not-accessible
    STATUS current
    DESCRIPTION
    "An entry in the service connection information table
    describes the ATM connection that provides a service across
    an ATM interface. The connection is identified by port and
    VPI/VCI value. Information about the connection includes the
    connection type (VP or VC, SVC or PVC), and the association of
    the connection with a service type. Specific connection
    information, such as traffic descriptors, should be accessed
    in the atmfVpc and atmfVcc tables defined in ILMI. "
 -- INDEX { atmfAtmServicePortIndex, atmfAtmServiceVpi,atmfAtmServiceVci}
    INDEX { ifIndex }
   
--     AUGMENTS { atmfAtmServiceConnInfoEntry   }
    ::= { zxDslamatmfAtmServiceConnInfoTable  1 }
 
 ZxDslamatmfAtmServiceConnInfoEntry ::= SEQUENCE {
    atmfAtmServiceRowStatus     UCHAR
    }
    
 atmfAtmServiceRowStatus OBJECT-TYPE
    SYNTAX UCHAR
    MAX-ACCESS read-only
    STATUS current
    DESCRIPTION
    "The value of 0 (zero)has the special meaning of identifying
    the ATM Interface over which this ILMI message was received. "
    ::= { zxDslamatmfAtmServiceConnInfoEntry 1 }    
 
 zxDslamatmfAAL1ProfileTable OBJECT-TYPE
    SYNTAX SEQUENCE OF ZxDslamatmfAAL1ProfileEntry
    MAX-ACCESS not-accessible
    STATUS current
    DESCRIPTION
    "The ATM Forum ILMI Auto Configuration Extension AAL1
    Profile Information. "
    ::= { zxDslam 11}
    
 zxDslamatmfAAL1ProfileEntry OBJECT-TYPE
    SYNTAX ZxDslamatmfAAL1ProfileEntry
    MAX-ACCESS not-accessible
    STATUS current
    DESCRIPTION
    "An entry in the AAL1 Profile table provides data that
    describes the AAL1 processing function. "
 
--     AUGMENTS { atmfAAL1ProfileEntry  }
    INDEX { ifIndex }
     
    -- INDEX { atmfAAL1ProfileIndex }
    ::= { zxDslamatmfAAL1ProfileTable 1 }
 
 ZxDslamatmfAAL1ProfileEntry ::= SEQUENCE {
    atmfAAL1RowStatus   UCHAR
    }
 
 atmfAAL1RowStatus OBJECT-TYPE
    SYNTAX UCHAR
    MAX-ACCESS read-only
    STATUS current
    DESCRIPTION
    "A number between which identifies the entry in the AAL1
    Profile Table. "
    ::= { zxDslamatmfAAL1ProfileEntry 1 }
 
 --zxDslamatmfAAL34ProfileTable
 zxDslamatmfAAL34ProfileTable OBJECT-TYPE
    SYNTAX SEQUENCE OF ZxDslamatmfAAL34ProfileEntry
    MAX-ACCESS not-accessible
    STATUS current
    DESCRIPTION
    "The ATM Forum ILMI Auto Configuration Extension AAL3/4
    Profile Information. "
    ::= {zxDslam 12 }
    
 zxDslamatmfAAL34ProfileEntry OBJECT-TYPE
    SYNTAX ZxDslamatmfAAL34ProfileEntry
    MAX-ACCESS not-accessible
    STATUS current
    DESCRIPTION
    "An entry in the AAL34 Profile table provides data that
    describes the AAL3/4 processing function. "
 -- INDEX { atmfAAL34ProfileIndex }
--     AUGMENTS { atmfAAL34ProfileEntry }
    INDEX { ifIndex }

    ::= { zxDslamatmfAAL34ProfileTable 1 }
    
 ZxDslamatmfAAL34ProfileEntry ::= SEQUENCE {
    atmfAAL34RowStatus      UCHAR
    }
    
 atmfAAL34RowStatus  OBJECT-TYPE
    SYNTAX UCHAR
    MAX-ACCESS read-only
    STATUS current
    DESCRIPTION
    "A number between which identifies the entry in the AAL3/4
    Profile Table. "
    ::= { zxDslamatmfAAL34ProfileEntry 1 }
 
 zxDslamatmfAAL5ProfileTable OBJECT-TYPE
    SYNTAX SEQUENCE OF ZxDslamatmfAAL5ProfileEntry
    MAX-ACCESS not-accessible
    STATUS current
    DESCRIPTION
    "The ATM Forum ILMI Auto Configuration Extension AAL5
    Profile Information. "
    ::= { zxDslam 13 }
    
 zxDslamatmfAAL5ProfileEntry OBJECT-TYPE
    SYNTAX ZxDslamatmfAAL5ProfileEntry
    MAX-ACCESS not-accessible
    STATUS current
    DESCRIPTION
    "An entry in the AAL5 Profile table provides data that
    describes the AAL5 processing function. "
 -- INDEX { atmfAAL5ProfileIndex }
--     AUGMENTS { atmfAAL5ProfileEntry  }
    INDEX { ifIndex }
    ::= { zxDslamatmfAAL5ProfileTable 1 }
    
 ZxDslamatmfAAL5ProfileEntry ::= SEQUENCE {
    atmfAAL5RowStatus       UCHAR,
    atmfAAL5ProfileName     DisplayString
    }
    
 atmfAAL5RowStatus OBJECT-TYPE
    SYNTAX  UCHAR
    MAX-ACCESS read-only
    STATUS current
    DESCRIPTION
    " "
    ::= { zxDslamatmfAAL5ProfileEntry 1 }
 
 atmfAAL5ProfileName OBJECT-TYPE
     SYNTAX DisplayString (SIZE (1..33))
     MAX-ACCESS read-write
     STATUS current
     DESCRIPTION
         "
          The AAL5 Profile Name."
 ::= { zxDslamatmfAAL5ProfileEntry 2 }
 
 
 

zxDslamatmfAAL2ProfileTable OBJECT-TYPE
    SYNTAX SEQUENCE OF ZxDslamatmfAAL2ProfileEntry
    MAX-ACCESS not-accessible
    STATUS current
    DESCRIPTION
    "The ATM Forum ILMI Auto Configuration Extension AAL5
    Profile Information. "
    ::= { zxDslam 14 }
    
zxDslamatmfAAL2ProfileEntry OBJECT-TYPE
    SYNTAX ZxDslamatmfAAL2ProfileEntry
    MAX-ACCESS not-accessible
    STATUS current
    DESCRIPTION
    "An entry in the AAL2 Profile table provides data that
    describes the AAL2 processing function. "
    INDEX { ifIndex }
    ::= { zxDslamatmfAAL2ProfileTable 1 }
    
ZxDslamatmfAAL2ProfileEntry ::= SEQUENCE {
    atmfAAL2RowStatus       UCHAR
    }
    
atmfAAL2RowStatus OBJECT-TYPE
    SYNTAX  UCHAR
    MAX-ACCESS read-only
    STATUS current
    DESCRIPTION
    " "
    ::= { zxDslamatmfAAL2ProfileEntry 1 }



-- Dslam APS Mgmt Obj

zxDslamAPSLogicPortTable OBJECT-TYPE
    SYNTAX SEQUENCE OF ZxDslamAPSLogicPortEntry
    MAX-ACCESS not-accessible
    STATUS current
    DESCRIPTION
    "The APS 1+1 logic  port Information. "
    ::= { zxDslam 15 }
    
zxDslamAPSLogicPortEntry OBJECT-TYPE
    SYNTAX ZxDslamAPSLogicPortEntry
    MAX-ACCESS not-accessible
    STATUS current
    DESCRIPTION
    "An entry in the APS logic port table . "
    INDEX { zxDslamAPSLogicPort }
    ::= { zxDslamAPSLogicPortTable 1 }
    
ZxDslamAPSLogicPortEntry ::= SEQUENCE {
    zxDslamAPSLogicPortRowStatus                UCHAR,     
    zxDslamAPSLogicPort                         UCHAR,
    zxDslamAPSLogicPortSdhApsOptSet             UCHAR,
    zxDslamAPSLogicPortSdhApsLockSet            UCHAR,
    zxDslamAPSLogicPortSdhApsReverSet           UCHAR,
    zxDslamAPSLogicPortSdhApsServiceTransPort   UCHAR,
    zxDslamAPSLogicPortsdThresh                 UCHAR,
    zxDslamAPSLogicPortsfThresh                 UCHAR,
    zxDslamAPSLogicPortholdtime                 UCHAR,
    zxDslamAPSLogicPortSwitchReson              UCHAR,
    zxDslamAPSLogicPortSwitchResult             UCHAR,
    zxDslamAPSLogicPortRecoverTime              UCHAR,
    zxDslamAPSLogicPortSwitchChannel            UCHAR
    
    }                                     

zxDslamAPSLogicPortRowStatus OBJECT-TYPE             
    SYNTAX  UCHAR                         
    MAX-ACCESS read-write                 
    STATUS current                        
    DESCRIPTION
    " "
    ::= { zxDslamAPSLogicPortEntry 1 }  

zxDslamAPSLogicPort OBJECT-TYPE             
    SYNTAX  UCHAR                         
    MAX-ACCESS read-write                 
    STATUS current                        
    DESCRIPTION
    " "
    ::= { zxDslamAPSLogicPortEntry 2 }
                                          
zxDslamAPSLogicPortSdhApsOptSet OBJECT-TYPE             
    SYNTAX  UCHAR                         
    MAX-ACCESS read-write                 
    STATUS current                        
    DESCRIPTION
    " "
    ::= { zxDslamAPSLogicPortEntry 3 }

zxDslamAPSLogicPortSdhApsLockSet OBJECT-TYPE             
    SYNTAX  UCHAR                         
    MAX-ACCESS read-write                 
    STATUS current                        
    DESCRIPTION
    " "
    ::= { zxDslamAPSLogicPortEntry 4 }
    
zxDslamAPSLogicPortSdhApsReverSet OBJECT-TYPE             
    SYNTAX  UCHAR                         
    MAX-ACCESS read-write                 
    STATUS current                        
    DESCRIPTION
    " "
    ::= { zxDslamAPSLogicPortEntry 5 }
    
zxDslamAPSLogicPortSdhApsServiceTransPort OBJECT-TYPE             
    SYNTAX  UCHAR                         
    MAX-ACCESS read-write                 
    STATUS current                        
    DESCRIPTION
    " "
    ::= { zxDslamAPSLogicPortEntry 6 }
    
zxDslamAPSLogicPortsdThresh OBJECT-TYPE             
    SYNTAX  UCHAR                         
    MAX-ACCESS read-write                 
    STATUS current                        
    DESCRIPTION
    " "
    ::= { zxDslamAPSLogicPortEntry 7 }
    
zxDslamAPSLogicPortsfThresh OBJECT-TYPE             
    SYNTAX  UCHAR                         
    MAX-ACCESS read-write                 
    STATUS current                        
    DESCRIPTION
    " "
    ::= { zxDslamAPSLogicPortEntry 8 }
    
zxDslamAPSLogicPortholdtime OBJECT-TYPE             
    SYNTAX  UCHAR                         
    MAX-ACCESS read-write                 
    STATUS current                        
    DESCRIPTION
    " "
    ::= { zxDslamAPSLogicPortEntry 9 }
    
zxDslamAPSLogicPortSwitchReson OBJECT-TYPE             
    SYNTAX  UCHAR                         
    MAX-ACCESS read-write                 
    STATUS current                        
    DESCRIPTION
    " "
    ::= { zxDslamAPSLogicPortEntry 10 }
    
zxDslamAPSLogicPortSwitchResult OBJECT-TYPE             
    SYNTAX  UCHAR                         
    MAX-ACCESS read-write                 
    STATUS current                        
    DESCRIPTION
    " "
    ::= { zxDslamAPSLogicPortEntry 11 }



zxDslamAPSLogicPortRecoverTime OBJECT-TYPE             
    SYNTAX  UCHAR                         
    MAX-ACCESS read-write                 
    STATUS current                        
    DESCRIPTION
    " "
    ::= { zxDslamAPSLogicPortEntry 12 }

zxDslamAPSLogicPortSwitchChannel OBJECT-TYPE             
    SYNTAX  UCHAR                         
    MAX-ACCESS read-write                 
    STATUS current                        
    DESCRIPTION
    " 0:switch to working port; 1:switch to standby port "
    ::= { zxDslamAPSLogicPortEntry 13 }



    
--system configuration
bgs10SystemConfigure        OBJECT IDENTIFIER   ::= { zxbgs10mib 1} 
bgs10MyConfigure            OBJECT IDENTIFIER ::= { bgs10SystemConfigure 1}

bgs10MyConfigureOfficType OBJECT-TYPE
    SYNTAX      INTEGER {   otHost(1),
                            otSwitch(2),
                            otDevice(3)}
    MAX-ACCESS  read-only
    STATUS      current
    DESCRIPTION
        "The type of switcher.according to the location,capability,
        the ZXBS10 ATM switcher are distinguished into three types:
        ----otHost:backbone ATM Switcher
        ----otSwitch;edge ATM Switcher
        ----otDevice:access ATM Switcher."
    ::= { bgs10MyConfigure 1 }
    
bgs10MyConfigureNetPrefix   OBJECT-TYPE
    SYNTAX      OCTET STRING(SIZE(13))
    MAX-ACCESS  read-only
    STATUS      current
    DESCRIPTION
        "Network prefix."
    ::= { bgs10MyConfigure 2 }
        
bgs10MyConfigureNet OBJECT-TYPE
    SYNTAX      INTEGER{ pstn(1),
                         rwtn(2),
                         nftn(3),
                         eptn(4),
                         cltn(5),
                         plmn(6)}
    MAX-ACCESS  read-only
    STATUS      current
    DESCRIPTION
        "the type of the switcher in which the ATM Switcher is located
        notmally the network types are:
        ----PSTN:public switching telephone network
        ----RWTN:railway telephone network
        ----NFTN:national defence telephone network
        ----EPTN:electrical power telephone network
        ----CLTN:coal telephone network
        ----PLMN:public land mobile network"
    ::= { bgs10MyConfigure 3 }
        
bgs10MyConfigureCacArithmetic OBJECT-TYPE
    SYNTAX      INTEGER{pcr(1),add(2)}
    MAX-ACCESS  read-only
    STATUS      current
    DESCRIPTION
        "the choice of CAC arithmetic."
    ::= { bgs10MyConfigure 4 }
        
bgs10MyConfigureFeeIntevalTime  OBJECT-TYPE
    SYNTAX      INTEGER
    MAX-ACCESS  read-write
    STATUS      current
    DESCRIPTION
        "the Interval for PVC/PVP connection accounting.according to 
        the standard comment of Information Industrial Minstry,It 
        should not be beyond 24 hours.
        Here it demands the unit be hours."
    ::= { bgs10MyConfigure 5 }
    
bgs10MyConfigureAlarmNo OBJECT-TYPE
    SYNTAX      INTEGER
    MAX-ACCESS  read-write
    STATUS      current
    DESCRIPTION
        "The no of the Current Alarm"
    ::= { bgs10MyConfigure 6 }

bgs10MyConfigureLoopBackID  OBJECT-TYPE
    SYNTAX      OCTET STRING(SIZE(16))
    MAX-ACCESS  read-write
    STATUS      current
    DESCRIPTION
        "LoopbackID "
    ::= { bgs10MyConfigure 7 }

bgs10MyConfigureInBandMACAddress    OBJECT-TYPE
    SYNTAX      MacAddress
    MAX-ACCESS  read-write
    STATUS      current
    DESCRIPTION
        "LoopbackID "
    ::= { bgs10MyConfigure 8 }

bgs10MyConfigureOutBandMACAddress   OBJECT-TYPE
    SYNTAX      MacAddress
    MAX-ACCESS  read-write
    STATUS      current
    DESCRIPTION
        "LoopbackID "
    ::= { bgs10MyConfigure 9 }

bgs10MyConfigureMasterCoreSlot  OBJECT-TYPE
    SYNTAX      INTEGER
    MAX-ACCESS  read-write
    STATUS      current
    DESCRIPTION
        "LoopbackID "
    ::= { bgs10MyConfigure 10 }





--The Traps for ZXB10 and its successors.
          
--The phyical Hardware Unit Alarm
                                
--The Alarms of the power Board of 25-G and 5-G ATM switchers quotes
--ATM FORUM af-nm-0095.001:'atmM4HwFanFailAlarm'(atmfM4MIBTrapPrefix.41)
                
--The Alarm of power voltage (+5,-48)of 25-G and 5-G ATM switchers
--referenced ATM FORUM af-nm-0095.001:'atmfM4HwPowerAlarm'(
--atmfM4MIBTrapPrefix.25).the folowing are the supplyment to it.

zxbgs10PowerBoardTrap           OBJECT IDENTIFIER       ::= { zxbgs10Traps 1 }
zxbgs10PowerBoardTrapPrefix     OBJECT IDENTIFIER       ::= { zxbgs10PowerBoardTrap 0 }
        
bgs10PowerChannel1V5Alarm       NOTIFICATION-TYPE
        OBJECTS {       atmfM4PlugInUnitOperStatus,
                                atmfM4TrapAlarmSeverity
                        }
        STATUS  current
        DESCRIPTION
                "indicates the Alarm of +5 power at Channel No.1."
        ::= { zxbgs10PowerBoardTrapPrefix 1 }

bgs10PowerChannel1V3Alarm NOTIFICATION-TYPE
        OBJECTS {       atmfM4PlugInUnitOperStatus,
                                atmfM4TrapAlarmSeverity
                        }
        STATUS  current
        DESCRIPTION
                "indicaes the Alarm of V3.3 power at Channel No.1."
        ::= { zxbgs10PowerBoardTrapPrefix 2 }
        
bgs10PowerChannel2V5Alarm       NOTIFICATION-TYPE
        OBJECTS {       atmfM4PlugInUnitOperStatus,
                                atmfM4TrapAlarmSeverity
                        }
        STATUS  current
        DESCRIPTION
                "indicates the Alarm of +5 power at Channel No.2."
        ::= { zxbgs10PowerBoardTrapPrefix 3 }

bgs10PowerChannel2V3Alarm NOTIFICATION-TYPE
        OBJECTS {       atmfM4PlugInUnitOperStatus,
                                atmfM4TrapAlarmSeverity
                        }
        STATUS  current
        DESCRIPTION
                "indicaes the Alarm of V3.3 power at Channel No.2."
        ::= { zxbgs10PowerBoardTrapPrefix 4 }
        
bgs10PowerChannel3V5Alarm       NOTIFICATION-TYPE
        OBJECTS {       atmfM4PlugInUnitOperStatus,
                                atmfM4TrapAlarmSeverity
                        }
        STATUS  current
        DESCRIPTION
                "indicates the Alarm of +5 power at Channel No.3."
        ::= { zxbgs10PowerBoardTrapPrefix 5 }

bgs10PowerChannel3V3Alarm NOTIFICATION-TYPE
        OBJECTS {       atmfM4PlugInUnitOperStatus,
                                atmfM4TrapAlarmSeverity
                        }
        STATUS  current
        DESCRIPTION
                "indicaes the Alarm of V3.3 power at Channel No.3."
        ::= { zxbgs10PowerBoardTrapPrefix 6 }
        
bgs10PowerChannel4V5Alarm       NOTIFICATION-TYPE
        OBJECTS {       atmfM4PlugInUnitOperStatus,
                                atmfM4TrapAlarmSeverity
                        }
        STATUS  current
        DESCRIPTION
                "indicates the Alarm of +5 power at Channel No.4."
        ::= { zxbgs10PowerBoardTrapPrefix 7 }

bgs10PowerChannel4V3Alarm NOTIFICATION-TYPE
        OBJECTS {       atmfM4PlugInUnitOperStatus,
                                atmfM4TrapAlarmSeverity
                        }
        STATUS  current
        DESCRIPTION
                "indicaes the Alarm of V3.3 power at Channel No.4."
        ::= { zxbgs10PowerBoardTrapPrefix 8 }
        
bgs10PowerChannel1OfflineAlarm NOTIFICATION-TYPE
        OBJECTS {       atmfM4PlugInUnitOperStatus,
                                atmfM4TrapAlarmSeverity
                        }
        STATUS  current
        DESCRIPTION
                "indicaes the off-line Alarm of Channel No.1."
        ::= { zxbgs10PowerBoardTrapPrefix 9 }
                
bgs10PowerChannel2OfflineAlarm NOTIFICATION-TYPE
        OBJECTS {       atmfM4PlugInUnitOperStatus,
                                atmfM4TrapAlarmSeverity
                        }
        STATUS  current
        DESCRIPTION
                "indicaes the off-line Alarm of Channel No.2."
        ::= { zxbgs10PowerBoardTrapPrefix 10 }
        
bgs10PowerChannel3OfflineAlarm NOTIFICATION-TYPE
        OBJECTS {       atmfM4PlugInUnitOperStatus,
                                atmfM4TrapAlarmSeverity
                        }
        STATUS  current
        DESCRIPTION
                "indicaes the off-line Alarm of Channel No.3."
        ::= { zxbgs10PowerBoardTrapPrefix 11 }
        
bgs10PowerChannel4OfflineAlarm NOTIFICATION-TYPE
        OBJECTS {       atmfM4PlugInUnitOperStatus,
                                atmfM4TrapAlarmSeverity
                        }
        STATUS  current
        DESCRIPTION
                "indicaes the off-line Alarm of Channel No.4."
        ::= { zxbgs10PowerBoardTrapPrefix 12 }


        
--The Alarm of Clock board references ATM FORUM af-nm-0095.001:
--atmfM4HwTimingProbAlarm .and the following  is that ZXB10 system 
--supplies the Alarm to it.

bgs10ClkBoardTrap               OBJECT IDENTIFIER       ::= { zxbgs10Traps 2 }
bgs10ClkBoardTrapPrefix OBJECT IDENTIFIER       ::= { bgs10ClkBoardTrap 0}

bgs10ClkChannel1BenchAlarm NOTIFICATION-TYPE
        OBJECTS {       entPhysicalContainedIn,
                                entPhysicalParentRelPos,
                                entPhysicalClass,
                                atmfM4TrapAlarmSeverity
                        }
        STATUS  current
        DESCRIPTION
                "Indicates the Alarm of clock board's Channel No.1."
        ::= { bgs10ClkBoardTrapPrefix 1 } 

bgs10ClkChannel2BenchAlarm NOTIFICATION-TYPE
        OBJECTS {       entPhysicalContainedIn,
                                entPhysicalParentRelPos,
                                entPhysicalClass,
                                atmfM4TrapAlarmSeverity
                        }
        STATUS  current
        DESCRIPTION
                "Indicates the Alarm of clock board's Channel No.2."
        ::= { bgs10ClkBoardTrapPrefix 2 } 
        
bgs10ClkChannel3BenchAlarm NOTIFICATION-TYPE
        OBJECTS {       entPhysicalContainedIn,
                                entPhysicalParentRelPos,
                                entPhysicalClass,
                                atmfM4TrapAlarmSeverity
                        }
        STATUS  current
        DESCRIPTION
                "Indicates the Alarm of clock board's Channel No.3."
        ::= { bgs10ClkBoardTrapPrefix 3 } 
        
bgs10ClkChannel4BenchAlarm NOTIFICATION-TYPE
        OBJECTS {       entPhysicalContainedIn,
                                entPhysicalParentRelPos,
                                entPhysicalClass,
                                atmfM4TrapAlarmSeverity
                        }
        STATUS  current
        DESCRIPTION
                "Indicates the Alarm of clock board's Channel No.4."
        ::= { bgs10ClkBoardTrapPrefix 4 } 
        
bgs10ClkChannel5BenchAlarm NOTIFICATION-TYPE
        OBJECTS {       entPhysicalContainedIn,
                                entPhysicalParentRelPos,
                                entPhysicalClass,
                                atmfM4TrapAlarmSeverity
                        }
        STATUS  current
        DESCRIPTION
                "Indicates the Alarm of clock board's Channel No.5."
        ::= {   bgs10ClkBoardTrapPrefix 5 } 
        
bgs10ClkChannel6BenchAlarm NOTIFICATION-TYPE
        OBJECTS {       entPhysicalContainedIn,
                                entPhysicalParentRelPos,
                                entPhysicalClass,
                                atmfM4TrapAlarmSeverity
                        }
        STATUS  current
        DESCRIPTION
                "Indicates the Alarm of clock board's Channel No.6."
        ::= { bgs10ClkBoardTrapPrefix 6 }
        
bgs10ClkCrystalStopAlarm        NOTIFICATION-TYPE
        OBJECTS {       entPhysicalContainedIn,
                                entPhysicalParentRelPos,
                                entPhysicalClass,
                                atmfM4TrapAlarmSeverity
                        }
        STATUS  current
        DESCRIPTION
                "Indicates that the crystal stop working."
        ::= { bgs10ClkBoardTrapPrefix 7 }
        
bgs10ClkRamBadAlarm     NOTIFICATION-TYPE
        OBJECTS {       entPhysicalContainedIn,
                                entPhysicalParentRelPos,
                                entPhysicalClass,
                                atmfM4TrapAlarmSeverity
                        }
        STATUS  current
        DESCRIPTION
                "Indicates that the ram is bad 
                worse."
        ::= { bgs10ClkBoardTrapPrefix 8 }
        
bgs10ClkChannel1BenchOfflineAlarm       NOTIFICATION-TYPE
        OBJECTS {       entPhysicalContainedIn,
                                entPhysicalParentRelPos,
                                entPhysicalClass,
                                atmfM4TrapAlarmSeverity
                        }
        STATUS  current
        DESCRIPTION
                "Indicates that the bench No.1 of clock board is off-line."
        ::= {   bgs10ClkBoardTrapPrefix 9 } 
        
bgs10ClkChannel2BenchOfflineAlarm       NOTIFICATION-TYPE
        OBJECTS {       entPhysicalContainedIn,
                                entPhysicalParentRelPos,
                                entPhysicalClass,
                                atmfM4TrapAlarmSeverity
                        }
        STATUS  current
        DESCRIPTION
                "Indicates that the bench No.2 of clock board is off-line."
        ::= { bgs10ClkBoardTrapPrefix 10 }
        
bgs10ClkChannel3BenchOfflineAlarm       NOTIFICATION-TYPE
        OBJECTS {       entPhysicalContainedIn,
                                entPhysicalParentRelPos,
                                entPhysicalClass,
                                atmfM4TrapAlarmSeverity
                        }
        STATUS  current
        DESCRIPTION
                "Indicates that the bench No.3 of clock board is off-line."
        ::= { bgs10ClkBoardTrapPrefix 11 }
        
bgs10ClkChannel4BenchOfflineAlarm       NOTIFICATION-TYPE
        OBJECTS {       entPhysicalContainedIn,
                                entPhysicalParentRelPos,
                                entPhysicalClass,
                                atmfM4TrapAlarmSeverity
                        }
        STATUS  current
        DESCRIPTION
                "Indicates that the bench No.4 of clock board is off-line."
        ::= { bgs10ClkBoardTrapPrefix 12 }

bgs10ClkChannel5BenchOfflineAlarm       NOTIFICATION-TYPE
        OBJECTS {       entPhysicalContainedIn,
                                entPhysicalParentRelPos,
                                entPhysicalClass,
                                atmfM4TrapAlarmSeverity
                        }
        STATUS  current
        DESCRIPTION
                "Indicates that the bench No.5 of clock board is off-line."
        ::= {   bgs10ClkBoardTrapPrefix 13 } 
        
bgs10ClkChannel6BenchOfflineAlarm       NOTIFICATION-TYPE
        OBJECTS {       entPhysicalContainedIn,
                                entPhysicalParentRelPos,
                                entPhysicalClass,
                                atmfM4TrapAlarmSeverity
                        }
        STATUS  current
        DESCRIPTION
                "Indicates that the bench No.6 of clock board is off-line."
        ::= { bgs10ClkBoardTrapPrefix 14 }
        
bgs10ClkBoardOnLineStatus       NOTIFICATION-TYPE
        OBJECTS {       bgs10PlugInUnitCardType,
                                atmfM4PlugInUnitAvailStatus,
                                bgs10PlugInUnitMasterStatus
                        }
        STATUS  current
        DESCRIPTION
                "the Clock Card stats's notification ."
        ::= { bgs10ClkBoardTrapPrefix 29 }
        

-- The Alarm of Net board.The following are defined for ZXB10 and its 
--successors.

bgs10NetCardTraps               OBJECT IDENTIFIER       ::= { zxbgs10Traps 3 }
bgs10NetCardTrapsPrefix OBJECT IDENTIFIER       ::= { bgs10NetCardTraps 0}

bgs10NetCardASXIdleAddrCounterZeroAlarm NOTIFICATION-TYPE
        OBJECTS {       entPhysicalContainedIn,
                                entPhysicalParentRelPos,
                                entPhysicalClass,
                                atmfM4TrapAlarmSeverity
                        }
        STATUS  current
        DESCRIPTION
                "Indicates that the idle address counter of the ASX clip becomes 
                zero."
        ::= { bgs10NetCardTrapsPrefix 1 }
        
bgs10NetCardASXLinkListErrAlarm NOTIFICATION-TYPE
        OBJECTS {       entPhysicalContainedIn,
                                entPhysicalParentRelPos,
                                entPhysicalClass,
                                atmfM4TrapAlarmSeverity
                        }
        STATUS  current
        DESCRIPTION
                "Indicates that the LInk list of the ASX clip is wrong."
        ::= { bgs10NetCardTrapsPrefix 2 }
        
bgs10NetCardASXInputClkStatusChangeAlarm        NOTIFICATION-TYPE
        OBJECTS {       entPhysicalContainedIn,
                                entPhysicalParentRelPos,
                                entPhysicalClass,
                                atmfM4TrapAlarmSeverity
                        }
        STATUS  current
        DESCRIPTION
                "Indicates that the status of the input clock of the ASX clip is
                changed."
        ::= { bgs10NetCardTrapsPrefix 3 }
        
bgs10NetCardASXInPortOverSpeedAlarm     NOTIFICATION-TYPE
   OBJECTS      {       entPhysicalContainedIn,
                                entPhysicalParentRelPos,
                                entPhysicalClass,
                                atmfM4TrapAlarmSeverity
                        }
        STATUS  current
        DESCRIPTION
                "Indicates that the inport of the ASX clip is over speed."
        ::= { bgs10NetCardTrapsPrefix 4 }

bgs10NetCardASXCRCCheckErrAlarm NOTIFICATION-TYPE
        OBJECTS {       entPhysicalContainedIn,
                                entPhysicalParentRelPos,
                                entPhysicalClass,
                                atmfM4TrapAlarmSeverity
                        }
        STATUS  current
        DESCRIPTION
                "Indicates that the CRC check occurs error."
        ::= { bgs10NetCardTrapsPrefix 5 }
        
bgs10NetCardASXCheckoutErrAlarm NOTIFICATION-TYPE
        OBJECTS {       entPhysicalContainedIn,
                                entPhysicalParentRelPos,
                                entPhysicalClass,
                                atmfM4TrapAlarmSeverity
                        }
        STATUS  current
        DESCRIPTION
                "Indicates that the ASX clip's chekcout is error."
        ::= { bgs10NetCardTrapsPrefix 6 }

bgs10NetCardACESumErrAlarm      NOTIFICATION-TYPE
        OBJECTS {       entPhysicalContainedIn,
                                entPhysicalParentRelPos,
                                entPhysicalClass,
                                atmfM4TrapAlarmSeverity
                        }
        STATUS  current
        DESCRIPTION
                "Indicates that the ACE clip's sum is error."
        ::= { bgs10NetCardTrapsPrefix 7 }
        
bgs10NetCardACEInputClkStatusChangeAlarm        NOTIFICATION-TYPE
        OBJECTS {       entPhysicalContainedIn,
                                entPhysicalParentRelPos,
                                entPhysicalClass,
                                atmfM4TrapAlarmSeverity
                        }
        STATUS  current
        DESCRIPTION
                "Indicates that the input clock's status of the ACE clip is changed."
        ::= { bgs10NetCardTrapsPrefix 8 }
        
bgs10NetCardACEInPortOverSpeedAlarm     NOTIFICATION-TYPE
        OBJECTS {       entPhysicalContainedIn,
                                entPhysicalParentRelPos,
                                entPhysicalClass,
                                atmfM4TrapAlarmSeverity
                        }
        STATUS  current
        DESCRIPTION
                "indicates that in port of the ACE clip is over speed."
        ::= { bgs10NetCardTrapsPrefix 9 }

bgs10NetCardACECheckErrAlarm    NOTIFICATION-TYPE
        OBJECTS {       entPhysicalContainedIn,
                                entPhysicalParentRelPos,
                                entPhysicalClass,
                                atmfM4TrapAlarmSeverity
                        }
        STATUS  current
        DESCRIPTION
                "Indicates that the ACE clip's check is error."
        ::= { bgs10NetCardTrapsPrefix 10 }

--The Alarm of the Line card.The trap defined in ATM FORUM af-nm-0095.001
--(atmfm4LineCardAlarm:atmfm4MIBTrapPrefix 23) indicates the producing the 
--Alarm line card's position. the following traps are defined for detail 
--descroiption to every trap,and only for ZXB10 and its successors.

bgs10LICTraps           OBJECT IDENTIFIER ::= { zxbgs10Traps 4 }
bgs10LICTrapsPrefix     OBJECT IDENTIFIER ::= { bgs10LICTraps 0 }

bgs10LICECapFSyncErAlarm        NOTIFICATION-TYPE
        OBJECTS {       entPhysicalContainedIn,
                                entPhysicalParentRelPos,
                                entPhysicalClass,
                                atmfM4TrapAlarmSeverity
                        }
        STATUS  current
        DESCRIPTION
                "Indicates that egress captured FIFO cells synchronization error occurrs."
        ::= { bgs10LICTrapsPrefix 1 }
        
bgs10LICICapFSyncErAlarm        NOTIFICATION-TYPE
        OBJECTS {       entPhysicalContainedIn,
                                entPhysicalParentRelPos,
                                entPhysicalClass,
                                atmfM4TrapAlarmSeverity
                        }
        STATUS  current
        DESCRIPTION
                "Indicates that the ingress captured FIFO cells synchronization error occurs."
        ::= { bgs10LICTrapsPrefix 2 }

bgs10LICInsertFSyncErAlarm      NOTIFICATION-TYPE
        OBJECTS {       entPhysicalContainedIn,
                                entPhysicalParentRelPos,
                                entPhysicalClass,
                                atmfM4TrapAlarmSeverity
                        }
        STATUS  current
        DESCRIPTION
                "Indicates that the insert FIFO cells synchronization error occurs."
        ::= { bgs10LICTrapsPrefix 3 }
        
bgs10LICEmipErAlarm     NOTIFICATION-TYPE
        OBJECTS {       entPhysicalContainedIn,
                                entPhysicalParentRelPos,
                                entPhysicalClass,
                                atmfM4TrapAlarmSeverity
                        }
        STATUS  current
        DESCRIPTION
                "Indicates that external memory interface parity error occurs."
        ::= { bgs10LICTrapsPrefix 4 }

bgs10LICIRxPErAlarm     NOTIFICATION-TYPE
        OBJECTS {       entPhysicalContainedIn,
                                entPhysicalParentRelPos,
                                entPhysicalClass,
                                atmfM4TrapAlarmSeverity
                        }
        STATUS  current
        DESCRIPTION
                "Indicates that the ingress parity error on UTOPIA recieve bus error occurs."
        ::= { bgs10LICTrapsPrefix 5 }
        
bgs10LICERxPErAlarm     NOTIFICATION-TYPE
        OBJECTS {       entPhysicalContainedIn,
                                entPhysicalParentRelPos,
                                entPhysicalClass,
                                atmfM4TrapAlarmSeverity
                        }
        STATUS  current
        DESCRIPTION
                "Indicates that the parity error on recieved egress cells error occurs."
        ::= { bgs10LICTrapsPrefix 6 }
        
bgs10LICUSyncErAlarm    NOTIFICATION-TYPE
        OBJECTS {       entPhysicalContainedIn,
                                entPhysicalParentRelPos,
                                entPhysicalClass,
                                atmfM4TrapAlarmSeverity
                        }
        STATUS  current
        DESCRIPTION
                "Indicates that the synchronization error takes place."
        ::= { bgs10LICTrapsPrefix 7 }
        
bgs10LICPETErrAlarm     NOTIFICATION-TYPE
        OBJECTS {       entPhysicalContainedIn,
                                entPhysicalParentRelPos,
                                entPhysicalClass,
                                atmfM4TrapAlarmSeverity
                        }
        STATUS  current
        DESCRIPTION
                "Indicates that the policing E update time out error."
        ::= { bgs10LICTrapsPrefix 8 }

bgs10LICVCISzErAlarm    NOTIFICATION-TYPE
        OBJECTS {       entPhysicalContainedIn,
                                entPhysicalParentRelPos,
                                entPhysicalClass,
                                atmfM4TrapAlarmSeverity
                        }
        STATUS  current
        DESCRIPTION
                "Indicates that the VCI size error occurs."
        ::= { bgs10LICTrapsPrefix 9 }
        
bgs10LICVPISzErAlarm    NOTIFICATION-TYPE
        OBJECTS {       entPhysicalContainedIn,
                                entPhysicalParentRelPos,
                                entPhysicalClass,
                                atmfM4TrapAlarmSeverity
                        }
        STATUS  current
        DESCRIPTION
                "Indicates that the VPI szie error occurs."
        ::= { bgs10LICTrapsPrefix 10 }
        
bgs10LICMPHYOvrnAlarm   NOTIFICATION-TYPE
        OBJECTS {       entPhysicalContainedIn,
                                entPhysicalParentRelPos,
                                entPhysicalClass,
                                atmfM4TrapAlarmSeverity
                        }
        STATUS  current
        DESCRIPTION
                "Indicates that MPHY port overrun condition has occured."
        ::= { bgs10LICTrapsPrefix 11 }
        
bgs10LICInFiFLAlarm     NOTIFICATION-TYPE
        OBJECTS {       entPhysicalContainedIn,
                                entPhysicalParentRelPos,
                                entPhysicalClass,
                                atmfM4TrapAlarmSeverity
                        }
        STATUS  current
        DESCRIPTION
                "Indicates that ingress FIFO full condition takes place."
        ::= { bgs10LICTrapsPrefix 12 }
        
bgs10LICIERRSAlarm      NOTIFICATION-TYPE
        OBJECTS {       entPhysicalContainedIn,
                                entPhysicalParentRelPos,
                                entPhysicalClass,
                                atmfM4TrapAlarmSeverity
                        }
        STATUS  current
        DESCRIPTION
                "Indicates that the sequencing error in ingress linked lists takes place."
        ::= { bgs10LICTrapsPrefix 13 }
        
bgs10LICVERRPAlarm      NOTIFICATION-TYPE
        OBJECTS {       entPhysicalContainedIn,
                                entPhysicalParentRelPos,
                                entPhysicalClass,
                                atmfM4TrapAlarmSeverity
                        }
        STATUS  current
        DESCRIPTION
                "Inidcates that the parity error in incoming egress cell takes place."
        ::= { bgs10LICTrapsPrefix 14 }
        
bgs10LICEsErrAlarm      NOTIFICATION-TYPE
        OBJECTS {       entPhysicalContainedIn,
                                entPhysicalParentRelPos,
                                entPhysicalClass,
                                atmfM4TrapAlarmSeverity
                        }
        STATUS  current
        DESCRIPTION
                "Inidcates that sequencing error in egress linked lists."
        ::= { bgs10LICTrapsPrefix 15 }
        
bgs10LICIpRtyErrAlarm   NOTIFICATION-TYPE
        OBJECTS {       entPhysicalContainedIn,
                                entPhysicalParentRelPos,
                                entPhysicalClass,
                                atmfM4TrapAlarmSeverity
                        }
        STATUS  current
        DESCRIPTION
                "Indicates that parity error in stored ingress cells takes place."
        ::= { bgs10LICTrapsPrefix 16 }
        
bgs10LICEprtyErrAlarm   NOTIFICATION-TYPE
        OBJECTS {       entPhysicalContainedIn,
                                entPhysicalParentRelPos,
                                entPhysicalClass,
                                atmfM4TrapAlarmSeverity
                        }
        STATUS  current
        DESCRIPTION
                "Indicates that parity error in stored egress cells takes palce."
        ::= { bgs10LICTrapsPrefix 17 }
        
bgs10LICIbpOvrExcAlarm  NOTIFICATION-TYPE
        OBJECTS {       entPhysicalContainedIn,
                                entPhysicalParentRelPos,
                                entPhysicalClass,
                                atmfM4TrapAlarmSeverity
                        }
        STATUS  current
        DESCRIPTION
                "Indicates that the backpressure override threshold exceeded takes place."
        ::= { bgs10LICTrapsPrefix 18 }
        
bgs10LICPpErrAlarm      NOTIFICATION-TYPE
        OBJECTS {       entPhysicalContainedIn,
                                entPhysicalParentRelPos,
                                entPhysicalClass,
                                atmfM4TrapAlarmSeverity
                        }
        STATUS  current
        DESCRIPTION
                "Indicates that parity error from pointer RAM has occured."
        ::= { bgs10LICTrapsPrefix 19 }
        
bgs10LICPillErrAlarm    NOTIFICATION-TYPE
        OBJECTS {       entPhysicalContainedIn,
                                entPhysicalParentRelPos,
                                entPhysicalClass,
                                atmfM4TrapAlarmSeverity
                        }
        STATUS  current
        DESCRIPTION
                "Indicates that ingress free list exhaustion error has occured."
        ::= { bgs10LICTrapsPrefix 20 }
        
bgs10LICPellErrAlarm    NOTIFICATION-TYPE
        OBJECTS {       entPhysicalContainedIn,
                                entPhysicalParentRelPos,
                                entPhysicalClass,
                                atmfM4TrapAlarmSeverity
                        }
        STATUS  current
        DESCRIPTION
                "Indicates that egress free list exhaustion error has occrued."
        ::= { bgs10LICTrapsPrefix 21 }
        
bgs10LICPeIpErrAlarm    NOTIFICATION-TYPE
        OBJECTS {       entPhysicalContainedIn,
                                entPhysicalParentRelPos,
                                entPhysicalClass,
                                atmfM4TrapAlarmSeverity
                        }
        STATUS  current
        DESCRIPTION
                "indicates that the egress index pair(IP) free list exhaustion error has 
                occured."
        ::= { bgs10LICTrapsPrefix 22 }

bgs10LICUSyncErrAlarm   NOTIFICATION-TYPE
        OBJECTS {       entPhysicalContainedIn,
                                entPhysicalParentRelPos,
                                entPhysicalClass,
                                atmfM4TrapAlarmSeverity
                        }
        STATUS  current
        DESCRIPTION
                "Indicates that the ingress synchronization error has occured."
        ::= { bgs10LICTrapsPrefix 23 }
        
bgs10LICUegSyncErrPAlarm        NOTIFICATION-TYPE
        OBJECTS {       entPhysicalContainedIn,
                                entPhysicalParentRelPos,
                                entPhysicalClass,
                                atmfM4TrapAlarmSeverity
                        }
        STATUS  current
        DESCRIPTION
                "Indicates that the egress synchronization error has occured."
        ::= { bgs10LICTrapsPrefix 24 }

--The Communication Alarm(SDH)
--The following traps are for ZXB10 and its successors.

bgs10CommSDHTraps                       OBJECT IDENTIFIER ::= { zxbgs10Traps 5 }
bgs10CommSDHTrapsPrefix         OBJECT IDENTIFIER ::= { bgs10CommSDHTraps 0 }

--The LCD Alarm has defined in ATM Forum af-nm-0095.001:atmf4IfLcdAlarm
--(atmfM4MIBTrapPrefix 2 },so it isn't necessary to redefine it.

bgs10CommSDHTroolAlarm  NOTIFICATION-TYPE
        OBJECTS {       ifOperStatus,
                                atmfM4TrapAlarmSeverity
                        }
        STATUS  current
        DESCRIPTION
                "indicates that transmitting reference out of lock(Abbr:TROOL) has
                occurred (PM5346 clip)."
        ::= { bgs10CommSDHTrapsPrefix 1 }
        
bgs10CommSDHRdoolAlarm  NOTIFICATION-TYPE
        OBJECTS {       ifOperStatus,
                                atmfM4TrapAlarmSeverity
                        }
        STATUS  current
        DESCRIPTION
                "Indicates that recieving data out of lock (Abbr:RDOOL) has
                occurred (PM5346 clip)."
        ::= { bgs10CommSDHTrapsPrefix 2 }

bgs10CommSDHOofAlarm            NOTIFICATION-TYPE
        OBJECTS {       ifOperStatus,
                                atmfM4TrapAlarmSeverity
                        }
        STATUS  current
        DESCRIPTION
                "Indicates that an OOFD Alarm condition has occurred(created by 
                PM5346 clip)."
        ::= { bgs10CommSDHTrapsPrefix 3 }

--The LOF Alarm has been defined by ATM Forum af-nm-0095.001:atmfM4LofAlarm
--(atmfM4MIBTrapPrefix 3).Here should not redefine it.
 
--The LOS Alarm has been defined by ATM Forum af-nm-0095.001:atmfM4LosAlarm
--(atmfM4MIBTrapPrefix 5).Here should not redefine it.

--The RDI Alarm has been defined in ATM Forum af-nm-0095.001:atmfM4RdiAlarm
--(atmfM4MIBTrapPrefix 9), Here define two Alarms sbout it: one for line,
--another for path.

bgs10CommSDHLRdiAlarm   NOTIFICATION-TYPE
        OBJECTS {       ifOperStatus,
                                atmfM4TrapAlarmSeverity
                        }
        STATUS  current
        DESCRIPTION
                "Indicates that an line RDI Alarm condition has occurred(created
                by PM5346 clip)."
        ::= { bgs10CommSDHTrapsPrefix 4 }
        
bgs10CommSDHPRdiAlarm   NOTIFICATION-TYPE
        OBJECTS {       ifOperStatus,
                                atmfM4TrapAlarmSeverity
                        }
        STATUS  current
        DESCRIPTION
                "indicates that a path RDT Alarm condition has occurred(created
                by PM5346 clip)."
        ::= { bgs10CommSDHTrapsPrefix 5  }
  
--The AIS Alarm has been defined in ATM Forum af-nm-0095.001:atmfM4AisAlarm
--(atmfM4MIBTrapPrefix 9), Here define two Alarms sbout it: one for line,
--another for path.
bgs10CommSDHLAisAlarm   NOTIFICATION-TYPE
        OBJECTS {       ifOperStatus,
                                atmfM4TrapAlarmSeverity
                        }
        STATUS  current
        DESCRIPTION
                "Indicates that a line Ais Alarm condition has occurred(created 
                by PM5346 clip)."
        ::= { bgs10CommSDHTrapsPrefix 6 }
        
bgs10CommSDHPAisAlarm   NOTIFICATION-TYPE
        OBJECTS {       ifOperStatus,
                                atmfM4TrapAlarmSeverity
                        }
        STATUS  current
        DESCRIPTION
                "Indicates that a path AIS Alarm condition has occurred(created
                by PM5346 clip)."
        ::= { bgs10CommSDHTrapsPrefix 7 }

bgs10CommSDHRroolAlarm  NOTIFICATION-TYPE
        OBJECTS {       ifOperStatus,
                                atmfM4TrapAlarmSeverity
                        }
        STATUS  current
        DESCRIPTION
                "Indicates that the recieving reference clock is out of lock(created
                PM5346)."
        ::= { bgs10CommSDHTrapsPrefix 8 }
        
--the atmfM4IfLopAlarm has defined LOP Alarm in ATM Forum af-nm-0095.001
--So here don't redefine it.

--the ATM Alarm has defined in ATM Forum af-nm-0095.001. So here should not
--redefine them.

        
bgs10Cardtraps                  OBJECT IDENTIFIER       ::= { zxbgs10Traps 8 }
bgs10CardTrapsPrefix    OBJECT IDENTIFIER       ::= { bgs10Cardtraps 0 }

bgs10CardOnLineStatus                   NOTIFICATION-TYPE
        OBJECTS {       bgs10PlugInUnitCardType,
                                atmfM4PlugInUnitAvailStatus,
                                bgs10PlugInUnitMasterStatus
                        }
        STATUS  current
        DESCRIPTION
                "the card stats's notification ."
        ::= { bgs10CardTrapsPrefix 1 }
        
bgs10PerfTraps                  OBJECT IDENTIFIER       ::= { zxbgs10Traps 9 }
bgs10PerfTrapsPrefix    OBJECT IDENTIFIER       ::= { bgs10PerfTraps 0 }

bgs10PerfPortDiscardHECViolCell         NOTIFICATION-TYPE
        OBJECTS {       alarmValue,
                                alarmRisingThreshold,
                                alarmFallingThreshold,
                                atmfM4TrapAlarmSeverity
                        }
        STATUS  current
        DESCRIPTION
                "the discard violate cells ."
        ::= { bgs10PerfTrapsPrefix 1 }
        
bgs10UpcNpcDisagreementCell                             NOTIFICATION-TYPE
        OBJECTS {       alarmValue,
                                alarmRisingThreshold,
                                atmfM4TrapAlarmSeverity
                        }
        STATUS  current
        DESCRIPTION
                "the UPC/NPC disagreement cells ."
        ::= { bgs10PerfTrapsPrefix 2 }
        
bgs10OAMLoopback        NOTIFICATION-TYPE
        OBJECTS {       bgs10PmLoopBackTestIndex,
                                bgs10PmLoopBackTestResult
                        }
        STATUS  current
        DESCRIPTION
                "the OAM loop-back test notification ."
        ::= { bgs10PerfTrapsPrefix 3 }
        
bgs10OAMLoopbackTestOver NOTIFICATION-TYPE
        OBJECTS {       bgs10PmLoopBackTestIndex,
                                bgs10PmLoopBackTestResult
                        }
        STATUS  current
        DESCRIPTION
                "the OAM loop-back test notification ."
        ::= { bgs10PerfTrapsPrefix 4 }

-- bgs10E1CellsTraps            OBJECT IDENTIFIER       ::= { zxbgs10Traps 10 }
-- bgs10E1CellsTrapsPrefix      OBJECT IDENTIFIER       ::= { bgs10E1CellsTraps 0 }     
-- 
-- bgs10E1CellsYellowAlarm      NOTIFICATION-TYPE
--      OBJECTS {       bgs10E1LinkOperStatus,
--                              atmfM4TrapAlarmSeverity
--                      }
--      STATUS  current
--      DESCRIPTION
--              "the E1 yellow Alarm notification ."
--      ::= { bgs10E1CellsTrapsPrefix 1 }
--      
-- bgs10E1CellsLofAlarm NOTIFICATION-TYPE
--      OBJECTS {       bgs10E1LinkOperStatus,
--                              atmfM4TrapAlarmSeverity
--                      }
--      STATUS  current
--      DESCRIPTION
--              "the E1 LOF Alarm notification ."
--      ::= { bgs10E1CellsTrapsPrefix 2 }
--      
-- bgs10E1CellsLosAlarm NOTIFICATION-TYPE
--      OBJECTS {       bgs10E1LinkOperStatus,
--                              atmfM4TrapAlarmSeverity
--                      }
--      STATUS  current
--      DESCRIPTION
--              "the E1 LOS Alarm notification ."
--      ::= { bgs10E1CellsTrapsPrefix 3 }
--      
-- bgs10E1CellsAisAlarm NOTIFICATION-TYPE
--      OBJECTS {       bgs10E1LinkOperStatus,
--                              atmfM4TrapAlarmSeverity
--                      }
--      STATUS  current
--      DESCRIPTION
--              "the E1 AIS Alarm notification ."
--      ::= { bgs10E1CellsTrapsPrefix 4 }
--      
-- bgs10E1CellsCrcAlarm NOTIFICATION-TYPE
--      OBJECTS {       bgs10E1LinkOperStatus,
--                              atmfM4TrapAlarmSeverity
--                      }
--      STATUS  current
--      DESCRIPTION
--              "the E1 CRC Alarm notification ."
--      ::= { bgs10E1CellsTrapsPrefix 5 }
--      
-- bgs10E1CellsAtmLcdAlarm      NOTIFICATION-TYPE
--      OBJECTS {       bgs10E1LinkOperStatus,
--                              atmfM4TrapAlarmSeverity
--                      }
--      STATUS  current
--      DESCRIPTION
--              "the E1 ATM LCD Alarm notification ."
--      ::= { bgs10E1CellsTrapsPrefix 6 }
-- 

--The Fans' Alarm, different from ATM Forum

bgs10FanTraps                           OBJECT IDENTIFIER       ::= { zxbgs10Traps 11 }
bgs10FanTrapsPrefix                     OBJECT IDENTIFIER       ::= { bgs10FanTraps 0 }

bgs10Fan1Alarm                  NOTIFICATION-TYPE
        OBJECTS {       atmfM4TrapAlarmSeverity
                        }
        STATUS  current
        DESCRIPTION
                "The Alarm of Fan No.1"
        ::= { bgs10FanTrapsPrefix 1}
        
bgs10Fan2Alarm                  NOTIFICATION-TYPE
        OBJECTS {       atmfM4TrapAlarmSeverity
                        }
        STATUS  current
        DESCRIPTION
                "The Alarm of Fan No.2"
        ::= { bgs10FanTrapsPrefix 2}
        
        
bgs10Fan3Alarm                  NOTIFICATION-TYPE
        OBJECTS {       atmfM4TrapAlarmSeverity
                        }
        STATUS  current
        DESCRIPTION
                "The Alarm of Fan No.3"
        ::= { bgs10FanTrapsPrefix 3}


bgs10Fan4Alarm                  NOTIFICATION-TYPE
        OBJECTS {       atmfM4TrapAlarmSeverity
                        }
        STATUS  current
        DESCRIPTION
                "The Alarm of Fan No.4"
        ::= { bgs10FanTrapsPrefix 4}


--the E3 Traps
bgs10E3Traps                    OBJECT IDENTIFIER       ::= { zxbgs10Traps 16 }
bgs10E3TrapsPrefix              OBJECT IDENTIFIER       ::= { bgs10E3Traps 0 }

bgs10E3RAIAlarm NOTIFICATION-TYPE
        OBJECTS {       entPhysicalContainedIn,
                                entPhysicalParentRelPos,
                                entPhysicalClass,
                                atmfM4TrapAlarmSeverity
                        }
        STATUS  current
        DESCRIPTION
                "the RAI Alarm of the E3 Physical  Port."
        ::= { bgs10E3TrapsPrefix 1 }
        
bgs10E3LOFAlarm NOTIFICATION-TYPE
        OBJECTS {       entPhysicalContainedIn,
                                entPhysicalParentRelPos,
                                entPhysicalClass,
                                atmfM4TrapAlarmSeverity
                        }
        STATUS  current
        DESCRIPTION
                "the LOF Alarm of the E3 Physical  Port."
        ::= { bgs10E3TrapsPrefix 2 }
        
bgs10E3LOSAlarm NOTIFICATION-TYPE
        OBJECTS {       entPhysicalContainedIn,
                                entPhysicalParentRelPos,
                                entPhysicalClass,
                                atmfM4TrapAlarmSeverity
                        }
        STATUS  current
        DESCRIPTION
                "the LOS Alarm of the E3 Physical  Port."
        ::= { bgs10E3TrapsPrefix 3 }

bgs10E3AISAlarm NOTIFICATION-TYPE
        OBJECTS {       entPhysicalContainedIn,
                                entPhysicalParentRelPos,
                                entPhysicalClass,
                                atmfM4TrapAlarmSeverity
                        }
        STATUS  current
        DESCRIPTION
                "the AIS Alarm of the E3 Physical  Port."
        ::= { bgs10E3TrapsPrefix 4 }
        
bgs10E3FERFAlarm        NOTIFICATION-TYPE
        OBJECTS {       entPhysicalContainedIn,
                                entPhysicalParentRelPos,
                                entPhysicalClass,
                                atmfM4TrapAlarmSeverity
                        }
        STATUS  current
        DESCRIPTION
                "the FERF Alarm of the E3 Physical  Port."
        ::= { bgs10E3TrapsPrefix 5 }

bgs10E3LCDAlarm NOTIFICATION-TYPE
        OBJECTS {       entPhysicalContainedIn,
                                entPhysicalParentRelPos,
                                entPhysicalClass,
                                atmfM4TrapAlarmSeverity
                        }
        STATUS  current
        DESCRIPTION
                "the LCD Alarm of the E3 Physical  Port."
        ::= { bgs10E3TrapsPrefix 6 }
        
--the PVC Traps
bgs10PVCTraps                   OBJECT IDENTIFIER       ::= { zxbgs10Traps 17 }
bgs10PVCTrapsPrefix             OBJECT IDENTIFIER       ::= { bgs10PVCTraps 0 }

bgs10PVCNIAlarm NOTIFICATION-TYPE
        OBJECTS {       bgs10PvcLModule,
                                bgs10PvcLPort,
                                bgs10PvcLVpi,
                                bgs10PvcLVci,
                                atmfM4TrapAlarmSeverity
                        }
        STATUS  current
        DESCRIPTION
                "the PVCNI Alarm ."
        ::= { bgs10PVCTrapsPrefix 1 }
        

--The POS Alarm
bgs10POSTraps                   OBJECT IDENTIFIER       ::= { zxbgs10Traps 19 }
bgs10POSTrapsPrefix             OBJECT IDENTIFIER       ::= { bgs10POSTraps 0 }

bgs10POSLOS                     NOTIFICATION-TYPE
        OBJECTS {               entPhysicalContainedIn,
                                entPhysicalParentRelPos,
                                entPhysicalClass,
                                atmfM4TrapAlarmSeverity
                }
        STATUS  current
        DESCRIPTION
                "The port  Alarm of POS LOS"
        ::= { bgs10POSTrapsPrefix 1}

bgs10POSLOF                     NOTIFICATION-TYPE
        OBJECTS {               entPhysicalContainedIn,
                                entPhysicalParentRelPos,
                                entPhysicalClass,
                                atmfM4TrapAlarmSeverity
                }
        STATUS  current
        DESCRIPTION
                "The port  Alarm of POS LOF"
        ::= { bgs10POSTrapsPrefix 2}

bgs10POSLOP                     NOTIFICATION-TYPE
        OBJECTS {               entPhysicalContainedIn,
                                entPhysicalParentRelPos,
                                entPhysicalClass,
                                atmfM4TrapAlarmSeverity
                }
        STATUS  current
        DESCRIPTION
                "The port  Alarm of POS LOP"
        ::= { bgs10POSTrapsPrefix 3}

bgs10POSAISL                    NOTIFICATION-TYPE
        OBJECTS {               entPhysicalContainedIn,
                                entPhysicalParentRelPos,
                                entPhysicalClass,
                                atmfM4TrapAlarmSeverity
                }
        STATUS  current
        DESCRIPTION
                "The port  Alarm of POS AIS-L"
        ::= { bgs10POSTrapsPrefix 4}

bgs10POSRDIL                    NOTIFICATION-TYPE
        OBJECTS {               entPhysicalContainedIn,
                                entPhysicalParentRelPos,
                                entPhysicalClass,
                                atmfM4TrapAlarmSeverity
                }
        STATUS  current
        DESCRIPTION
                "The port  Alarm of POS RDI-L"
        ::= { bgs10POSTrapsPrefix 5}

bgs10POSAISP                    NOTIFICATION-TYPE
        OBJECTS {               entPhysicalContainedIn,
                                entPhysicalParentRelPos,
                                entPhysicalClass,
                                atmfM4TrapAlarmSeverity
                }
        STATUS  current
        DESCRIPTION
                "The port  Alarm of POS AISP"
        ::= { bgs10POSTrapsPrefix 6}

bgs10POSRDIP                    NOTIFICATION-TYPE
        OBJECTS {               entPhysicalContainedIn,
                                entPhysicalParentRelPos,
                                entPhysicalClass,
                                atmfM4TrapAlarmSeverity
                }
        STATUS  current
        DESCRIPTION
                "The port  Alarm of POS RDI-P-P"
        ::= { bgs10POSTrapsPrefix 7}



--  zxDslamTraps    
 
--zxDslamMibTableLastChangeTrap 
zxDslamMibTableLastChangeTrap NOTIFICATION-TYPE
           OBJECTS { zxDslamMibTableLastChange }
           STATUS  current
           DESCRIPTION
               "A zxDslamMibTableLastChangeTrap trap signifies that the zxDslamMibDataLoadEntry has 
                been changed"
       ::= { zxDslamTraps 0 1 }  

--zxDslamCommandModifyDataTrap
zxDslamCommandModifyDataTrap    NOTIFICATION-TYPE
           OBJECTS { zxDslamMibTableLastChange }
           STATUS  current
           DESCRIPTION
               "A zxDslamMibTableLastChangeTrap trap signifies that the zxDslamMibDataLoadEntry has 
                been changed"
       ::= { zxDslamTraps 0 2 }  




END



    LINE-TEST-MIB DEFINITIONS ::= BEGIN
    
	IMPORTS
	        MODULE-IDENTITY, TimeTicks,	OBJECT-TYPE,
			NOTIFICATION-TYPE, enterprises,IpAddress	FROM SNMPv2-SMI
			MacAddress                      		FROM SNMPv2-TC
	        	InterfaceIndex					FROM IF-MIB;
	
	zte MODULE-IDENTITY
	LAST-UPDATED "2703200000Z"
	ORGANIZATION ""
	CONTACT-INFO ""
	DESCRIPTION  "Initial Version"
	
	::= { enterprises 3902 } 
	zxDsl	OBJECT IDENTIFIER ::= { zte 1004 }
	zxDsl_2 OBJECT IDENTIFIER ::= { zxDsl 2 }
	zxDsl_2_1	OBJECT IDENTIFIER ::= { zxDsl_2 1 }
		

  zxDSLLineTestCardInfoTable OBJECT-TYPE
        SYNTAX      SEQUENCE OF zxDSLLineTestCardInfoEntry
        MAX-ACCESS  not-accessible
        STATUS      current
        DESCRIPTION
          "zxDSLLineTestCardInfoTable."
        ::= { zxDsl_2_1 1 }

    zxDSLLineTestCardInfoEntry OBJECT-TYPE
        SYNTAX      zxDSLLineTestCardInfoEntry
        MAX-ACCESS  not-accessible
        STATUS      current
        DESCRIPTION
        "zxDSLLineTestCardInfoEntry."
 	INDEX   {zxDSLLineTestCardInfoCardno}
         ::= { zxDSLLineTestCardInfoTable 1 }

    zxDSLLineTestCardInfoEntry ::=
        SEQUENCE {
           zxDSLLineTestCardInfoRowStatus  INTEGER ,
           zxDSLLineTestCardInfoCardno   INTEGER,
           zxDSLLineTestCardInfoCardType INTEGER,
           zxDSLLineTestCardInfoAvailStatus INTEGER,
           zxDSLLineTestCardInfoCardDescr OCTET STRING,
           zxDSLLineTestCardInfosoftver OCTET STRING,
           zxDSLLineTestCardInfobuildtime OCTET STRING,
           zxDSLLineTestCardInfohardver OCTET STRING,
           zxDSLLineTestCardInfoAtrribute INTEGER,
           zxDSLLineTestCardInfoAdminStatus INTEGER,
           zxDSLLineTestCardInfoSerialStatus INTEGER,
           zxDSLLineTestCardInfoOperStatus INTEGER,
           zxDSLLineTestCardInfoBackupsoftver OCTET STRING,
           zxDSLLineTestCardInfoBackupbuildtime OCTET STRING,
           zxDSLLineTestCardInforeserve1 INTEGER,
           zxDSLLineTestCardInforeserve2 INTEGER
        }


	zxDSLLineTestCardInfoRowStatus OBJECT-TYPE
  	SYNTAX      INTEGER
  	MAX-ACCESS  read-write
  	STATUS      current
  	DESCRIPTION
      " zxDSLLineTestCardInfoRowStatus"
  	REFERENCE
        ""
    ::= { zxDSLLineTestCardInfoEntry 1 }
    
	zxDSLLineTestCardInfoCardno OBJECT-TYPE
  	SYNTAX      INTEGER
  	MAX-ACCESS  not-accessible
  	STATUS      current
  	DESCRIPTION
      ""
  	REFERENCE
        ""
    ::= { zxDSLLineTestCardInfoEntry 2 }

	zxDSLLineTestCardInfoCardType OBJECT-TYPE
  	SYNTAX      INTEGER
  	MAX-ACCESS  read-write
  	STATUS      current
  	DESCRIPTION
      ""
  	REFERENCE
        ""
    ::= { zxDSLLineTestCardInfoEntry 3 }

	zxDSLLineTestCardInfoAvailStatus OBJECT-TYPE
  	SYNTAX      INTEGER
  	MAX-ACCESS  read-only
  	STATUS      current
  	DESCRIPTION
      "
      	define AvailStatus_Available		( UCHAR )1
		define AvailStatus_inTest   		( UCHAR )2
		define AvailStatus_Failed			( UCHAR )3
		define AvailStatus_powerOff 		( UCHAR )4
		define AvailStatus_notInstall		( UCHAR )5
		define AvailStatus_offLine  		( UCHAR )6
		define AvailStatus_Dependency		( UCHAR )7
		define AvailStatus_onLine			( UCHAR )8
		"
  	REFERENCE
        ""
    ::= { zxDSLLineTestCardInfoEntry 4 }

	zxDSLLineTestCardInfoCardDescr OBJECT-TYPE
  	SYNTAX      OCTET STRING
  	MAX-ACCESS  read-write
  	STATUS      current
  	DESCRIPTION
      ""
  	REFERENCE
        ""
    ::= { zxDSLLineTestCardInfoEntry 5 }

	zxDSLLineTestCardInfosoftver OBJECT-TYPE
  	SYNTAX      OCTET STRING
  	MAX-ACCESS  read-write
  	STATUS      current
  	DESCRIPTION
      ""
  	REFERENCE
        ""
    ::= { zxDSLLineTestCardInfoEntry 6 }

	zxDSLLineTestCardInfobuildtime OBJECT-TYPE
  	SYNTAX      OCTET STRING
  	MAX-ACCESS  read-write
  	STATUS      current
  	DESCRIPTION
      ""
  	REFERENCE
        ""
    ::= { zxDSLLineTestCardInfoEntry 7 }

	zxDSLLineTestCardInfohardver OBJECT-TYPE
  	SYNTAX      OCTET STRING
  	MAX-ACCESS  read-write
  	STATUS      current
  	DESCRIPTION
      ""
  	REFERENCE
        ""
    ::= { zxDSLLineTestCardInfoEntry 8 }

	zxDSLLineTestCardInfoAtrribute OBJECT-TYPE
  	SYNTAX      INTEGER
  	MAX-ACCESS  read-write
  	STATUS      current
  	DESCRIPTION
      "LNP_ATTR_ROOT:1    LNP_ATTR_OTHER: 2"
  	REFERENCE
        ""
    ::= { zxDSLLineTestCardInfoEntry 9 }

	zxDSLLineTestCardInfoAdminStatus OBJECT-TYPE
  	SYNTAX      INTEGER
  	MAX-ACCESS  read-write
  	STATUS      current
  	DESCRIPTION
      "1:up   2: down  3: testing(reset)"
  	REFERENCE
        ""
    ::= { zxDSLLineTestCardInfoEntry 10 }

	zxDSLLineTestCardInfoSerialStatus OBJECT-TYPE
  	SYNTAX      INTEGER
  	MAX-ACCESS  read-write
  	STATUS      current
  	DESCRIPTION
      "0:all down  1: left up  2: right up  3: all up"
  	REFERENCE
        ""
    ::= { zxDSLLineTestCardInfoEntry 11 }

	zxDSLLineTestCardInfoOperStatus OBJECT-TYPE
  	SYNTAX      INTEGER
  	MAX-ACCESS  read-write
  	STATUS      current
  	DESCRIPTION
      ""
  	REFERENCE
        ""
    ::= { zxDSLLineTestCardInfoEntry 12 }

	zxDSLLineTestCardInfoBackupsoftver OBJECT-TYPE
  	SYNTAX      OCTET STRING
  	MAX-ACCESS  read-write
  	STATUS      current
  	DESCRIPTION
      ""
  	REFERENCE
        ""
    ::= { zxDSLLineTestCardInfoEntry 13 }

	zxDSLLineTestCardInfoBackupbuildtime OBJECT-TYPE
  	SYNTAX      OCTET STRING
  	MAX-ACCESS  read-write
  	STATUS      current
  	DESCRIPTION
      ""
  	REFERENCE
        ""
    ::= { zxDSLLineTestCardInfoEntry 14 }

	zxDSLLineTestCardInforeserve1 OBJECT-TYPE
  	SYNTAX      INTEGER
  	MAX-ACCESS  read-write
  	STATUS      current
  	DESCRIPTION
      ""
  	REFERENCE
        ""
    ::= { zxDSLLineTestCardInfoEntry 15 }

	zxDSLLineTestCardInforeserve2 OBJECT-TYPE
  	SYNTAX      INTEGER
  	MAX-ACCESS  read-write
  	STATUS      current
  	DESCRIPTION
      ""
  	REFERENCE
        ""
    ::= { zxDSLLineTestCardInfoEntry 16 }

END
