-- File Name : ZTE-DSL-SVLAN-MIB.mi2
-- Date      : Mon Oct 17 14:11:11 GMT+08:00 2005
-- Author    : AdventNet Agent Toolkit C Edition - MibEditor 6



ZTE-DSL-SVLAN-MIB	DEFINITIONS ::= BEGIN
	IMPORTS
		zxDsl
			FROM ZTE-DSL-MIB
		RowStatus, TEXTUAL-CONVENTION
			FROM SNMPv2-TC
		dot1dBasePort
                        FROM BRIDGE-MIB
                ifIndex
                        FROM IF-MIB
		MODULE-IDENTITY, OBJECT-TYPE, Integer32
			FROM SNMPv2-SMI;

	zxDslSvlanMib	MODULE-IDENTITY
		LAST-UPDATED	"200404151500Z"
		ORGANIZATION	"ZTE Corporation"
		CONTACT-INFO	"ma ke
                  Mail: ZTE@zte.com.cn
                  Tel : 021-68896477"
		DESCRIPTION		"This MIB defines zte dsl ..........        managed objects."
		::=  {  zxDsl  14  }

-- TEXTUAL-CONVENTIONS --
	PortList ::= TEXTUAL-CONVENTION 
		DISPLAY-HINT	""
		STATUS			current
		DESCRIPTION
			"Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
		SYNTAX 			OCTET STRING

	zxDslSvlanObjects	OBJECT IDENTIFIER
		::=  {  zxDslSvlanMib  1  }

	zxDslSvlanTrapObjects	OBJECT IDENTIFIER
		::=  {  zxDslSvlanMib  2  }

	zxDslSvlanTpid	OBJECT-TYPE	
		SYNTAX			Integer32
		MAX-ACCESS		read-write
		STATUS			current
		DESCRIPTION		"the tpid of the svlan which is identify in whole system! "
		REFERENCE		""
		::=  {  zxDslSvlanObjects  1  }

	zxDslSvlanCTpid	OBJECT-TYPE	
		SYNTAX			Integer32
		MAX-ACCESS		read-write
		STATUS			current
		DESCRIPTION		"the ctpid of the svlan which is identify in whole system! "
		REFERENCE		""
		::=  {  zxDslSvlanObjects  2  }

	zxDslSvlanTable	OBJECT-TYPE
		SYNTAX		SEQUENCE  OF  ZxDslSvlanEntry
		MAX-ACCESS	not-accessible
		STATUS		current
		DESCRIPTION	"This table includes common attributes describing
       both ends of the line.  It is required for all ADSL
       physical interfaces.  ADSL physical interfaces are
       those ifEntries where ifType is equal to adsl(94)."
		::=  { zxDslSvlanObjects  3 }

	zxDslSvlanEntry	OBJECT-TYPE
		SYNTAX		ZxDslSvlanEntry
		MAX-ACCESS	not-accessible
		STATUS		current
		DESCRIPTION	"An entry in zxDslSvlanTable."
		INDEX		{  zxDslSvlanId  }
		::=  { zxDslSvlanTable 1 }

	ZxDslSvlanEntry  ::=  SEQUENCE {
		zxDslSvlanId  Integer32,
		zxDslSvlanAccessPorts  PortList,
		zxDslSvlanUplinkPorts  PortList,
		zxDslSvlanRowStatus  RowStatus
		}


	zxDslSvlanId	OBJECT-TYPE	
		SYNTAX			Integer32
		MAX-ACCESS		not-accessible
		STATUS			current
		DESCRIPTION		"SVLAN INDEX"
		::=  {  zxDslSvlanEntry  1  }


	zxDslSvlanAccessPorts	OBJECT-TYPE	
		SYNTAX			PortList
		MAX-ACCESS		read-write
		STATUS			current
		DESCRIPTION		"The set of ports which are permanently assigned to the
       egress list for this SVLAN by management.  Changes to a
       bit in this object affect the per-port per-SVLAN
       Registrar control for Registration Fixed for the
       relevant GVRP state machine on each port.  A port may
       not be added in this set if it is already a member of
       the set of ports in zxDslSvlanForbiddenEgressPorts.  The
       default value of this object is a string of zeros of
       appropriate length, indicating not fixed."
		::=  {  zxDslSvlanEntry  2  }


	zxDslSvlanUplinkPorts	OBJECT-TYPE	
		SYNTAX			PortList
		MAX-ACCESS		read-write
		STATUS			current
		DESCRIPTION		"The set of ports which are prohibited by management
       from being included in the egress list for this SVLAN.
       Changes to this object that cause a port to be included
       or excluded affect the per-port per-SVLAN Registrar

       control for Registration Forbidden for the relevant GVRP
       state machine on each port.  A port may not be added in
       this set if it is already a member of the set of ports
       in zxDslSvlanStaticEgressPorts.  The default value of
       this object is a string of zeros of appropriate length,
       excluding all ports from the forbidden set."
		::=  {  zxDslSvlanEntry  3  }


	zxDslSvlanRowStatus	OBJECT-TYPE	
		SYNTAX			RowStatus
		MAX-ACCESS		read-create
		STATUS			current
		DESCRIPTION		"This object indicates the status of this entry."
		::=  {  zxDslSvlanEntry  4  }
		

        zxDslPortSvlanTable	OBJECT-TYPE
		SYNTAX		SEQUENCE  OF  ZxDslPortSvlanEntry
		MAX-ACCESS	not-accessible
		STATUS		current
		DESCRIPTION	"."
		::=  { zxDslSvlanObjects  4 }

	zxDslPortSvlanEntry	OBJECT-TYPE
		SYNTAX		ZxDslPortSvlanEntry
		MAX-ACCESS	not-accessible
		STATUS		current
		DESCRIPTION	"An entry in zxDslPortSvlanTable."
		INDEX		{  ifIndex  }
		::=  { zxDslPortSvlanTable 1 }

	ZxDslPortSvlanEntry  ::=  SEQUENCE {
		zxDslSvlanPortInnerTag Unsigned32		
		}
		
	zxDslSvlanPortInnerTag	OBJECT-TYPE	
		SYNTAX			Unsigned32
		MAX-ACCESS		read-write
		STATUS			current
		DESCRIPTION		""
		::=  {  zxDslPortSvlanEntry  1  }	

        zxDslPortPvcSvlanTable	OBJECT-TYPE
		SYNTAX		SEQUENCE  OF  ZxDslPortPvcSvlanEntry
		MAX-ACCESS	not-accessible
		STATUS		current
		DESCRIPTION	"."
		::=  { zxDslSvlanObjects  5 }

	zxDslPortPvcSvlanEntry	OBJECT-TYPE
		SYNTAX		ZxDslPortPvcSvlanEntry
		MAX-ACCESS	not-accessible
		STATUS		current
		DESCRIPTION	"An entry in zxDslPortPvcSvlanTable."
		INDEX		{  dot1dBasePort  }
		::=  { zxDslPortPvcSvlanTable 1 }

	ZxDslPortPvcSvlanEntry  ::=  SEQUENCE {	
        zxDslPortPvcSvlanEnable                Integer32,
		zxDslPortPvcPsvlanId                   Unsigned32,
        zxDslPortPvcTlsEnable                  Integer32,
        zxDslPortPvcMCastVlanId                Unsigned32
		}
	
	zxDslPortPvcSvlanEnable	OBJECT-TYPE	
		SYNTAX			Integer32
		MAX-ACCESS		read-write
		STATUS			current
		DESCRIPTION		""
		::=  {  zxDslPortPvcSvlanEntry  1  }
	
	zxDslPortPvcPsvlanId	OBJECT-TYPE	
		SYNTAX			Unsigned32
		MAX-ACCESS		read-write
		STATUS			current
		DESCRIPTION		""
		::=  {  zxDslPortPvcSvlanEntry  2  }	


	zxDslPortPvcTlsEnable	OBJECT-TYPE	
                SYNTAX            Integer32
		MAX-ACCESS		read-write
		STATUS			current
		DESCRIPTION		"Enable/disable TLS(Transparent LAN Service) of this port ."
		::=  {  zxDslPortPvcSvlanEntry  3  }	

    zxDslPortPvcMCastVlanId	OBJECT-TYPE	
		SYNTAX			Unsigned32(1..4094)
		MAX-ACCESS		read-write
		STATUS			current
		DESCRIPTION		"Multicast SPAN VLAN ID"
		::=  {  zxDslPortPvcSvlanEntry  4  }	

    zxDslSlotSvlanTable	OBJECT-TYPE
		SYNTAX		SEQUENCE  OF  ZxDslSlotSvlanEntry
		MAX-ACCESS	not-accessible
		STATUS		current
		DESCRIPTION	"."
		::=  { zxDslSvlanObjects  6 }

	zxDslSlotSvlanEntry	OBJECT-TYPE
		SYNTAX		ZxDslSlotSvlanEntry
		MAX-ACCESS	not-accessible
		STATUS		current
		DESCRIPTION	"An entry in zxDslSlotSvlanTable."
		INDEX		{  zxDslSlot  }
		::=  { zxDslSlotSvlanTable 1 }

	ZxDslSlotSvlanEntry  ::=  SEQUENCE {
		zxDslSlot                Integer32,
		zxDslSlotSvlanEnable     Integer32
		}

	zxDslSlot	OBJECT-TYPE	
		SYNTAX			Integer32
		MAX-ACCESS		not-accessible
		STATUS			current
		DESCRIPTION		"SLOT INDEX"
		::=  {  zxDslSlotSvlanEntry  1  }
		
	zxDslSlotSvlanEnable	OBJECT-TYPE	
		SYNTAX			Integer32
		MAX-ACCESS		read-write
		STATUS			current
		DESCRIPTION		""
		::=  {  zxDslSlotSvlanEntry  2  }		
		       
			
	zxDslRvlanTable	OBJECT-TYPE
		SYNTAX		SEQUENCE  OF  ZxDslRvlanEntry
		MAX-ACCESS	not-accessible
		STATUS		current
		DESCRIPTION	"."
		::=  { zxDslSvlanObjects  7 }

	zxDslRvlanEntry	OBJECT-TYPE
		SYNTAX		ZxDslRvlanEntry
		MAX-ACCESS	not-accessible
		STATUS		current
		DESCRIPTION	"An entry in zxDslRvlanTable."
		INDEX		{  zxDslRvlanId  }
		::=  { zxDslRvlanTable 1 }

	ZxDslRvlanEntry  ::=  SEQUENCE {
		zxDslRvlanId             Integer32,
		zxDslRvlanUseType        Unsigned32,
		zxDslRvlanRowStatus      RowStatus
		}

	zxDslRvlanId	OBJECT-TYPE	
		SYNTAX			Integer32 ( 1..4094 )
		MAX-ACCESS		not-accessible
		STATUS			current
		DESCRIPTION		"RVLAN INDEX"
		::=  {  zxDslRvlanEntry  1  }
		
	zxDslRvlanUseType	OBJECT-TYPE	
		SYNTAX			Unsigned32{anic(1)
                                                  }
		MAX-ACCESS		read-write
		STATUS			current
		DESCRIPTION		""
		::=  {  zxDslRvlanEntry  2  }		
		
        zxDslRvlanRowStatus	OBJECT-TYPE	
		SYNTAX			RowStatus
		MAX-ACCESS		read-create
		STATUS			current
		DESCRIPTION		"This object indicates the status of this entry."
		::=  {  zxDslRvlanEntry  3  }		

END
