-- File Name : zxDslVlanSvlanMib
-- Date      : Mon Oct 17 14:11:11 GMT+08:00 2005
-- Author    : AdventNet Agent Toolkit C Edition - MibEditor 6



ZTE-DSL-PORT-VLAN	DEFINITIONS ::= BEGIN
	IMPORTS
		zxDsl
			FROM ZTE-DSL-MIB
		RowStatus, TEXTUAL-CONVENTION
			FROM SNMPv2-TC
		dot1dBasePort
                        FROM BRIDGE-MIB
                ifIndex
                        FROM IF-MIB
		MODULE-IDENTITY, OBJECT-TYPE, Integer32
			FROM SNMPv2-SMI;

	zxDslPortVlanMib	MODULE-IDENTITY
		LAST-UPDATED	"200404151500Z"
		ORGANIZATION	"ZTE Corporation"
		CONTACT-INFO	"ma ke
                  Mail: ZTE@zte.com.cn
                  Tel : 021-68896477"
		DESCRIPTION		"This MIB defines zte dsl ..........        managed objects."
		::=  {  zxDsl  21  }

-- TEXTUAL-CONVENTIONS --
	PortList ::= TEXTUAL-CONVENTION 
		DISPLAY-HINT	""
		STATUS			current
		DESCRIPTION
			"Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
		SYNTAX 			OCTET STRING

	zxDslVlanObjects	OBJECT IDENTIFIER
		::=  {  zxDslPortVlanMib  1  }

	zxDslVlanTrapObjects	OBJECT IDENTIFIER
		::=  {  zxDslPortVlanMib  2  }	
		
	
	zxDslVlanTotalNumber  OBJECT-TYPE
		SYNTAX			Integer32
		MAX-ACCESS		read-only
		STATUS			current
		DESCRIPTION		"the vlan total number in whole system! "
		REFERENCE		""
		::=  { zxDslVlanObjects  1 }	

	zxDslPortVlanListTable	OBJECT-TYPE
		SYNTAX		SEQUENCE  OF  ZxDslPortVlanListEntry
		MAX-ACCESS	not-accessible
		STATUS		current
		DESCRIPTION	"This table includes common attributes describing
       both ends of the line.  It is required for all ADSL
       physical interfaces.  ADSL physical interfaces are
       those ifEntries where ifType is equal to adsl(94)."
		::=  { zxDslVlanObjects  2 }

	zxDslPortVlanListEntry	OBJECT-TYPE
		SYNTAX		ZxDslPortVlanListEntry
		MAX-ACCESS	not-accessible
		STATUS		current
		DESCRIPTION	"An entry in zxDslPortVlanListTable."
		INDEX		{  ifIndex  }
		::=  { zxDslPortVlanListTable 1 }

	ZxDslPortVlanListEntry  ::=  SEQUENCE {
		zxDslPortUntagVlans   OCTET STRING,
		zxDslPortTagVlans     OCTET STRING		
		}

    zxDslPortUntagVlans	OBJECT-TYPE	
        SYNTAX			OCTET STRING(SIZE(512))
        MAX-ACCESS		read-only
        STATUS			current		
        DESCRIPTION		"This object indicates these vlans in which port joined
                        by accsss mode.     
                                         
                        Each bit of the 512 bytes(4096 bits) represents the 
                        status of corresponding VLAN, bit 0 represents VLAN 1,
                        bit 1 represents VLAN 2... and bit 4093 represents
                        VLAN 4094.    
                         
                        A value of 1 indicates current port bind in that vlan."        
                        ::=  {  zxDslPortVlanListEntry  1  }

    zxDslPortTagVlans	OBJECT-TYPE	
        SYNTAX			OCTET STRING(SIZE(512))
        MAX-ACCESS		read-only
        STATUS			current
        DESCRIPTION		"This object indicates these vlans in which port joined 
                        by trunk mode.
                        
                        Each bit of the 512 bytes(4096 bits) represents the 
                        status of corresponding VLAN, bit 0 represents VLAN 1, 
                        bit 1 represents VLAN 2... and bit 4093 represents 
                        VLAN 4094.
                        
                        A value of 1 indicates current port bind in that vlan."		
        ::=  {  zxDslPortVlanListEntry  2  }	
END
