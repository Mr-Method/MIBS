ZTE-DSL-MULTICAST-MIB DEFINITIONS ::= BEGIN
    IMPORTS 
        MODULE-IDENTITY, OBJECT-TYPE,NOTIFICATION-TYPE,
            IpAddress,TimeTicks,Counter32, Gauge32          FROM SNMPv2-SMI
        RowStatus                                           FROM SNMPv2-TC
        SnmpAdminString                                     FROM SNMP-FRAMEWORK-MIB
        PortList       	                                    FROM Q-BRIDGE-MIB           
        zxDsl                                               FROM ZTE-DSL-LINE-EXT-MIB;


zxDslMulticastMib MODULE-IDENTITY
    LAST-UPDATED "200511051100Z"
    ORGANIZATION "ZTE Corporation"
    CONTACT-INFO "ZTE NMS dept. 
                  Ma Jian       68896249,
                  Su Chunshan   68896292  "
    DESCRIPTION  "This MIB defines Description of zte multicast Service managed objects. "
    ::= {zxDsl 8}

zxDslMulticastObjects      OBJECT IDENTIFIER ::= {zxDslMulticastMib 1}
zxDslMulticastTrapObjects  OBJECT IDENTIFIER ::= {zxDslMulticastMib 2}

-- ----------------------------------------------------------------------------
--  Multicast MIB
--  lisr& marb & majh write the mi2 file, March 02,2004
-- ---------------------------------------------------------------------------

    zxMulticastIGMP      OBJECT IDENTIFIER ::= {zxDslMulticastObjects 1}
    zxMulticastMVR       OBJECT IDENTIFIER ::= {zxDslMulticastObjects 2}    
    zxMulticastCAC       OBJECT IDENTIFIER ::= {zxDslMulticastObjects 3}
    zxMulticastPRW       OBJECT IDENTIFIER ::= {zxDslMulticastObjects 4}      
    zxMulticastCDR       OBJECT IDENTIFIER ::= {zxDslMulticastObjects 5}   
    
-- ---------------------------------------------------------------------------
--  zxMulticastIGMP
-- ---------------------------------------------------------------------------
    zxIgmpEnabled  OBJECT-TYPE
        SYNTAX INTEGER
        { 
            true ( 1 ) , 
            false ( 2 ) , 
            through ( 3 )
        }
        MAX-ACCESS read-write
        STATUS current
        DESCRIPTION
            "DURABLE: { false )
             Setting this object to true(1) enables IGMP .  Setting
             it to false(2) disables IGMP.             
             Note that IGMP can function with or without GVRP and
             GMRP enabled."
        ::= { zxMulticastIGMP 1 }
        
    zxIgmpAging  OBJECT-TYPE
        SYNTAX Integer32 (30..3600)
        MAX-ACCESS read-write
        STATUS current
        DESCRIPTION
            "DURABLE: { 300 )
             The timeout period in seconds for aging out Multicast Groups
             dynamically learned with IGMP.  Note that aging operates
             on a per interface per VLAN per multicast group basis."
        ::= { zxMulticastIGMP 2 }       
        
    zxIgmpMode  OBJECT-TYPE
        SYNTAX 	INTEGER(1..3)
        MAX-ACCESS read-write
        STATUS current
        DESCRIPTION
            "IGMP mode"
        ::= { zxMulticastIGMP 3 }  
       
    zxIgmpSMSRetrieve  OBJECT-TYPE
        SYNTAX INTEGER{
                        retrievable(0),
			retrieveType1(1),
                        retrieveType2(2),
		        retrieving(3)
                      }
        MAX-ACCESS read-write
        STATUS current
        DESCRIPTION
            "used to retrieve data from sms server,when commit '1'or '2',need to retrieve."
        ::= { zxMulticastIGMP 4 }
    
    zxIgmpPortTable OBJECT-TYPE
        SYNTAX SEQUENCE OF ZxIgmpPortEntry 
        MAX-ACCESS not-accessible
        STATUS   current
        DESCRIPTION
            "A table that contains all IGMP informations."
        ::= { zxMulticastIGMP 5 }

    zxIgmpPortEntry  OBJECT-TYPE
        SYNTAX     ZxIgmpPortEntry 
        MAX-ACCESS not-accessible
        STATUS     current
        DESCRIPTION
            "A list of  entries of all IGMP information."
        INDEX  { zxIgmpIfIndex }
        ::= { zxIgmpPortTable 1 }

    ZxIgmpPortEntry ::= SEQUENCE {
        zxIgmpIfIndex        INTEGER,
        zxIgmpsnoopMaxpermit INTEGER,		
        zxIgmpFastLeave      INTEGER,
        zxIgmpBandwidth      Unsigned32,
        zxIgmpPacketVersion  BITS,
        zxIgmpEnable         INTEGER,
	zxIgmpMaxIgmpPacketNum INTEGER
    }
	
    zxIgmpIfIndex            OBJECT-TYPE
        SYNTAX         INTEGER
        MAX-ACCESS     not-accessible
        STATUS         current
        DESCRIPTION
            "The port No."
        ::= { zxIgmpPortEntry 1}
     
    zxIgmpsnoopMaxpermit     OBJECT-TYPE
        SYNTAX         INTEGER
        MAX-ACCESS     read-write
        STATUS         current
        DESCRIPTION
            "The maximum permitted number of the controlled multicast list about this port ."
        ::= { zxIgmpPortEntry 2}
     
    zxIgmpFastLeave  OBJECT-TYPE
        SYNTAX 	INTEGER
        MAX-ACCESS read-write
        STATUS current
        DESCRIPTION
            "the status of fast-leave property."
        ::= { zxIgmpPortEntry 3 }
	
    zxIgmpBandwidth   OBJECT-TYPE
        SYNTAX 	Unsigned32(1..1048576)
	MAX-ACCESS read-write
        STATUS current
        DESCRIPTION
            ""
        ::= { zxIgmpPortEntry 4 }
 
   zxIgmpPacketVersion   OBJECT-TYPE
        SYNTAX 	BITS
	{
         V1(0),
         V2(1),            
         V3(2)
	}
        MAX-ACCESS read-write
        STATUS current
        DESCRIPTION
            ""
        ::= { zxIgmpPortEntry 5 }

    zxIgmpEnable    OBJECT-TYPE
        SYNTAX 	INTEGER
	{ 
          enable(1),
          disable(2)
	}
        MAX-ACCESS read-write
        STATUS current
        DESCRIPTION
            ""
        ::= { zxIgmpPortEntry 6 }


     zxIgmpMaxIgmpPacketNum     OBJECT-TYPE
        SYNTAX         INTEGER(0..500)
        MAX-ACCESS     read-write
        STATUS         current
        DESCRIPTION
            "The maximum permitted number of the igmp packets about this port ."
        ::= { zxIgmpPortEntry 7}

    zxIgmpUplinkFloodEnabled  OBJECT-TYPE
        SYNTAX TruthValue
        MAX-ACCESS read-write
        STATUS current
        DESCRIPTION
            "DURABLE: { false )
             Setting this object to true(1) enables IGMP Uplink flood. Setting
             it to false(2) disables IGMP Uplink flood."
        ::= { zxMulticastIGMP 6 }

    zxIgmpBandwidthControl  OBJECT-TYPE
        SYNTAX TruthValue
        MAX-ACCESS read-write
        STATUS current
        DESCRIPTION
            "DURABLE: { false )
             Setting this object to true(1) enables bandwidth control. Setting
             it to false(2) disables bandwidth control."
        ::= { zxMulticastIGMP 7 }
    zxIgmpManageSTBMacStatus  OBJECT-TYPE
        SYNTAX TruthValue
        MAX-ACCESS read-write
        STATUS current
        DESCRIPTION
            ""
        ::= { zxMulticastIGMP 8 }
    zxIgmpGlobalBandCheckCtrl  OBJECT-TYPE
        SYNTAX TruthValue
        MAX-ACCESS read-write
        STATUS current
        DESCRIPTION
            "DURABLE: { false )
             Setting this object to true(1) enables global bandwidth control. Setting
             it to false(2) disables global bandwidth control."
        ::= { zxMulticastIGMP 9 }
	  zxIgmpGlobalBandValue	OBJECT-TYPE	
		    SYNTAX			Unsigned32(1..6291456)
		    MAX-ACCESS		read-write
		    STATUS			current
		    DESCRIPTION		
            "DURABLE: { 6291456 )
            Bandwidth Cost by this device "
		::=  {  zxMulticastIGMP  10  }  
    
     zxIgmpFastJoininInterval     OBJECT-TYPE
        SYNTAX         INTEGER(10..1000)
        MAX-ACCESS     read-write
        STATUS         current
        DESCRIPTION
            "DURABLE: { 100 ),The Interval in seconds for the igmp Fast Joinin ."
        ::= { zxMulticastIGMP 11}           
-- ---------------------------------------------------------------------------
--     zxMulticastMVR
-- ---------------------------------------------------------------------------
    zxMVREnable OBJECT-TYPE
        SYNTAX INTEGER{
            enable(1),
            disable(2)
        }
        MAX-ACCESS read-write
        STATUS current
        DESCRIPTION
            "Enable/disable MVR in this system."
        ::= { zxMulticastMVR 1 }

    zxMVRMaxResponseTime OBJECT-TYPE
        SYNTAX INTEGER
        MAX-ACCESS read-write
        STATUS current
        DESCRIPTION
            "Max response time ."
        ::= { zxMulticastMVR 2 } 
    
    zxMVRTable OBJECT-TYPE
        SYNTAX SEQUENCE OF ZxMVREntry
        MAX-ACCESS not-accessible
        STATUS current
        DESCRIPTION
            "A table that contains all ZXDSL informations in this stack system.
	    It is allowed to get in master module."
	::= { zxMulticastMVR 3 }

    zxMVREntry OBJECT-TYPE
        SYNTAX ZxMVREntry
        MAX-ACCESS not-accessible
        STATUS current
        DESCRIPTION
            "A list of  entries of all ZXDSL information."
        INDEX { zxMVRMvlan}
        ::= { zxMVRTable 1 }

    ZxMVREntry ::= SEQUENCE {
        zxMVRMvlan              INTEGER,
        zxMVRMaxGroup           INTEGER,
        zxMVRSrcIp              IpAddress,        
        zxMVRSrcPortList        PortList,        
        zxMVRRowStatus          RowStatus          	
    }

    zxMVRMvlan OBJECT-TYPE
        SYNTAX INTEGER(1..4095)
        MAX-ACCESS not-accessible
        STATUS current
        DESCRIPTION
            "mvlan ID."
        ::= { zxMVREntry 1 }

    zxMVRMaxGroup OBJECT-TYPE
        SYNTAX INTEGER(1..512)
        MAX-ACCESS read-create
        STATUS current
        DESCRIPTION
            "Max groups in mvlan"
        ::= { zxMVREntry 2 }
        
    zxMVRSrcIp	OBJECT-TYPE	
		SYNTAX			IpAddress
		MAX-ACCESS		read-create
		STATUS			current
		DESCRIPTION		" "
		::=  {  zxMVREntry  3  }
	
    zxMVRSrcPortList OBJECT-TYPE
        SYNTAX PortList
        MAX-ACCESS read-create
        STATUS current
        DESCRIPTION
            "Source port in mvlan"
        ::= { zxMVREntry 4 }          
	
    zxMVRRowStatus OBJECT-TYPE
        SYNTAX RowStatus
        MAX-ACCESS read-create
        STATUS current
        DESCRIPTION
            "RowStatus"
        ::= { zxMVREntry 5 }
        
    zxMVRExtTable OBJECT-TYPE
        SYNTAX SEQUENCE OF ZxMVRExtEntry
        MAX-ACCESS not-accessible
        STATUS current
        DESCRIPTION
            "A table that contains all ZXDSL informations in this stack system.
	    It is allowed to get in master module."
	::= { zxMulticastMVR 4 }

    zxMVRExtEntry OBJECT-TYPE
        SYNTAX ZxMVRExtEntry
        MAX-ACCESS not-accessible
        STATUS current
        DESCRIPTION
            "A list of  entries of all ZXDSL information."
        INDEX { zxMVRMvlan, zxMVRScId}
        ::= { zxMVRExtTable 1 }

    ZxMVRExtEntry ::= SEQUENCE {
        zxMVRExtRecvPortList       PortList,
        zxMVRExtRowStatus          RowStatus
    }
        
    zxMVRExtRecvPortList	OBJECT-TYPE	
	SYNTAX			PortList
	MAX-ACCESS		read-create
	STATUS			current
	DESCRIPTION		"Interface ."
	::=  {  zxMVRExtEntry  1  }       
	
    zxMVRExtRowStatus OBJECT-TYPE
        SYNTAX RowStatus
        MAX-ACCESS read-create
        STATUS current
        DESCRIPTION
            "RowStatus"
        ::= { zxMVRExtEntry 2 }        
	
    zxMVRGroupTable OBJECT-TYPE
        SYNTAX SEQUENCE OF zxMVRGroupEntry
        MAX-ACCESS not-accessible
        STATUS current
        DESCRIPTION
            "A table that contains all groups in the mvlan."
        ::= { zxMulticastMVR 5 }

    zxMVRGroupEntry OBJECT-TYPE
        SYNTAX zxMVRGroupEntry
        MAX-ACCESS not-accessible
        STATUS current
        DESCRIPTION
            "A list of  entries of all groups information in mvlan."
            INDEX { zxMVRGroupIp}
        ::= { zxMVRGroupTable 1 }

    zxMVRGroupEntry ::= SEQUENCE {
        zxMVRGroupIp                   IpAddress,
        zxMVRMvlanId                   INTEGER,
        zxMVRGroupStaRecvPortList      PortList,
        zxMVRGroupName                 DisplayString,
        zxMVRGroupRowStatus            RowStatus          	
    }    
    
    zxMVRGroupIp	OBJECT-TYPE	
	SYNTAX			IpAddress
	MAX-ACCESS		not-accessible
	STATUS			current
	DESCRIPTION		"multicast ip address . it can be 0.0.0.0 when setting "
	::=  {  zxMVRGroupEntry  1  }

    zxMVRMvlanId OBJECT-TYPE
        SYNTAX INTEGER(1..4095)
        MAX-ACCESS read-create
        STATUS current
        DESCRIPTION
            "vlan."
        ::= { zxMVRGroupEntry 2 }
	
    zxMVRGroupStaRecvPortList OBJECT-TYPE
        SYNTAX PortList
        MAX-ACCESS read-create
        STATUS current
        DESCRIPTION
            "Interface ."
        ::= { zxMVRGroupEntry 3 }    
	
    zxMVRGroupName OBJECT-TYPE
        SYNTAX DisplayString
        MAX-ACCESS read-create
        STATUS current
        DESCRIPTION
            "zxMVRGroupName"
        ::= { zxMVRGroupEntry 4 }   


    zxMVRGroupRowStatus OBJECT-TYPE
        SYNTAX RowStatus
        MAX-ACCESS read-create
        STATUS current
        DESCRIPTION
            "RowStatus"
        ::= { zxMVRGroupEntry 5 }                   


-- Dyn Recv Port        
    zxMVRDynRecvPortTable	OBJECT-TYPE
	SYNTAX		SEQUENCE  OF  ZxMVRDynRecvPortEntry
	MAX-ACCESS	not-accessible
	STATUS		current
	DESCRIPTION	"Description"
	::=  { zxMulticastMVR  6 }

    zxMVRDynRecvPortEntry	OBJECT-TYPE
	SYNTAX		ZxMVRDynRecvPortEntry
	MAX-ACCESS	not-accessible
	STATUS		current
	DESCRIPTION	"Row Description"
	INDEX		{  zxMVRMvlan, zxMVRGroupIp  }
	::=  { zxMVRDynRecvPortTable 1 }

    ZxMVRDynRecvPortEntry  ::=  SEQUENCE {
	zxMVRGroupDynRecvPortList  PortList
    }

    zxMVRGroupDynRecvPortList	OBJECT-TYPE	
	SYNTAX			PortList
	MAX-ACCESS		read-only
	STATUS			current
	DESCRIPTION		" "
	::=  {  zxMVRDynRecvPortEntry  1  }      
	
    zxMVRPortScTable OBJECT-TYPE
        SYNTAX SEQUENCE OF zxMVRPortScEntry
        MAX-ACCESS not-accessible
        STATUS current
        DESCRIPTION
            "A table that contains pvc info of the ports in mvlan."
        ::= { zxMulticastMVR 7 }

    zxMVRPortScEntry OBJECT-TYPE
        SYNTAX zxMVRPortScEntry
        MAX-ACCESS not-accessible
        STATUS current
        DESCRIPTION
            "A list of  entries of all pvc info of the ports in mvlan."
        INDEX {zxMVRPort, zxMVRScId }
        ::= { zxMVRPortScTable 1 }

    zxMVRPortScEntry ::= SEQUENCE {
        zxMVRPort                 INTEGER,
        zxMVRScId                 INTEGER,
        zxMVRScVlanOrPvc          INTEGER,
        zxMVRScPvcID              INTEGER,
        zxMVRScVlanID             INTEGER,
        zxMVRScType               INTEGER,		
        zxMVRPortScRowStatus      RowStatus
    }
		
    zxMVRPort OBJECT-TYPE
        SYNTAX INTEGER
        MAX-ACCESS not-accessible
        STATUS current
        DESCRIPTION
            "port No."
        ::= { zxMVRPortScEntry 1 }
	
    zxMVRScId OBJECT-TYPE
        SYNTAX INTEGER
        MAX-ACCESS not-accessible
        STATUS current
        DESCRIPTION
            "MVR sub channel id"
    ::= { zxMVRPortScEntry 2 }
	
 	
    zxMVRScVlanOrPvc OBJECT-TYPE
        SYNTAX INTEGER{
            VLAN(1),
            PVC(2)
        }
        MAX-ACCESS read-create
        STATUS current
        DESCRIPTION
            "Sc Map Mode:Vlan or PVC"
        ::= { zxMVRPortScEntry 3 }
	
    zxMVRScPvcID OBJECT-TYPE
        SYNTAX INTEGER
        MAX-ACCESS read-create
        STATUS current
        DESCRIPTION
            "Pvc id of this SC"
        ::= { zxMVRPortScEntry 4 }
	
	
    zxMVRScVlanID OBJECT-TYPE
        SYNTAX INTEGER
        MAX-ACCESS read-create
        STATUS current
        DESCRIPTION
            "vlan ID of this Sc"
        ::= { zxMVRPortScEntry 5 }		
	
    zxMVRScType OBJECT-TYPE
        SYNTAX INTEGER{
            ALL(1),
            IGMP(2),
            DATA(3)
        }
        MAX-ACCESS read-create
        STATUS current
        DESCRIPTION
            "Sc Type "
        ::= { zxMVRPortScEntry 6 }
        
    zxMVRPortScRowStatus OBJECT-TYPE
        SYNTAX RowStatus
        MAX-ACCESS read-create
        STATUS current
        DESCRIPTION
            "RowStatus"
        ::= { zxMVRPortScEntry 7 }	
        
    zxMVRSpanVlanEnable OBJECT-TYPE
        SYNTAX INTEGER{
            enable(1),
            disable(2)
        }
        MAX-ACCESS read-write
        STATUS current
        DESCRIPTION
            "Enable/disable MVR in multi-vlans."
        ::= { zxMulticastMVR 8 }        	

-- Bandwidth Ctrl table


    zxAcBandwidthCtrlTable	OBJECT-TYPE
		SYNTAX		SEQUENCE  OF  zxAcBandwidthCtrlEntry
		MAX-ACCESS	not-accessible
		STATUS		current
		DESCRIPTION	""
		::=  { zxMulticastMVR  9 }

	zxAcBandwidthCtrlEntry	OBJECT-TYPE
		SYNTAX		ZxACGpIpEntry
		MAX-ACCESS	not-accessible
		STATUS		current
		DESCRIPTION	""
		INDEX		{ zxACGpIp  }
		::=  { zxAcBandwidthCtrlTable 1 }

	zxAcBandwidthCtrlEntry  ::=  SEQUENCE {
		zxAcGpBandwidthCost  Unsigned32,
		zxAcGpFastJoin       Integer32
		}

	zxAcGpBandwidthCost	OBJECT-TYPE	
		SYNTAX			Unsigned32(1..65536)
		MAX-ACCESS		read-write
		STATUS			current
		DESCRIPTION		"Bandwidth Cost by this group "
		::=  {  zxAcBandwidthCtrlEntry  1  }


	zxAcGpFastJoin	OBJECT-TYPE	
		SYNTAX			Integer32
		                {
		                    enable(1),
		                    disable(2)
		                }
		MAX-ACCESS		read-write
		STATUS			current
		DESCRIPTION		" if use FastJoin group function."
		::=  {  zxAcBandwidthCtrlEntry  2  }
      
   zxMVRSynMvlan OBJECT-TYPE
        SYNTAX INTEGER(1..4094)
        MAX-ACCESS read-write
        STATUS current
        DESCRIPTION
            ""
        ::= { zxMulticastMVR 10 }
    zxMVRSynMvlanGroup OBJECT-TYPE
        SYNTAX IpAddress
        MAX-ACCESS read-write
        STATUS current
        DESCRIPTION
            ""
        ::= { zxMulticastMVR 11 }

    zxMVRPortGroupTable OBJECT-TYPE
        SYNTAX SEQUENCE OF zxMVRPortGroupEntry
        MAX-ACCESS not-accessible
        STATUS current
        DESCRIPTION
            ""
        ::= { zxMulticastMVR 12 }

    zxMVRPortGroupEntry OBJECT-TYPE
        SYNTAX zxMVRPortGroupEntry
        MAX-ACCESS not-accessible
        STATUS current
        DESCRIPTION
            "A list of  entries of all groups information in mvlan."
            INDEX {zxIgmpIfIndex,zxMVRGroupIp}
        ::= { zxMVRPortGroupTable 1 }

    zxMVRPortGroupEntry ::= SEQUENCE {
        zxIgmpTypeInGroup   INTEGER
    } 

    zxIgmpPortTypeInGroup     OBJECT-TYPE
        SYNTAX         INTEGER{
            static(1),
            dynamic(2)
        }
        MAX-ACCESS     read-only
        STATUS         current
        DESCRIPTION
            ""
        ::= { zxMVRPortGroupEntry 1}
-- ---------------------------------------------------------------------------
--    zxMulticastCAC
-- ---------------------------------------------------------------------------

    zxACPrwSwitch OBJECT-TYPE
        SYNTAX 		INTEGER{
            enable(1),
            disable(2)
        }
        MAX-ACCESS 	read-write
        STATUS current
        DESCRIPTION
            "the switch used by both CAC and PRW module, '1'-enable."
        ::= { zxMulticastCAC 1 }
 
 
    zxACGpIpTable OBJECT-TYPE
        SYNTAX SEQUENCE OF ZxACGpIpEntry
        MAX-ACCESS not-accessible
        STATUS     current
        DESCRIPTION
            "CAC Address Table info"
        ::= { zxMulticastCAC 2 }
 
    zxACGpIpEntry OBJECT-TYPE
        SYNTAX     ZxACGpIpEntry
        MAX-ACCESS not-accessible
        STATUS     current
        DESCRIPTION
            "A list of  entries of all Multicast address information."
        INDEX  { zxACGpIp }
        ::= { zxACGpIpTable 1 }

    ZxACGpIpEntry ::= SEQUENCE {
        zxACGpIp                 IpAddress,
        zxACGpMaxPrwCount        Counter,
        zxACGpMaxPrwInter        Counter,
        zxACGpPrwResumeInter     Counter,
        zxACGpPortList           PortList,
        zxACGpPortRight          PortList,
        zxACGpName               DisplayString,
        zxACGpRowStatus          RowStatus,        
        zxACGpViewParamProfile   DisplayString
    }

    zxACGpIp 	OBJECT-TYPE
        SYNTAX 		IpAddress
        MAX-ACCESS 	read-create
        STATUS current
        DESCRIPTION
            "Group IP."
        ::= { zxACGpIpEntry 1 }

    zxACGpMaxPrwCount OBJECT-TYPE
        SYNTAX 		Counter
        MAX-ACCESS 	read-create
        STATUS          deprecated
        DESCRIPTION
            "The max preview count of the multicast group."
        ::= { zxACGpIpEntry 2 }

    zxACGpMaxPrwInter OBJECT-TYPE
        SYNTAX 		Counter
        MAX-ACCESS 	read-create
        STATUS          deprecated
        DESCRIPTION
            "The max preview time."
        ::= { zxACGpIpEntry 3 }

    zxACGpPrwResumeInter OBJECT-TYPE
        SYNTAX 		Counter
        MAX-ACCESS 	read-create
        STATUS          deprecated
        DESCRIPTION
            "The interval of two continuous previews."
        ::= { zxACGpIpEntry 4 }

    zxACGpPortList 	OBJECT-TYPE
        SYNTAX 		PortList
        MAX-ACCESS 	read-create
        STATUS      deprecated
        DESCRIPTION
            "port list."
        ::= { zxACGpIpEntry 5 }
	
    zxACGpPortRight OBJECT-TYPE
        SYNTAX 		PortList
        MAX-ACCESS 	read-create
        STATUS      deprecated
        DESCRIPTION
            "The Group Right for multicast."
        ::= { zxACGpIpEntry 6 }

    zxACGpName OBJECT-TYPE
        SYNTAX DisplayString
        MAX-ACCESS read-create
        STATUS current
        DESCRIPTION
            "zxACGpName"
        ::= { zxACGpIpEntry 7 }   

    zxACGpRowStatus OBJECT-TYPE
        SYNTAX 		RowStatus
        MAX-ACCESS 	read-create
        STATUS          current
        DESCRIPTION
            "Row Status of AC Table."
        ::= { zxACGpIpEntry 8 }  
        
    zxACGpViewParamProfile OBJECT-TYPE
        SYNTAX DisplayString
        MAX-ACCESS read-create
        STATUS current
        DESCRIPTION
            "ViewParamProfile name for this Group."
        ::= { zxACGpIpEntry 9 }   
    	


-- Pkg of group 

    zxAcPkgTable OBJECT-TYPE
        SYNTAX SEQUENCE OF zxAcPkgEntry
        MAX-ACCESS not-accessible
        STATUS current
        DESCRIPTION
            "A table that contains Pkg info."
        ::= { zxMulticastCAC 3 }

    zxAcPkgEntry OBJECT-TYPE
        SYNTAX zxAcPkgEntry
        MAX-ACCESS not-accessible
        STATUS current
        DESCRIPTION
            "A list of entries of all Pkg info.
             Pkg is a collection of multicast groups."
        INDEX {zxAcPkgName }
        ::= { zxAcPkgTable 1 }

    zxAcPkgEntry ::= SEQUENCE {
        zxAcPkgName           SnmpAdminString,
        zxAcPkgIndex          INTEGER,
        zxAcPkgDesc           SnmpAdminString,
        zxAcPkgUserRecvPortList    PortList,
		zxAcPkgRowStatus      RowStatus
    }
		
    zxAcPkgName OBJECT-TYPE
        SYNTAX      SnmpAdminString
        MAX-ACCESS  not-accessible
        STATUS      current
        DESCRIPTION
            "Pkg Name is display name,only latin letter permit."
        ::= { zxAcPkgEntry 1 }

    zxAcPkgIndex OBJECT-TYPE
        SYNTAX      INTEGER
        MAX-ACCESS  read-create
        STATUS      current
        DESCRIPTION
            "Pkg index shoulde be one and only,and zxAcPkgGroupsTable will 
            use it as table index of Pkg."
        ::= { zxAcPkgEntry 2 }
        
    zxAcPkgDesc OBJECT-TYPE
        SYNTAX      SnmpAdminString
        MAX-ACCESS  read-create
        STATUS      current
        DESCRIPTION
            "Pkg Name is display name,only latin letter permit."
        ::= { zxAcPkgEntry 3 }

    zxAcPkgUserRecvPortList OBJECT-TYPE
        SYNTAX      PortList
        MAX-ACCESS  read-create
        STATUS      current
        DESCRIPTION
            "RecvPort of User who ordered this pkg."
        ::= { zxAcPkgEntry 4 }

    zxAcPkgRowStatus OBJECT-TYPE
        SYNTAX      RowStatus
        MAX-ACCESS  read-create
        STATUS      current
        DESCRIPTION
            "RowStatus of this row."
        ::= { zxAcPkgEntry 5 }


--  Groups info for Pkg

    zxAcPkgGroupsTable OBJECT-TYPE
        SYNTAX SEQUENCE OF zxAcPkgEntry
        MAX-ACCESS not-accessible
        STATUS current
        DESCRIPTION
            "A table that contains multicast Groups info for pkg."
        ::= { zxMulticastCAC 4 }

    zxAcPkgGroupsEntry OBJECT-TYPE
        SYNTAX zxAcPkgGroupsEntry
        MAX-ACCESS not-accessible
        STATUS current
        DESCRIPTION
            "A list of entries of all PkgGroups info.
             This table indicates Pkg is a collection of multicast groups."
        INDEX {zxAcPkgIndex, zxACGpIp }
        ::= { zxAcPkgGroupsTable 1 }

    zxAcPkgGroupsEntry ::= SEQUENCE {
        zxAcPkgGpAccessRight    INTEGER,
        zxAcPkgGpDesc           SnmpAdminString,
        zxAcPkgGpRowStatus      RowStatus
    }
		

    zxAcPkgGpAccessRight OBJECT-TYPE
         SYNTAX      INTEGER  {
              noRight (0),
              view (1),
              preview (2)
            }
        MAX-ACCESS  read-create
        STATUS      current
        DESCRIPTION
            "User's Right of access multicast group in this pkg."

        DEFVAL { 2 }
        ::= { zxAcPkgGroupsEntry 1 }


    zxAcPkgGpRowStatus OBJECT-TYPE
        SYNTAX      RowStatus
        MAX-ACCESS  read-create
        STATUS      current
        DESCRIPTION
            "RowStatus of this row."
        ::= { zxAcPkgGroupsEntry 2 }
	


-- View(including preview) cfg param profile

    zxAcViewParamProfileTable OBJECT-TYPE
        SYNTAX SEQUENCE OF zxAcViewParamProfileEntry
        MAX-ACCESS not-accessible
        STATUS current
        DESCRIPTION
            "   A table that contains view(including preview)  cfg param profile 
             info.It is used to define group's preview attributes.
             
                When some of the parameters in a view Profile are changed, 
             the new settings shall take effect for the channels using this 
             Profile immediately."
        ::= { zxMulticastCAC 6 }

    zxAcViewParamProfileEntry OBJECT-TYPE
        SYNTAX zxAcViewParamProfileEntry
        MAX-ACCESS not-accessible
        STATUS current
        DESCRIPTION
            "A list of entries of all zxAcViewParamProfile info."
        INDEX {zxAcViewParamProfileName }
        ::= { zxAcViewParamProfileTable 1 }

    zxAcViewParamProfileEntry ::= SEQUENCE {
        zxAcViewParamProfileName  DisplayString,
        zxAcViewParamMaxPrwCount  INTEGER,
        zxAcViewParamMaxPrwInter  INTEGER,
        zxAcViewParamPrwBlackoutInter INTEGER,
        zxAcViewParamProfileRowStatus RowStatus
    }
		
    zxAcViewParamProfileName OBJECT-TYPE
        SYNTAX      DisplayString
        MAX-ACCESS  read-create
        STATUS      current
        DESCRIPTION
            "Profile Name."
        ::= {zxAcViewParamProfileEntry 1 }      
        
		
    zxAcViewParamMaxPrwCount OBJECT-TYPE
        SYNTAX      INTEGER
        MAX-ACCESS  read-create
        STATUS      current
        DESCRIPTION
            "Max Preview Count for channels."
        ::= {zxAcViewParamProfileEntry 2 }      
        
    zxAcViewParamMaxPrwInter OBJECT-TYPE
        SYNTAX      INTEGER
        UNITS       "seconds"
        MAX-ACCESS  read-create
        STATUS      current
        DESCRIPTION
            "Max Preview Count for channels."
        ::= {zxAcViewParamProfileEntry 3 }      

    zxAcViewParamPrwBlackoutInter OBJECT-TYPE
        SYNTAX      INTEGER
        UNITS       "seconds"
        MAX-ACCESS  read-create
        STATUS      current
        DESCRIPTION
            "User's blackout interval of preview for channels."
        ::= {zxAcViewParamProfileEntry 4 }      
        
        
    zxAcViewParamProfileRowStatus OBJECT-TYPE
        SYNTAX      RowStatus
        MAX-ACCESS  read-create
        STATUS      current
        DESCRIPTION
            "RowStatus of this row."
        ::= { zxAcViewParamProfileEntry 5 }    
        
-- ---------------------------------------------------------------------------
--	zxMulticastPRW
-- ---------------------------------------------------------------------------
    zxPRWManageReset OBJECT-TYPE
        SYNTAX 		INTEGER
        MAX-ACCESS 	read-write
        STATUS current
        DESCRIPTION
            "used to manage reset in PRW module,when '1',need to reset."
        ::= { zxMulticastPRW 1 }

    zxPRWResetPeriod	OBJECT-TYPE
        SYNTAX 		INTEGER
        MAX-ACCESS 	read-write
        STATUS current
        DESCRIPTION
            "specify the fix time of reseting the preview management structure."
        ::= { zxMulticastPRW 2 }
    zxPRWResetTime OBJECT-TYPE
        SYNTAX 		Unsigned32
        MAX-ACCESS 	read-write
        STATUS current
        DESCRIPTION
            ""
        ::= { zxMulticastPRW 3 }
 
-- ---------------------------------------------------------------------------
--	zxMulticastCDR
-- ---------------------------------------------------------------------------

    zxCDRMaxSize OBJECT-TYPE
        SYNTAX 		Unsigned32
        MAX-ACCESS 	read-write
        STATUS current
        DESCRIPTION
            "The max size of CDR."
        ::= { zxMulticastCDR 1 }
	
    zxCDRServerIP OBJECT-TYPE
        SYNTAX 		IpAddress
        MAX-ACCESS 	read-write
        STATUS current
        DESCRIPTION
            "The IP of SMS server."
        ::= { zxMulticastCDR 2 }
        
    zxCDRMaxSendInterval	OBJECT-TYPE
        SYNTAX		Unsigned32
        MAX-ACCESS	read-write	
        STATUS	current
        DESCRIPTION
            "The Max Send Interval of CDR Record."
        ::= { zxMulticastCDR 3 }
        
    zxCDREnable OBJECT-TYPE
        SYNTAX 		TruthValue
        MAX-ACCESS 	read-write
        STATUS current
        DESCRIPTION
            "DURABLE: { false )
             Setting this object to true(1) enables CDR .  Setting
             it to false(2) disables CDR."
        ::= { zxMulticastCDR 4 }
        
    zxCDRCurrentRecordNumber OBJECT-TYPE
        SYNTAX   INTEGER
        MAX-ACCESS  read-only
        STATUS current
        DESCRIPTION
            "the number of CDR records"
        ::= { zxMulticastCDR 5 }		
        
    zxCDRDenyEnable OBJECT-TYPE
        SYNTAX   TruthValue
        MAX-ACCESS  read-write
        STATUS current
        DESCRIPTION
            "Setting this object to true(1) enables CDR when the right of user is deny.  Setting
             it to false(2) disables CDR when the right of user is deny."
        ::= { zxMulticastCDR 6 }
        
    zxCDRPreviewEnable OBJECT-TYPE
        SYNTAX   TruthValue
        MAX-ACCESS  read-write
        STATUS current
        DESCRIPTION
            "Setting this object to true(1) enables CDR when the right of user is preview.  Setting
             it to false(2) disables CDR when the right of user is preview."
        ::= { zxMulticastCDR 7 }
   
   zxCDRInterval OBJECT-TYPE
        SYNTAX   Unsigned32(0..360)
        MAX-ACCESS  read-write
        STATUS current
        DESCRIPTION
            "the interval  between two CDR in minutes"
        ::= { zxMulticastCDR 8 }        
   zxCDRReportAction OBJECT-TYPE
        SYNTAX   INTEGER
        MAX-ACCESS  read-write
        STATUS current
        DESCRIPTION
            ""
        ::= { zxMulticastCDR 9 }	
END
