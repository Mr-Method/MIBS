ATM-ZHONGXING-BGS10-MIB	DEFINITIONS ::= BEGIN 
	
--The root of the path.
	
IMPORTS
	MODULE-IDENTITY,OBJECT-TYPE,NOTIFICATION-TYPE,enterprises,Integer32,
	Unsigned32,TimeTicks,Counter32,IpAddress,Gauge32
											FROM SNMPv2-SMI
	AtmAddr									FROM ATM-TC-MIB
	ifIndex,ifOperStatus					FROM IF-MIB
	atmInterfaceConfEntry					FROM ATM-MIB
	lecConfigEntry							FROM LAN-EMULATION-CLIENT-MIB
	elanConfEntry,lecsTlvEntry,lecsConfEntry
											FROM LAN-EMULATION-ELAN-MIB
	lesConfEntry							FROM LAN-EMULATION-LES-MIB
	busConfEntry							FROM LAN-EMULATION-BUS-MIB
	atmfPortEntry							FROM ATM-FORUM-MIB
	entPhysicalContainedIn,	entPhysicalParentRelPos,
	entPhysicalClass						FROM ENTITY-MIB				
	atmfM4TrapAlarmSeverity,atmfM4PlugInUnitEntry,atmfM4PlugInUnitAvailStatus,
	atmfM4TcProtoCurrEntry,atmfM4VpUpcNpcCurrEntry,atmfM4VcUpcNpcCurrEntry,
	atmfM4PlugInUnitOperStatus
											FROM ATM-FORUM-SNMP-M4-MIB
	atmfCESConfEntry						FROM ATMF-CES
	alarmValue,alarmRisingThreshold,alarmFallingThreshold,alarmEntry
											FROM RFC1271-MIB
	TEXTUAL-CONVENTION,RowStatus			FROM SNMPv2-TC
	rs232PortEntry							FROM RFC1317-MIB
	rs232SyncPortEntry						FROM RFC1317-MIB
	x25StatEntry							FROM RFC1382-MIB
	lapbFlowEntry							FROM RFC1381-MIB
	x25ClearedCircuitEntry					FROM RFC1382-MIB
	InterfaceIndex							FROM IF-MIB
	CESConnectionPort						FROM ATMF-CES
	VpiInteger								FROM ATMF-CES
	VciInteger								FROM ATMF-CES;
		
zhongxing MODULE-IDENTITY 
	LAST-UPDATED	"9905171300+0800"
	ORGANIZATION	"ATM Working Group,Zhongxing Telecom. Co."
	CONTACT-INFO	"
					ATM Data & Network Management Group,
					ATM Working Group,
					Nanjing Research Institute,
					Zhongxing Telecom. Co.
					Phone: 86 25 4826606 331
					Fax: 86 25 4806481
					Email:njzxj@public1.ptt.js.cn"
					 
	DESCRIPTION		"The Module for Zhongxing ATM products--ZXBGS10(and its 
					successors)."
	REVISION		"9909021505+0800"
	DESCRIPTION		"The lastest Modification to the Port table."
		::= { enterprises 3092}
			
--The path for zhongxing ATM.
	
zhongxingatm	OBJECT IDENTIFIER	::= { zhongxing 2}
	
--The path for ZXBGS10 and its successors.

zxbgs10mib			OBJECT IDENTIFIER	::= { zhongxingatm 1}

--bgs10SystemConfigure		OBJECT IDENTIFIER	::= { zxbgs10mib 1}	
--bgs10MIBObjects		OBJECT IDENTIFIER	::= { zxbgs10mib 2}
--bgs10RouteMIB			OBJECT IDENTIFIER	::= { zxbgs10mib 3}
--bgs10Alarm			OBJECT IDENTIFIER	::= { zxbgs10mib 4}
--bgs10SvcViewTable		OBJECT IDENTIFIER	::= { zxbgs10mib 5}
--bgs10SvcStatisTable		OBJECT IDENTIFIER	::= { zxbgs10mib 6}
--bgs10CardCtrlTable		OBJECT IDENTIFIER	::= { zxbgs10mib 7}
--bgs10MMLMIB			OBJECT IDENTIFIER	::= { zxbgs10mib 8}
--bgs10DnalMIB			OBJECT IDENTIFIER	::= { zxbgs10mib 9}
--bgs10Pvc			OBJECT IDENTIFIER	::= { zxbgs10mib 10}
--bgs10FrfMIB			OBJECT IDENTIFIER	::= { zxbgs10mib 11}
--bgs10IMA			OBJECT IDENTIFIER	::= { zxbgs10mib 12}
--bgs10ModuleMIB		OBJECT IDENTIFIER	::= { zxbgs10mib 13}
--bgs10SubAttrMIB		OBJECT IDENTIFIER	::= { zxbgs10mib 14}
--bgs10PerformanceMIB		OBJECT IDENTIFIER	::= { zxbgs10mib 15}
--bgs10IspMIB			OBJECT IDENTIFIER	::= { zxbgs10mib 16}
--bgs10M4MIB			OBJECT IDENTIFIER	::= { zxbgs10mib 17}
--bgs10PortMIB			OBJECT IDENTIFIER	::= { zxbgs10mib 18}
--bgs10VpiMapEsVpiMIB		OBJECT IDENTIFIER	::= { zxbgs10mib 19}
--bgs10IfConfigure		OBJECT IDENTIFIER	::= { zxbgs10mib 20 }
--bgs10LecConfigure		OBJECT IDENTIFIER	::= { zxbgs10mib 21 }
--bgs10ElanConfigure		OBJECT IDENTIFIER	::= { zxbgs10mib 22 }
--bgs10LecsConfigure		OBJECT IDENTIFIER	::= { zxbgs10mib 23 }
--bgs10LecsTLV			OBJECT IDENTIFIER	::= { zxbgs10mib 24 }
--bgs10LesConfigure		OBJECT IDENTIFIER	::= { zxbgs10mib 25 }
--bgs10BusConfigure		OBJECT IDENTIFIER	::= { zxbgs10mib 26 }
--bgs10Pvp			OBJECT IDENTIFIER	::= { zxbgs10mib 27 }
--bgs10CesConfigTable		OBJECT IDENTIFIER	::= { zxbgs10mib 28 }
--bgs10E1MIB			OBJECT IDENTIFIER 	::= { zxbgs10mib 29 }
--bgs10Unit			OBJECT IDENTIFIER 	::= { zxbgs10mib 30 }
--bgs10PmMib			OBJECT IDENTIFIER 	::= { zxbgs10mib 31 }
--bgs10M4PlugInUnit		OBJECT IDENTIFIER	::= { zxbgs10mib 32 }
--bgs10NetConfig		OBJECT IDENTIFIER 	::= { zxbgs10mib 33 }
--bgs10TcProtoCurTable		OBJECT IDENTIFIER 	::= { zxbgs10mib 34 }
--bgs10VpUpcNpcCurrTable 	OBJECT IDENTIFIER 	::= { zxbgs10mib 35 }
--bgs10CongestTable		OBJECT IDENTIFIER 	::= { zxbgs10mib 36 }
--bgs10VcUpcNpcCurrTable 	OBJECT IDENTIFIER 	::= { zxbgs10mib 37 }
--bgs10SoftSpecialAlarmTable 	OBJECT IDENTIFIER 	::= { zxbgs10mib 38 }
--bgs10X25			OBJECT IDENTIFIER 	::= { zxbgs10mib 39 }
--bgs10Signal			OBJECT IDENTIFIER 	::= { zxbgs10mib 40 }
--bgs10Ipoa			OBJECT IDENTIFIER	::= { zxbgs10mib 41 }
--bgs10Mpls			OBJECT IDENTIFIER	::= { zxbgs10mib 42 }
--bgs10SPVC			OBJECT IDENTIFIER	::= { zxbgs10mib 43 }
--bgs10CesSPVC			OBJECT IDENTIFIER	::= { zxbgs10mib 44 }
--bgs10SPVP			OBJECT IDENTIFIER	::= { zxbgs10mib 45 }
--bgs10Version			OBJECT IDENTIFIER	::= { zxbgs10mib 46 }
--bgs10LdpTrace			OBJECT IDENTIFIER	::= { zxbgs10mib 47 }
--bgs10PPVCServer		OBJECT IDENTIFIER	::= { zxbgs10mib 48 }
--bgs10NMPS			OBJECT IDENTIFIER	::= { zxbgs10mib 49 }
--bgs10NmsIDInfo		OBJECT IDENTIFIER	::= { zxbgs10mib 50 }
--bgs10NMPSVPTable		OBJECT IDENTIFIER	::= { zxbgs10mib 51 }
--bgs10NMPSFRTable		OBJECT IDENTIFIER	::= { zxbgs10mib 52 }
--bgs10NMPSCESTable		OBJECT IDENTIFIER	::= { zxbgs10mib 53 }
--bgs10NMSServer		OBJECT IDENTIFIER	::= { zxbgs10mib 54 }
--dsx1ConfigTable		OBJECT IDENTIFIER	::= { zxbgs10mib 55 }
--dsx3ConfigTable		OBJECT IDENTIFIER	::= { zxbgs10mib 56 }
--bgs10TSTable 			OBJECT IDENTIFIER	::= { zxbgs10mib 57 }
--bgs10Rs232PortTable		OBJECT IDENTIFIER	::= { zxbgs10mib 58 }
--bgs10Tp25ConfigTable		OBJECT IDENTIFIER	::= { zxbgs10mib 59 }
--bgs10SDHConfigTable		OBJECT IDENTIFIER	::= { zxbgs10mib 60 }
--bgs10IMAGroupConfTable 	OBJECT IDENTIFIER	::= { zxbgs10mib 61 }
--bgs10IMALinkConfTable 	OBJECT IDENTIFIER	::= { zxbgs10mib 62 }
--bgs10LogicIfDlciTable 	OBJECT IDENTIFIER	::= { zxbgs10mib 63 }
--bgs10LogicIfIPTable 		OBJECT IDENTIFIER	::= { zxbgs10mib 64 }
--bgs10VLANPortConfigTable 	OBJECT IDENTIFIER	::= { zxbgs10mib 65 }
--bgs10VLANBridgeConfigTable 	OBJECT IDENTIFIER	::= { zxbgs10mib 66 }
--bgs10VLANFilterConfigTable 	OBJECT IDENTIFIER	::= { zxbgs10mib 67 }
--bgs10VLANConfigTable 		OBJECT IDENTIFIER	::= { zxbgs10mib 68 }
--bgs10IMAGroupStatTable 	OBJECT IDENTIFIER	::= { zxbgs10mib 69 }
--bgs10IMALinkStatTable 	OBJECT IDENTIFIER	::= { zxbgs10mib 70 }
--bgs10MPEGNodePriorityTable	OBJECT IDENTIFIER	::= { zxbgs10mib 71 }
--bgs10MPEGEncodePortTable	OBJECT IDENTIFIER	::= { zxbgs10mib 72 }
--bgs10radiusClient			OBJECT IDENTIFIER	::= { zxbgs10mib 73 }
--bgs10radIpAddr			OBJECT IDENTIFIER	::= { zxbgs10mib 74 }
--bgs10PPPFilter			OBJECT IDENTIFIER	::= { zxbgs10mib 75 }
--bgs10FilterRule			OBJECT IDENTIFIER	::= { zxbgs10mib 76 }
--bgs10POS61195				OBJECT IDENTIFIER	::= { zxbgs10mib 77 }
--bgs10PMPtable				OBJECT IDENTIFIER	::= { zxbgs10mib 78 }


--Traps for ZXB10 and its successors.

zxbgs10Traps			OBJECT IDENTIFIER ::= { zhongxingatm 2 }

--zxbgs10PowerBoardTrap		OBJECT IDENTIFIER	::= { zxbgs10Traps 1 }
--bgs10ClkBoardTrap		OBJECT IDENTIFIER	::= { zxbgs10Traps 2 }
--bgs10NetCardTraps		OBJECT IDENTIFIER	::= { zxbgs10Traps 3 }
--bgs10LICTraps			OBJECT IDENTIFIER 	::= { zxbgs10Traps 4 }
--bgs10CommSDHTraps		OBJECT IDENTIFIER 	::= { zxbgs10Traps 5 }
--bgs10FrfE1Traps		OBJECT IDENTIFIER 	::= { zxbgs10Traps 6 }
--bgs10FrfFrTraps		OBJECT IDENTIFIER 	::= { zxbgs10Traps 7 }
--bgs10Cardtraps		OBJECT IDENTIFIER	::= { zxbgs10Traps 8 }
--bgs10PerfTraps		OBJECT IDENTIFIER	::= { zxbgs10Traps 9 }
--bgs10E1CellTraps		OBJECT IDENTIFIER	::= { zxbgs10Traps 10 }
--bgs10FanTraps			OBJECT IDENTIFIER	::= { zxbgs10Traps 11 }
--bgs10SoftwareTraps	OBJECT IDENTIFIER	::= { zxbgs10Traps 12 }
--bgs10X25Traps			OBJECT IDENTIFIER	::= { zxbgs10Traps 13 }
--bgs10ImaTraps			OBJECT IDENTIFIER	::= { zxbgs10Traps 14 }
--bgs10Rs232Trap		OBJECT IDENTIFIER	::= { zxbgs10Traps 15 }
--bgs10E3Trap			OBJECT IDENTIFIER	::= { zxbgs10Traps 16 }

--Data type for zhongxing ATM MIB.

UShort	::=  TEXTUAL-CONVENTION
	STATUS		current
	DESCRIPTION
		"The 16-bit unsigned short integer."
	SYNTAX		INTEGER (0..65535)
	
UChar	::= TEXTUAL-CONVENTION
	STATUS		current
	DESCRIPTION
		"The 8-bit unsigned integer."
	SYNTAX	INTEGER (0..255)
		
UCHAR	::= TEXTUAL-CONVENTION
	STATUS		current
	DESCRIPTION
		"The 8-bit unsigned integer."
	SYNTAX	INTEGER (0..255)
	
X25Address	::= TEXTUAL-CONVENTION
	STATUS		current
	DESCRIPTION
		"The X.25 Address."
	SYNTAX	OCTET STRING(SIZE(8))
		
--This MIB module consists of the following groups.
--	(1)	My system configuration.
--	(2)	neighbor system configuration.
--	(3)	Chain Table.
--	(4)	Route Group.
--	(5)	Trunk Table.
--	(6)	Noc Table
--	(7)	The Terminater Number(DNHM) Table.
--	(8)	The Dn Module Table.
--	(9)	The DAS	table.
--	(10)The DNAL table.
--	(11)PVC table
--	(12)Frame Relay table.
--	(13)The DDI Table.
--	(14)The Module Table.
--	(15)The Subscriber Attribute's series.
--	(16)The Performance Table.
--	(17)The Signal Timer Table.
--	(18)The Signal Configuration table.
--	(19)The ISP Table.
--	(20)The M4 NE Table.
--	(21)The Port Table
--	(22)The VPI Map Es VPI Table.
--	(23)The Extensions to the interface configuration.
--	(24)The Extensions to the LEC configuration table.
--	(25)The Extensions to the ELAN configuration table.
--	(26)The Extensions to the LECS Configuration table.
--	(27)The Extensions to the LECS TLV Table.
--	(28)The Extensions to the LES Configuration table.
--	(29)The Extensions to the BUS configuration table.
--	(30)The Extensions to the Port Table.
 
--ZXBGS10 System Configuration.
bgs10SystemConfigure	OBJECT IDENTIFIER	::= { zxbgs10mib 1}
	
--The ZXBGS10 My configuration table extension 
bgs10MyConfigure		OBJECT IDENTIFIER ::= { bgs10SystemConfigure 1}

bgs10MyConfigureOfficType OBJECT-TYPE
	SYNTAX		INTEGER {	otHost(1),
							otSwitch(2),
							otDevice(3)}
	MAX-ACCESS	read-only
	STATUS		current
	DESCRIPTION
		"The type of switcher.according to the location,capability,
		the ZXBS10 ATM switcher are distinguished into three types:
		----otHost:backbone ATM Switcher
		----otSwitch;edge ATM Switcher
		----otDevice:access ATM Switcher."
	::= { bgs10MyConfigure 1 }
	
bgs10MyConfigureNetPrefix	OBJECT-TYPE
	SYNTAX		OCTET STRING(SIZE(13))
	MAX-ACCESS	read-only
	STATUS		current
	DESCRIPTION
		"Network prefix."
	::= { bgs10MyConfigure 2 }
		
bgs10MyConfigureNet	OBJECT-TYPE
	SYNTAX		INTEGER{ pstn(1),
						 rwtn(2),
						 nftn(3),
						 eptn(4),
						 cltn(5),
						 plmn(6)}
	MAX-ACCESS	read-only
	STATUS		current
	DESCRIPTION
		"the type of the switcher in which the ATM Switcher is located
		notmally the network types are:
		----PSTN:public switching telephone network
		----RWTN:railway telephone network
		----NFTN:national defence telephone network
		----EPTN:electrical power telephone network
		----CLTN:coal telephone network
		----PLMN:public land mobile network"
	::= { bgs10MyConfigure 3 }
		
bgs10MyConfigureCacArithmetic OBJECT-TYPE
	SYNTAX		INTEGER{pcr(1),add(2)}
	MAX-ACCESS	read-only
	STATUS		current
	DESCRIPTION
		"the choice of CAC arithmetic."
	::= { bgs10MyConfigure 4 }
		
bgs10MyConfigureFeeIntevalTime	OBJECT-TYPE
	SYNTAX		INTEGER
	MAX-ACCESS	read-write
	STATUS		current
	DESCRIPTION
		"the Interval for PVC/PVP connection accounting.according to 
		the standard comment of Information Industrial Minstry,It 
		should not be beyond 24 hours.
		Here it demands the unit be hours."
	::= { bgs10MyConfigure 5 }
	
bgs10MyConfigureAlarmNo	OBJECT-TYPE
	SYNTAX		INTEGER
	MAX-ACCESS	read-write
	STATUS		current
	DESCRIPTION
		"The no of the Current Alarm"
	::= { bgs10MyConfigure 6 }

--The Supplyment for M4 NE.
bgs10MIBObjects			OBJECT IDENTIFIER	::= { zxbgs10mib 2}

bgs10MIBPortPerformanceTime	OBJECT-TYPE 
	SYNTAX		Unsigned32
	MAX-ACCESS	read-write
	STATUS		current
	DESCRIPTION
		"The network element'port porformance's time.It is a supplyment to M4."
	::= { bgs10MIBObjects 1}
	
bgs10MIBUpcPerformanceTime	OBJECT-TYPE 
	SYNTAX		Unsigned32
	MAX-ACCESS	read-write
	STATUS		current
	DESCRIPTION
		"The network element's UPC porformance's time.It is a supplyment to M4."
	::= { bgs10MIBObjects 2}

bgs10MIBSVCViewPerformanceTime	OBJECT-TYPE 
	SYNTAX		Unsigned32
	MAX-ACCESS	read-write
	STATUS		current
	DESCRIPTION
		"The network element's SVC view porformance's time.It is a supplyment to M4."
	::= { bgs10MIBObjects 3}
	
bgs10MIBSpecialMMLFlag	OBJECT-TYPE 
	SYNTAX		UChar
	MAX-ACCESS	read-write
	STATUS		current
	DESCRIPTION
		"The special man-machine command's flag."
	::= { bgs10MIBObjects 4}
	
bgs10MIBClockBench8KHZ1Port	OBJECT-TYPE 
	SYNTAX		UShort
	MAX-ACCESS	read-write
	STATUS		current
	DESCRIPTION
		"The port number of No.1 Clock bench 8-KHz."
	::= { bgs10MIBObjects 5}

bgs10MIBClockBench8KHZ2Port	OBJECT-TYPE 
	SYNTAX		UShort
	MAX-ACCESS	read-write
	STATUS		current
	DESCRIPTION
		"The port number of No.2 Clock bench 8-KHz."
	::= { bgs10MIBObjects 6}
	
bgs10MIBAbsoluteDate	OBJECT-TYPE 
	SYNTAX		Unsigned32
	MAX-ACCESS	read-write
	STATUS		current
	DESCRIPTION
		"The NE's Absolute Date."
	::= { bgs10MIBObjects 7}
		
bgs10MIBAbsoluteTime	OBJECT-TYPE 
	SYNTAX		Unsigned32
	MAX-ACCESS	read-write
	STATUS		current
	DESCRIPTION
		"The NE's Absolute Time."
	::= { bgs10MIBObjects 8}
	
bgs10MIBMemoryStore		OBJECT-TYPE 
	SYNTAX		OCTET STRING(SIZE(40))
	MAX-ACCESS	read-write
	STATUS		current
	DESCRIPTION
		"."
	::= { bgs10MIBObjects 9}
	
bgs10MIBClockBench19MHZPort	OBJECT-TYPE	
	SYNTAX		UShort
	MAX-ACCESS	read-write
	STATUS		current
	DESCRIPTION
		"."
	::= { bgs10MIBObjects 10}
	
bgs10MIBMemoryLoad		OBJECT-TYPE 
	SYNTAX		OCTET STRING(SIZE(40))
	MAX-ACCESS	read-write
	STATUS		current
	DESCRIPTION
		"."
	::= { bgs10MIBObjects 11}

bgs10MIBwIfindex		OBJECT-TYPE 
	SYNTAX		UShort
	MAX-ACCESS	read-write
	STATUS		current
	DESCRIPTION
		"."
	::= { bgs10MIBObjects 12}

bgs10MIBILMISwitch		OBJECT-TYPE 
	SYNTAX		UShort
	MAX-ACCESS	read-write
	STATUS		current
	DESCRIPTION
		"."
	::= { bgs10MIBObjects 13}

--The Route Group		
bgs10RouteMIB			OBJECT IDENTIFIER	::= { zxbgs10mib 3}
	
-- Defintion of objects for route set table.
	
bgs10RouteTable	OBJECT-TYPE
	SYNTAX		SEQUENCE OF BGS10RouteEntry
	MAX-ACCESS	not-accessible
	STATUS		current
	DESCRIPTION
		"A list of the route information."
	::= { bgs10RouteMIB 1}
		
bgs10RouteEntry	OBJECT-TYPE
	SYNTAX		BGS10RouteEntry
	MAX-ACCESS	not-accessible
	STATUS		current
	DESCRIPTION
		"An entry to the table."
	INDEX	{ bgs10RouteAtmAddress }
	::= { bgs10RouteTable 1}
		
BGS10RouteEntry ::=
	SEQUENCE {
		bgs10RouteRowStatus			INTEGER,
		bgs10RouteAtmAddressStatus	INTEGER,
		bgs10RouteOperateStatus		INTEGER,
		bgs10RouteNodeNum			UChar,
		bgs10RouteAtmAddress		OCTET STRING,
		bgs10RouteServiceType		INTEGER,
		bgs10RouteRouteSet			UShort,
		bgs10RouteModule			UChar,
		bgs10RouteLength			UChar,
		bgs10RouteServicePID		OCTET STRING(SIZE(4)),
		bgs10RouteDefaultAddrFlag	INTEGER,
		bgs10RouteAddressPlan		INTEGER,
		bgs10RouteAlternateRouteDirect UShort,
		bgs10RouteAlternateRouteTwo UShort,
		bgs10RouteAlternateRouteThree UShort,
		bgs10RouteCurRouteSet       UShort,
		bgs10RouteRouteDirect 		UShort,
		bgs10RouteRouteTwo          UShort,
		bgs10RouteRouteThree        UShort
		}
	
bgs10RouteRowStatus	OBJECT-TYPE
	SYNTAX		INTEGER
	MAX-ACCESS	read-create
	STATUS		current
	DESCRIPTION	
		"the conteptual row."
	::= { bgs10RouteEntry 1}
		
bgs10RouteAtmAddressStatus		OBJECT-TYPE
	SYNTAX		INTEGER
	MAX-ACCESS	read-create
	STATUS		current
	DESCRIPTION
		"the status of the ATM address: 0--IISP configure address,1--ILMI."
	::= { bgs10RouteEntry 2}
		
bgs10RouteOperateStatus		OBJECT-TYPE
	SYNTAX		INTEGER	{	up(0),
							down(1)
						}
	MAX-ACCESS	read-create
	STATUS		current
	DESCRIPTION
		"the node operate status."
	::= { bgs10RouteEntry 3}
	
bgs10RouteNodeNum		OBJECT-TYPE
	SYNTAX		UChar
	MAX-ACCESS	read-create
	STATUS		current
	DESCRIPTION
		"the Node Number."
	::= { bgs10RouteEntry 4}
	
bgs10RouteAtmAddress		OBJECT-TYPE
	SYNTAX		OCTET STRING(SIZE(20))
	MAX-ACCESS	read-create
	STATUS		current
	DESCRIPTION
		"the ATM address."
	::= { bgs10RouteEntry 5}
	
bgs10RouteServiceType		OBJECT-TYPE
	SYNTAX		INTEGER
	MAX-ACCESS	read-create
	STATUS		current
	DESCRIPTION
		"Route No.4."
	::= { bgs10RouteEntry 6}	
		
bgs10RouteRouteSet		OBJECT-TYPE
	SYNTAX		UShort
	MAX-ACCESS	read-create
	STATUS		current
	DESCRIPTION
		"RouteSet."
	::= { bgs10RouteEntry 7}

bgs10RouteModule		OBJECT-TYPE
	SYNTAX		UChar
	MAX-ACCESS	read-create
	STATUS		current
	DESCRIPTION
		"Module No.."
	::= { bgs10RouteEntry 8}
	
bgs10RouteLength		OBJECT-TYPE
	SYNTAX		UChar
	MAX-ACCESS	read-create
	STATUS		current
	DESCRIPTION
		"route's length."
	::= { bgs10RouteEntry 9}
	
bgs10RouteServicePID	OBJECT-TYPE
	SYNTAX		OCTET STRING(SIZE(4))
	MAX-ACCESS	read-create
	STATUS		current
	DESCRIPTION
		"Service's PID."
	::= { bgs10RouteEntry 10}
	
bgs10RouteDefaultAddrFlag		OBJECT-TYPE
	SYNTAX		INTEGER{ default(0),
						 no-default(1)
					   }
	MAX-ACCESS	read-create
	STATUS		current
	DESCRIPTION
		"Address's default flag."
	::= { bgs10RouteEntry 11}
	
bgs10RouteAddressPlan	OBJECT-TYPE
	SYNTAX		INTEGER{ unknown(0),
						 isdn(1),
						 nsap(2),
						 private(9),
						 reversed(15)
					   }
	MAX-ACCESS	read-create
	STATUS		current
	DESCRIPTION
		"Address's default flag."
	::= { bgs10RouteEntry 12}
	
bgs10RouteAlternateRouteDirect		OBJECT-TYPE
	SYNTAX		UShort
	MAX-ACCESS	read-create
	STATUS		current
	DESCRIPTION
			"alternate_route_direct."
	::= { bgs10RouteEntry 13}
	
bgs10RouteAlternateRouteTwo 		OBJECT-TYPE
	SYNTAX		UShort
	MAX-ACCESS	read-create
	STATUS		current
	DESCRIPTION
			"alternate_route_two."
	::= { bgs10RouteEntry 14}

bgs10RouteAlternateRouteThree		OBJECT-TYPE
	SYNTAX		UShort
	MAX-ACCESS	read-create
	STATUS		current
	DESCRIPTION
			"alternate_route_three."
	::= { bgs10RouteEntry 15}
	
bgs10RouteCurRouteSet		       OBJECT-TYPE
	SYNTAX		UShort
	MAX-ACCESS	read-create
	STATUS		current
	DESCRIPTION
			"CurRouteSet."
	::= { bgs10RouteEntry 16}
	
bgs10RouteRouteDirect		OBJECT-TYPE
	SYNTAX		UShort
	MAX-ACCESS	read-create
	STATUS		current
	DESCRIPTION
			"route_direct."
	::= { bgs10RouteEntry 17}
	
bgs10RouteRouteTwo		OBJECT-TYPE
	SYNTAX		UShort
	MAX-ACCESS	read-create
	STATUS		current
	DESCRIPTION
			"route_two."
	::= { bgs10RouteEntry 18}
	
bgs10RouteRouteThree		OBJECT-TYPE
	SYNTAX		UShort
	MAX-ACCESS	read-create
	STATUS		current
	DESCRIPTION
			"route_three."
	::= { bgs10RouteEntry 19}	
-- Defintion of objects for route topology table.
	
bgs10TopTable	OBJECT-TYPE
	SYNTAX		SEQUENCE OF BGS10TopEntry
	MAX-ACCESS	not-accessible
	STATUS		current
	DESCRIPTION
		"A list of the route information."
	::= { bgs10RouteMIB 2}
		
bgs10TopEntry	OBJECT-TYPE
	SYNTAX		BGS10TopEntry
	MAX-ACCESS	not-accessible
	STATUS		current
	DESCRIPTION
		"the entry ."
	INDEX { bgs10TopSourceNode,
			bgs10TopDestNode
			}
	::= { bgs10TopTable 1}
		
BGS10TopEntry ::=
	SEQUENCE {
		bgs10TopRowStatus		RowStatus,
		bgs10TopOperateStatus	UChar,
        bgs10TopSourceNode		UChar,
        bgs10TopDestNode		UChar,
        bgs10TopCost			UChar
       }
       
bgs10TopRowStatus	OBJECT-TYPE
    SYNTAX		RowStatus
    MAX-ACCESS	read-create
    STATUS		current
    DESCRIPTION
    	"the conceptual row."
    ::={ bgs10TopEntry 1}
       
bgs10TopOperateStatus	OBJECT-TYPE
    SYNTAX		UChar
    MAX-ACCESS	read-create
    STATUS		current
    DESCRIPTION
    	"the operate status."
    ::= { bgs10TopEntry 2}
    	
bgs10TopSourceNode	OBJECT-TYPE
    SYNTAX		UChar
    MAX-ACCESS	read-create
    STATUS		current
    DESCRIPTION
    	"the source node."
    ::= { bgs10TopEntry 3}
    	
bgs10TopDestNode	OBJECT-TYPE
    SYNTAX		UChar
    MAX-ACCESS	read-create
    STATUS		current
    DESCRIPTION
    	"the destistion node."
    ::= { bgs10TopEntry 4}
    
bgs10TopCost	  OBJECT-TYPE
	SYNTAX		UChar
	MAX-ACCESS	read-create
	STATUS		current
	DESCRIPTION
		"the cost."
	::= { bgs10TopEntry 5 }

--the Alarm Table, and it's the supplyment to the Alarm table.in RFC1271 
bgs10Alarm			OBJECT IDENTIFIER	::= { zxbgs10mib 4}

bgs10AlarmTable		OBJECT-TYPE
	SYNTAX		SEQUENCE OF BGS10AlarmEntry
	MAX-ACCESS	not-accessible
	STATUS		current
	DESCRIPTION
		"A supplyment to RFC1271."
	::= { bgs10Alarm 1}
	
bgs10AlarmEntry	OBJECT-TYPE
	SYNTAX		BGS10AlarmEntry
	MAX-ACCESS	not-accessible
	STATUS		current
	DESCRIPTION
		"An Entry to bgs10AlarmTable."
	AUGMENTS { alarmEntry }
	::= { bgs10AlarmTable 1}
	
BGS10AlarmEntry ::=
	SEQUENCE {
		bgs10AlarmRowStatus							RowStatus,
		bgs10AlarmRisingOrFallingThresholdStatus	UCHAR
		
		}
	
bgs10AlarmRowStatus		OBJECT-TYPE
	SYNTAX		RowStatus
	MAX-ACCESS	read-create
	STATUS		current
	DESCRIPTION
		"The conceptal row staus ."
	::= { bgs10AlarmEntry 1}

bgs10AlarmRisingOrFallingThresholdStatus	OBJECT-TYPE
	SYNTAX		UCHAR
	MAX-ACCESS	read-create
	STATUS		current
	DESCRIPTION
		"The threshold's status."
	::= { bgs10AlarmEntry 2}
	
--The SVC view data.

bgs10SvcViewTable		OBJECT-TYPE
	SYNTAX		SEQUENCE OF BGS10SvcViewEntry
	MAX-ACCESS	not-accessible
	STATUS		current
	DESCRIPTION
		"A list of SVC view data."
	::= { zxbgs10mib 5}

bgs10SvcViewEntry 	OBJECT-TYPE
	SYNTAX		BGS10SvcViewEntry
	MAX-ACCESS	not-accessible
	STATUS		current
	DESCRIPTION
		"An entry in the table."
	INDEX {	bgs10ModuleNo,
			bgs10PortNo,
			bgs10DataViewNo
		}
	::= { bgs10SvcViewTable 1}
	
BGS10SvcViewEntry	::= 
	SEQUENCE {
		bgs10SvcViewRowStatus			RowStatus,
		bgs10SvcViewTime				Unsigned32,
		bgs10SvcViewCallFlag			UChar,
		bgs10SvcViewCau					UChar,
		bgs10SvcViewForwardBandwidth	Unsigned32,
		bgs10SvcViewBackwardBandwidth	Unsigned32,
		bgs10SvcViewCalledAddress		OCTET STRING(SIZE(20)),
		bgs10SvcViewCalledSubaddress	OCTET STRING(SIZE(20)),
		bgs10SvcViewCallingAddress		OCTET STRING(SIZE(20)),
		bgs10SvcViewCallingSubaddress	OCTET STRING(SIZE(20)),
		bgs10SvcViewModule				UChar,				
		bgs10SvcViewPort				UChar,
		bgs10SvcViewNumber				UChar
	}
	
bgs10SvcViewRowStatus	OBJECT-TYPE
	SYNTAX		RowStatus
	MAX-ACCESS	read-create
	STATUS		current
	DESCRIPTION
		"The row status."
	::= { bgs10SvcViewEntry 1 }
	
	
bgs10SvcViewTime	OBJECT-TYPE
	SYNTAX		Unsigned32
	MAX-ACCESS	read-create
	STATUS		current
	DESCRIPTION
		"the Time."
	::= { bgs10SvcViewEntry 2 }
	
bgs10SvcViewCallFlag	OBJECT-TYPE
	SYNTAX		UChar
	MAX-ACCESS	read-create
	STATUS		current
	DESCRIPTION
		"the call flag."
	::= { bgs10SvcViewEntry 3 }
	
bgs10SvcViewCau		OBJECT-TYPE
	SYNTAX		UChar
	MAX-ACCESS	read-create
	STATUS		current
	DESCRIPTION
		"the cau?."
	::= { bgs10SvcViewEntry 4 }
	
bgs10SvcViewForwardBandwidth	OBJECT-TYPE
	SYNTAX		Unsigned32
	MAX-ACCESS	read-create
	STATUS		current
	DESCRIPTION
		"the forward band width."
	::= { bgs10SvcViewEntry 5 }
	
bgs10SvcViewBackwardBandwidth		OBJECT-TYPE
	SYNTAX		Unsigned32
	MAX-ACCESS	read-create
	STATUS		current
	DESCRIPTION
		"the backward band width."
	::= { bgs10SvcViewEntry 6 }
	
bgs10SvcViewCalledAddress	OBJECT-TYPE
	SYNTAX		OCTET STRING(SIZE(20))
	MAX-ACCESS	read-create
	STATUS		current
	DESCRIPTION
		"The called address."
	::= { bgs10SvcViewEntry 7 }
	
bgs10SvcViewCalledSubaddress	OBJECT-TYPE
	SYNTAX		OCTET STRING(SIZE(20))
	MAX-ACCESS	read-create
	STATUS		current
	DESCRIPTION
		"The called sub-address."
	::= { bgs10SvcViewEntry 8 }
	
bgs10SvcViewCallingAddress		OBJECT-TYPE
	SYNTAX		OCTET STRING(SIZE(20))
	MAX-ACCESS	read-create
	STATUS		current
	DESCRIPTION
		"The calling address."
	::= { bgs10SvcViewEntry 9 }
	
bgs10SvcViewCallingSubaddress	OBJECT-TYPE
	SYNTAX		OCTET STRING(SIZE(20))
	MAX-ACCESS	read-create
	STATUS		current
	DESCRIPTION
		"The calling sub-address."
	::= { bgs10SvcViewEntry 10 }

bgs10SvcViewModule			OBJECT-TYPE
	SYNTAX		UChar
	MAX-ACCESS	read-create
	STATUS		current
	DESCRIPTION
		"The module No.."
	::= { bgs10SvcViewEntry 11 }
	
bgs10SvcViewPort			OBJECT-TYPE
	SYNTAX		UChar
	MAX-ACCESS	read-create
	STATUS		current
	DESCRIPTION
		"The port No.."
	::= { bgs10SvcViewEntry 12 }
	
bgs10SvcViewNumber			OBJECT-TYPE
	SYNTAX		UChar
	MAX-ACCESS	read-create
	STATUS		current
	DESCRIPTION
		"The view number.."
	::= { bgs10SvcViewEntry 13 }
	
--The SVC statistics data table.
bgs10SvcStatisTable	OBJECT-TYPE
 	SYNTAX		SEQUENCE OF BGS10SvcStatisEntry
	MAX-ACCESS	not-accessible
	STATUS		current
	DESCRIPTION
		"A list of SVC statistics data."
	::= { zxbgs10mib 6}

bgs10SvcStatisEntry		OBJECT-TYPE
	SYNTAX		BGS10SvcStatisEntry
	MAX-ACCESS	not-accessible
	STATUS		current
	DESCRIPTION
		"An Enrty to the table."
	INDEX {	bgs10SvcStatisModule,
			bgs10SvcStatisPort
		}
	::= { bgs10SvcStatisTable 1 }
	
BGS10SvcStatisEntry	::= 
	SEQUENCE {
		bgs10SvcStatisRowStatus				RowStatus,
		bgs10SvcStatisViewActionFlag		UChar,
		bgs10SvcStatisModule				UChar,
		bgs10SvcStatisPort					UChar,
		bgs10SvcStatisViewTimeInterval		Unsigned32,
		bgs10SvcStatisTotalCallCounter		Unsigned32,
		bgs10SvcStatisSuccessCallCounter	Unsigned32,
		bgs10SvcStatisFeeFlag				UChar
	}
	
bgs10SvcStatisRowStatus		OBJECT-TYPE
	SYNTAX		RowStatus
	MAX-ACCESS	read-create
	STATUS		current
	DESCRIPTION
		"The row status."
	::= { bgs10SvcStatisEntry 1}
	
bgs10SvcStatisViewActionFlag	OBJECT-TYPE
	SYNTAX		UChar
	MAX-ACCESS	read-create
	STATUS		current
	DESCRIPTION
		"The action flag."
	::= { bgs10SvcStatisEntry 2}
	
bgs10SvcStatisModule	OBJECT-TYPE
	SYNTAX		UChar
	MAX-ACCESS	read-create
	STATUS		current
	DESCRIPTION
		"The module No.."
	::= { bgs10SvcStatisEntry 3}
	
bgs10SvcStatisPort	OBJECT-TYPE
	SYNTAX		UChar
	MAX-ACCESS	read-create
	STATUS		current
	DESCRIPTION
		"The port No.."
	::= { bgs10SvcStatisEntry 4}
	
bgs10SvcStatisViewTimeInterval	OBJECT-TYPE
	SYNTAX		Unsigned32
	MAX-ACCESS	read-create
	STATUS		current
	DESCRIPTION
		"The time interval."
	::= { bgs10SvcStatisEntry 5}
	
bgs10SvcStatisTotalCallCounter	OBJECT-TYPE
	SYNTAX		Unsigned32
	MAX-ACCESS	read-create
	STATUS		current
	DESCRIPTION
		"The total call counter."
	::= { bgs10SvcStatisEntry 6}
	
bgs10SvcStatisSuccessCallCounter	OBJECT-TYPE
	SYNTAX		Unsigned32
	MAX-ACCESS	read-create
	STATUS		current
	DESCRIPTION
		"The successful call counter."
	::= { bgs10SvcStatisEntry 7}

bgs10SvcStatisFeeFlag		OBJECT-TYPE
	SYNTAX		UChar
	MAX-ACCESS	read-create
	STATUS		current
	DESCRIPTION
		"The fee flag."
	::= { bgs10SvcStatisEntry 8}
	
--The Card Control data table

bgs10CardCtrlTable	OBJECT-TYPE
	SYNTAX		SEQUENCE OF BGS10CardCtrlEntry
	MAX-ACCESS	not-accessible
	STATUS		current
	DESCRIPTION
		"A list of card control data information entries."
	::= { zxbgs10mib 7}

bgs10CardCtrlEntry	OBJECT-TYPE
	SYNTAX		BGS10CardCtrlEntry
	MAX-ACCESS	not-accessible
	STATUS		current
	DESCRIPTION
		"An entry in the table."
	INDEX {	bgs10ModuleNo }
	::= { bgs10CardCtrlTable 1}
	
BGS10CardCtrlEntry ::= 
	SEQUENCE {
		bgs10CardCtrlRowStatus		RowStatus,
		bgs10CardCtrlControlData	UChar,
		bgs10CardCtrlDAHigh			UChar,
		bgs10CardCtrlDALow			UChar,
		bgs10CardCtrlDataLen		UChar,
		bgs10CardCtrlClockStatus	OCTET STRING(SIZE(7))
	}                               
	
bgs10CardCtrlRowStatus		OBJECT-TYPE
	SYNTAX		RowStatus
	MAX-ACCESS	read-create
	STATUS		current
	DESCRIPTION
		"The conceptal row status."
	::= { bgs10CardCtrlEntry 1}
	
bgs10CardCtrlControlData	OBJECT-TYPE
	SYNTAX		UChar
	MAX-ACCESS	read-create
	STATUS		current
	DESCRIPTION
		"The control data."
	::= { bgs10CardCtrlEntry 2}
	
bgs10CardCtrlDAHigh			OBJECT-TYPE
	SYNTAX		UChar
	MAX-ACCESS	read-create
	STATUS		current
	DESCRIPTION
		"The data's high part."
	::= { bgs10CardCtrlEntry 3}
	
bgs10CardCtrlDALow			OBJECT-TYPE
	SYNTAX		UChar
	MAX-ACCESS	read-create
	STATUS		current
	DESCRIPTION
		"The data's low part."
	::= { bgs10CardCtrlEntry 4}
	
bgs10CardCtrlDataLen		OBJECT-TYPE
	SYNTAX		UChar
	MAX-ACCESS	read-create
	STATUS		current
	DESCRIPTION
		"The data's length."
	::= { bgs10CardCtrlEntry 5}
	
bgs10CardCtrlClockStatus	OBJECT-TYPE
	SYNTAX		OCTET STRING(SIZE(7))
	MAX-ACCESS	read-create
	STATUS		current
	DESCRIPTION
		"The data's length."
	::= { bgs10CardCtrlEntry 6}
	
--Man-Machine Language MIB
bgs10MMLResultTable	OBJECT-TYPE
	SYNTAX		SEQUENCE OF BGS10MMLResultEntry
	MAX-ACCESS	not-accessible
	STATUS		current
	DESCRIPTION
		"A list of Man-Machine language."
	::= { zxbgs10mib 8}
		
bgs10MMLResultEntry	OBJECT-TYPE
	SYNTAX		BGS10MMLResultEntry
	MAX-ACCESS	not-accessible
	STATUS		current
	DESCRIPTION
		"An entry in the table."
	INDEX {	bgs10MessageNo	}
	::= { bgs10MMLResultTable 1}
	
BGS10MMLResultEntry ::=
	SEQUENCE {
		bgs10MMLResultRowStatus		RowStatus,
		bgs10MMLResultErrNumber		UShort
		}
		
bgs10MMLResultRowStatus	OBJECT-TYPE
	SYNTAX		RowStatus
	MAX-ACCESS	read-create
	STATUS		current
	DESCRIPTION
		"row status."
	::= { bgs10MMLResultEntry 1}
	
bgs10MMLResultErrNumber		OBJECT-TYPE
	SYNTAX		UShort
	MAX-ACCESS	read-create
	STATUS		current
	DESCRIPTION
		"row status."
	::= { bgs10MMLResultEntry 2}

--This Node is specially for Index
bgs10MIBIndex			OBJECT IDENTIFIER	::= { zxbgs10mib 9}

bgs10MessageNo	OBJECT-TYPE
	SYNTAX		INTEGER
	MAX-ACCESS	not-accessible
	STATUS		current
	DESCRIPTION
		"For MML table."
	::= { bgs10MIBIndex 1}
	
bgs10ModuleNo	OBJECT-TYPE
	SYNTAX		INTEGER
	MAX-ACCESS	not-accessible
	STATUS		current
	DESCRIPTION
		"The 8-bit unsigned integer."
	::= { bgs10MIBIndex 2}
	
bgs10PortNo	OBJECT-TYPE
	SYNTAX		INTEGER
	MAX-ACCESS	not-accessible
	STATUS		current
	DESCRIPTION
		"The 8-bit unsigned integer."
	::= { bgs10MIBIndex 3}
	
bgs10DataViewNo	OBJECT-TYPE
	SYNTAX		INTEGER
	MAX-ACCESS	not-accessible
	STATUS		current
	DESCRIPTION
		"The 8-bit unsigned integer."
	::= { bgs10MIBIndex 4}
	
bgs10TotalPort	OBJECT-TYPE
	SYNTAX		INTEGER
	MAX-ACCESS	not-accessible
	STATUS		current
	DESCRIPTION
		"The integer."
	::= { bgs10MIBIndex 5}
	
--the PVC table 
bgs10Pvc				OBJECT IDENTIFIER	::= { zxbgs10mib 10}
        
bgs10PvcTable	OBJECT-TYPE
	SYNTAX		SEQUENCE OF BGS10PvcEntry
	MAX-ACCESS	not-accessible
	STATUS		current
	DESCRIPTION
		"A list of PVC configure information entries."
	::= { bgs10Pvc 1}
	
bgs10PvcEntry	OBJECT-TYPE
	SYNTAX		BGS10PvcEntry
	MAX-ACCESS	not-accessible
	STATUS		current
	DESCRIPTION
		"An entry in the table."
	INDEX {	bgs10PvcLModule,
			bgs10PvcLPort,
			bgs10PvcLVpi,
			bgs10PvcLVci,
			bgs10PvcHModule,
			bgs10PvcHPort,
			bgs10PvcHVpi,
			bgs10PvcHVci			
		}
	::= { bgs10PvcTable 1}
	
BGS10PvcEntry ::=
	SEQUENCE {
		bgs10PvcRowStatus				RowStatus,
		bgs10PvcLVpi					INTEGER,
		bgs10PvcL2HtrafficDescrType		INTEGER,
		bgs10PvcLModule					INTEGER,
		bgs10PvcHModule					INTEGER,
		bgs10PvcHPort					INTEGER,
		bgs10PvcLPort					INTEGER,
		bgs10PvcHVpi					INTEGER,
		bgs10PvcL2HtrafficQosClass		INTEGER,
		bgs10PvcH2LtrafficDescrType		INTEGER,
		bgs10PvcH2LtrafficQosClass		INTEGER,
		bgs10PvcPvcAdminStatus			INTEGER,
		bgs10PvcConnectStruct			INTEGER,
		bgs10PvcServiceCategory			INTEGER,
		bgs10PvcPvcOperStatus			INTEGER,
		bgs10PvcLCPType					INTEGER,
		bgs10PvcHCPType					INTEGER,
		bgs10PvcConnectType				INTEGER,
		bgs10PvcUse						INTEGER,
		bgs10PvcHVci					INTEGER,
		bgs10PvcLVci					INTEGER,
		bgs10PvcLAtmAddress				AtmAddr,
		bgs10PvcL2HtrafficDescrParam1	Unsigned32,
		bgs10PvcL2HtrafficDescrParam2	Unsigned32,
		bgs10PvcL2HtrafficDescrParam3	Unsigned32,
		bgs10PvcL2HtrafficDescrParam4	Unsigned32,
		bgs10PvcL2HtrafficDescrParam5	Unsigned32,
		bgs10PvcHAtmAddress				AtmAddr,
		bgs10PvcH2LtrafficDescrParam1	Unsigned32,
		bgs10PvcH2LtrafficDescrParam2	Unsigned32,
		bgs10PvcH2LtrafficDescrParam3	Unsigned32,
		bgs10PvcH2LtrafficDescrParam4	Unsigned32,
		bgs10PvcH2LtrafficDescrParam5	Unsigned32,
		bgs10PvcPMPconnectTag			UShort,
		bgs10PvcCrossconnectIdentifier	UShort,
		bgs10PvcCatchRM					BITS,
		bgs10PvcAllowEFC				BITS,
		bgs10PvcEPDFlag					BITS,
		bgs10PvcFeeGleanFlag			BITS,
		bgs10PvcPmodule					Unsigned32,
		bgs10PvcPVCType					Unsigned32,
		bgs10PvcManualControl			Unsigned32,
		bgs10PvcPport					Unsigned32,
		bgs10PvcPSwitchType				Unsigned32,
		bgs10PvcPvcPOperStatus			Unsigned32,
		bgs10PvcPVPI					Unsigned32,
		bgs10PvcOperatingMode			Unsigned32,
		bgs10PvcPCPType					Unsigned32,
		bgs10PvcPVCI					UShort,
		bgs10PvcPAtmAddress				AtmAddr,
		bgs10PvcGroupid					UShort,
		bgs10PvcAlarmStatus				UShort,
		bgs10PvcPolicing				UCHAR,
		bgs10PvcPacketType				UCHAR,
		bgs10PvcPCSInd					UCHAR,
		bgs10PvcSpecialIndex			UShort,
		bgs10PvcReNeindex				UCHAR,
		bgs10PvcReMoindex				UCHAR,
		bgs10PvcRePoindex				UCHAR
	}
	
bgs10PvcRowStatus	OBJECT-TYPE
	SYNTAX		RowStatus
	MAX-ACCESS	read-create
	STATUS		current
	DESCRIPTION
		"."
	::= { bgs10PvcEntry 1}
	
bgs10PvcLVpi	OBJECT-TYPE
	SYNTAX		INTEGER
	MAX-ACCESS	read-create
	STATUS		current
	DESCRIPTION
		"VPI connection's VPI."
	::= { bgs10PvcEntry 2}
	
bgs10PvcL2HtrafficDescrType	OBJECT-TYPE
	SYNTAX		INTEGER
	MAX-ACCESS	read-create
	STATUS		current
	DESCRIPTION
		"."
	::= { bgs10PvcEntry 3}
	
bgs10PvcLModule		OBJECT-TYPE
	SYNTAX		INTEGER
	MAX-ACCESS	read-create
	STATUS		current
	DESCRIPTION
		"."
	::= { bgs10PvcEntry 4}
	
bgs10PvcHModule	OBJECT-TYPE
	SYNTAX		INTEGER
	MAX-ACCESS	read-create
	STATUS		current
	DESCRIPTION
		"."
	::= { bgs10PvcEntry 5}
	
bgs10PvcHPort	OBJECT-TYPE
	SYNTAX		INTEGER
	MAX-ACCESS	read-create
	STATUS		current
	DESCRIPTION
		"."
	::= { bgs10PvcEntry 6}
	
bgs10PvcLPort	OBJECT-TYPE
	SYNTAX		INTEGER
	MAX-ACCESS	read-create
	STATUS		current
	DESCRIPTION
		"."
	::= { bgs10PvcEntry 7}
	
bgs10PvcHVpi	OBJECT-TYPE
	SYNTAX		INTEGER
	MAX-ACCESS	read-create
	STATUS		current
	DESCRIPTION
		"."
	::= { bgs10PvcEntry 8}
	
bgs10PvcL2HtrafficQosClass	OBJECT-TYPE
	SYNTAX		INTEGER
	MAX-ACCESS	read-create
	STATUS		current
	DESCRIPTION
		"."
	::= { bgs10PvcEntry 9}
	
bgs10PvcH2LtrafficDescrType	OBJECT-TYPE
	SYNTAX		INTEGER
	MAX-ACCESS	read-create
	STATUS		current
	DESCRIPTION
		"."
	::= { bgs10PvcEntry 10}
	
bgs10PvcH2LtrafficQosClass	OBJECT-TYPE
	SYNTAX		INTEGER
	MAX-ACCESS	read-create
	STATUS		current
	DESCRIPTION
		"."
	::= { bgs10PvcEntry 11}
	
bgs10PvcPvcAdminStatus	OBJECT-TYPE
	SYNTAX		INTEGER
	MAX-ACCESS	read-create
	STATUS		current
	DESCRIPTION
		"."
	::= { bgs10PvcEntry 12}
	
bgs10PvcConnectStruct	OBJECT-TYPE
	SYNTAX		INTEGER { 	singp2p(0),
							bip2p(1),
							singp2mp(2),
							singmp2p(3),
							mp2mp(4),
							bip2mp(5)}
	MAX-ACCESS	read-create
	STATUS		current
	DESCRIPTION
		"Pvc Connection type:
		--singal directional point to point(0)
		--bi-directional point to point (1)
		--singal directional point to multi-points (2)
		--singal directional multi-points to point (3)
		--multi-points to multi-points (4)
		--bi-dirctional point to multi-points (5)."
	::= { bgs10PvcEntry 13}
	
bgs10PvcServiceCategory	OBJECT-TYPE
	SYNTAX		INTEGER
	MAX-ACCESS	read-create
	STATUS		current
	DESCRIPTION
		"."
	::= { bgs10PvcEntry 14}
	
bgs10PvcPvcOperStatus	OBJECT-TYPE
	SYNTAX		INTEGER
	MAX-ACCESS	read-only
	STATUS		current
	DESCRIPTION
		"."
	::= { bgs10PvcEntry 15}
	
bgs10PvcLCPType	OBJECT-TYPE
	SYNTAX		INTEGER {	segEndPtNo(0),
							segEndPtYes(1),
							vpcConnectionEndPoint(2)
						}
	MAX-ACCESS	read-create
	STATUS		current
	DESCRIPTION
		"."
	::= { bgs10PvcEntry 16}
	
bgs10PvcHCPType	OBJECT-TYPE
	SYNTAX		INTEGER	{	segEndPtNo(0),
							segEndPtYes(1),
							vpcConnectionEndPoint(2)
						}
	MAX-ACCESS	read-create
	STATUS		current
	DESCRIPTION
		"."
	::= { bgs10PvcEntry 17}
	
bgs10PvcConnectType	OBJECT-TYPE
	SYNTAX		INTEGER
	MAX-ACCESS	read-create
	STATUS		current
	DESCRIPTION
		"."
	::= { bgs10PvcEntry 18}
	
bgs10PvcUse	OBJECT-TYPE
	SYNTAX		INTEGER { 	general(0),
							configureDirectVCC(1),
							controlDirectVCC(2),
							controlDistributeVCC(3),
							dataDirectVCC(4),
							multicastSendVCC(5),
							mulitcastForwardVCC(6)}
	MAX-ACCESS	read-create
	STATUS		current
	DESCRIPTION
		"."
	::= { bgs10PvcEntry 19}

bgs10PvcHVci	OBJECT-TYPE
	SYNTAX		INTEGER
	MAX-ACCESS	read-create
	STATUS		current
	DESCRIPTION
		"."
	::= { bgs10PvcEntry 20}
	
bgs10PvcLVci	OBJECT-TYPE
	SYNTAX		INTEGER
	MAX-ACCESS	read-create
	STATUS		current
	DESCRIPTION
		"."
	::= { bgs10PvcEntry 21}		
	
bgs10PvcLAtmAddress	OBJECT-TYPE
	SYNTAX		AtmAddr
	MAX-ACCESS	read-create
	STATUS		current
	DESCRIPTION
		"."
	::= { bgs10PvcEntry 22}
				
bgs10PvcL2HtrafficDescrParam1	OBJECT-TYPE
	SYNTAX		Unsigned32
	MAX-ACCESS	read-create
	STATUS		current
	DESCRIPTION
		"."
	::= { bgs10PvcEntry 23}
	
bgs10PvcL2HtrafficDescrParam2	OBJECT-TYPE
	SYNTAX		Unsigned32
	MAX-ACCESS	read-create
	STATUS		current
	DESCRIPTION
		"."
	::= { bgs10PvcEntry 24}
	
bgs10PvcL2HtrafficDescrParam3	OBJECT-TYPE
	SYNTAX		Unsigned32
	MAX-ACCESS	read-create
	STATUS		current
	DESCRIPTION
		"."
	::= { bgs10PvcEntry 25}
	
bgs10PvcL2HtrafficDescrParam4	OBJECT-TYPE
	SYNTAX		Unsigned32
	MAX-ACCESS	read-create
	STATUS		current
	DESCRIPTION
		"."
	::= { bgs10PvcEntry 26}
	
bgs10PvcL2HtrafficDescrParam5	OBJECT-TYPE
	SYNTAX		Unsigned32
	MAX-ACCESS	read-create
	STATUS		current
	DESCRIPTION
		"."
	::= { bgs10PvcEntry 27}
	
bgs10PvcHAtmAddress	OBJECT-TYPE
	SYNTAX		AtmAddr
	MAX-ACCESS	read-create
	STATUS		current
	DESCRIPTION
		"."
	::= { bgs10PvcEntry 28}
	
bgs10PvcH2LtrafficDescrParam1	OBJECT-TYPE
	SYNTAX		Unsigned32
	MAX-ACCESS	read-create
	STATUS		current
	DESCRIPTION
		"."
	::= { bgs10PvcEntry 29}
	
bgs10PvcH2LtrafficDescrParam2	OBJECT-TYPE
	SYNTAX		Unsigned32
	MAX-ACCESS	read-create
	STATUS		current
	DESCRIPTION
		"."
	::= { bgs10PvcEntry 30}
	
bgs10PvcH2LtrafficDescrParam3	OBJECT-TYPE
	SYNTAX		Unsigned32
	MAX-ACCESS	read-create
	STATUS		current
	DESCRIPTION
		"."
	::= { bgs10PvcEntry 31}
	
bgs10PvcH2LtrafficDescrParam4	OBJECT-TYPE
	SYNTAX		Unsigned32
	MAX-ACCESS	read-create
	STATUS		current
	DESCRIPTION
		"."
	::= { bgs10PvcEntry 32}
	
bgs10PvcH2LtrafficDescrParam5	OBJECT-TYPE
	SYNTAX		Unsigned32
	MAX-ACCESS	read-create
	STATUS		current
	DESCRIPTION
		"."
	::= { bgs10PvcEntry 33} 
	
bgs10PvcPMPconnectTag	OBJECT-TYPE
	SYNTAX		UShort
	MAX-ACCESS	read-only
	STATUS		current
	DESCRIPTION
		"the PMP connection tag."
	::= { bgs10PvcEntry 34 }
	
bgs10PvcCrossconnectIdentifier	OBJECT-TYPE
	SYNTAX		UShort
	MAX-ACCESS	read-only
	STATUS		current
	DESCRIPTION
		"the cross connection identifier."
	::= { bgs10PvcEntry 35 } 
	
bgs10PvcCatchRM	OBJECT-TYPE
	SYNTAX		BITS { not-catch(0),
					   catch(1)
					 }
	MAX-ACCESS	read-only
	STATUS		current
	DESCRIPTION
		"."
	::= { bgs10PvcEntry 36 } 
	
bgs10PvcAllowEFC	OBJECT-TYPE
	SYNTAX		BITS { not-allow(0),
					   allow(1)
					 }
	MAX-ACCESS	read-only
	STATUS		current
	DESCRIPTION
		"."
	::= { bgs10PvcEntry 37 } 
	
bgs10PvcEPDFlag		OBJECT-TYPE
	SYNTAX		BITS { not-set(0),
					   set(1)
					 }
	MAX-ACCESS	read-only
	STATUS		current
	DESCRIPTION
		"."
	::= { bgs10PvcEntry 38 } 
	
bgs10PvcFeeGleanFlag	OBJECT-TYPE
	SYNTAX		BITS { not-glean(0),
					   glean(1)
					 }
	MAX-ACCESS	read-only
	STATUS		current
	DESCRIPTION
		"."
	::= { bgs10PvcEntry 39 } 

bgs10PvcPmodule	OBJECT-TYPE
	SYNTAX		Unsigned32
	MAX-ACCESS	read-only
	STATUS		current
	DESCRIPTION
		"."
	::= { bgs10PvcEntry 40 }

bgs10PvcPVCType	OBJECT-TYPE
	SYNTAX		Unsigned32
	MAX-ACCESS	read-only
	STATUS		current
	DESCRIPTION
		"."
	::= { bgs10PvcEntry 41 }

bgs10PvcManualControl	OBJECT-TYPE
	SYNTAX		Unsigned32
	MAX-ACCESS	read-only
	STATUS		current
	DESCRIPTION
		"."
	::= { bgs10PvcEntry 42 }

bgs10PvcPport	OBJECT-TYPE
	SYNTAX		Unsigned32
	MAX-ACCESS	read-only
	STATUS		current
	DESCRIPTION
		"."
	::= { bgs10PvcEntry 43 }

bgs10PvcPSwitchType	OBJECT-TYPE
	SYNTAX		Unsigned32
	MAX-ACCESS	read-only
	STATUS		current
	DESCRIPTION
		"."
	::= { bgs10PvcEntry 44 }

bgs10PvcPvcPOperStatus	OBJECT-TYPE
	SYNTAX		Unsigned32
	MAX-ACCESS	read-only
	STATUS		current
	DESCRIPTION
		"."
	::= { bgs10PvcEntry 45 }

bgs10PvcPVPI	OBJECT-TYPE
	SYNTAX		Unsigned32
	MAX-ACCESS	read-only
	STATUS		current
	DESCRIPTION
		"."
	::= { bgs10PvcEntry 46 }

bgs10PvcOperatingMode	OBJECT-TYPE
	SYNTAX		Unsigned32
	MAX-ACCESS	read-only
	STATUS		current
	DESCRIPTION
		"."
	::= { bgs10PvcEntry 47 }

bgs10PvcPCPType	OBJECT-TYPE
	SYNTAX		Unsigned32
	MAX-ACCESS	read-only
	STATUS		current
	DESCRIPTION
		"."
	::= { bgs10PvcEntry 48 }

bgs10PvcPVCI	OBJECT-TYPE
	SYNTAX		UShort
	MAX-ACCESS	read-only
	STATUS		current
	DESCRIPTION
		"."
	::= { bgs10PvcEntry 49 }

bgs10PvcPAtmAddress	OBJECT-TYPE
	SYNTAX		AtmAddr
	MAX-ACCESS	read-only
	STATUS		current
	DESCRIPTION
		"."
	::= { bgs10PvcEntry 50 }

bgs10PvcGroupid	OBJECT-TYPE
	SYNTAX		UShort
	MAX-ACCESS	read-only
	STATUS		current
	DESCRIPTION
		"."
	::= { bgs10PvcEntry 51 }
	
bgs10PvcAlarmStatus	OBJECT-TYPE
	SYNTAX		UShort
	MAX-ACCESS	read-only
	STATUS		current
	DESCRIPTION
		"."
	::= { bgs10PvcEntry 52 }
	
bgs10PvcPolicing	OBJECT-TYPE	
	SYNTAX		UCHAR
	MAX-ACCESS	read-only
	STATUS		current
	DESCRIPTION
		"."
	::= { bgs10PvcEntry 53 }

bgs10PvcPacketType	OBJECT-TYPE	
	SYNTAX		UCHAR
	MAX-ACCESS	read-only
	STATUS		current
	DESCRIPTION
		"."
	::= { bgs10PvcEntry 54 }

bgs10PvcPCSInd	OBJECT-TYPE	
	SYNTAX		UCHAR
	MAX-ACCESS	read-only
	STATUS		current
	DESCRIPTION
		"."
	::= { bgs10PvcEntry 55 }
	
bgs10PvcSpecialIndex  OBJECT-TYPE	
	SYNTAX		UShort
	MAX-ACCESS	read-only
	STATUS		current
	DESCRIPTION
		"."
	::= { bgs10PvcEntry 56 }

bgs10PvcReNeindex  OBJECT-TYPE	
	SYNTAX		UCHAR
	MAX-ACCESS	read-only
	STATUS		current
	DESCRIPTION
		"."
	::= { bgs10PvcEntry 57 }

bgs10PvcReMoindex  OBJECT-TYPE	
	SYNTAX		UCHAR
	MAX-ACCESS	read-only
	STATUS		current
	DESCRIPTION
		"."
	::= { bgs10PvcEntry 58 }

bgs10PvcRePoindex  OBJECT-TYPE	
	SYNTAX		UCHAR
	MAX-ACCESS	read-only
	STATUS		current
	DESCRIPTION
		"."
	::= { bgs10PvcEntry 59 }

--The Frame Realy MIB.
bgs10FrfMIB				OBJECT IDENTIFIER	::= { zxbgs10mib 11}

--FRFPROFINDEX
FRFPROFINDEX ::= TEXTUAL-CONVENTION
	STATUS		current
	DESCRIPTION
		"The textual convention for index used in hash list."
	SYNTAX	Integer32
	
--The ZXBGS10 Frame Relay Connection Table.

bgs10FrfConnectionTable OBJECT-TYPE
	SYNTAX		SEQUENCE OF BGS10FrfConnectionEntry
	MAX-ACCESS	not-accessible
	STATUS		current
	DESCRIPTION
		"A list of frame relay information entries."
	::= { bgs10FrfMIB 1}
	
bgs10FrfConnectionEntry	OBJECT-TYPE
	SYNTAX		BGS10FrfConnectionEntry
	MAX-ACCESS	not-accessible
	STATUS		current
	DESCRIPTION
		"An entry in the table."
	INDEX {	bgs10FrfConnModule,
			bgs10FrfConnServiceIndex,
			bgs10FrfConnDLCI,
			bgs10FrfConnHighModule,
			bgs10FrfConnHighPort,
			bgs10FrfConnHighVPI,
			bgs10FrfConnHighVCI
		}
	::= { bgs10FrfConnectionTable 1}
	
BGS10FrfConnectionEntry ::=
	SEQUENCE {
		bgs10FrfConnRowStatus			RowStatus,
		bgs10FrfConnServiceIndex		INTEGER,
		bgs10FrfConnModule				INTEGER,
		bgs10FrfConnHighModule			INTEGER,
		bgs10FrfConnDLCI				Unsigned32,
		bgs10FrfConnMgtVCSigN392		INTEGER,
		bgs10FrfConnMgtVCSigN393		INTEGER,
		bgs10FrfConnHighPort			INTEGER,
		bgs10FrfConnDLCILength			INTEGER,
		bgs10FrfConnHighVPI				INTEGER,
		bgs10FrfConnTransparentMode		INTEGER,
		bgs10FrfConnInterworkingType	BITS,
		bgs10FrfConnHighVCI				Integer32,
		bgs10FrfConnHCpType				UChar,
		bgs10FrfConnCreateTime			TimeTicks,
		bgs10FrfConnTimeChange			TimeTicks,
		bgs10FrfConnCatchRM				BITS,
		bgs10FrfConnSubAdress			AtmAddr,
		bgs10FrfConnAllowEFC			BITS,
		bgs10FrfConnAddressType			INTEGER,
		bgs10FrfConnSubAddressType		INTEGER,
		bgs10FrfConnFrameAddressType	INTEGER,
		bgs10FrfConnAdminstrorStatus	INTEGER,
		bgs10FrfConnPVCEndptRcvdSigStatus
										INTEGER,
		bgs10FrfConnOperateStatus		INTEGER,
		bgs10FrfConnPVCAlarmReason		INTEGER,
		bgs10FrfConnMgtVCSigT391		INTEGER,
		bgs10FrfConnMgtVCSigT392		INTEGER,
		bgs10FrfConnPVCEndptInMaxFrameSize
										Integer32,
		bgs10FrfConnPVCEndptInBc		Integer32,
		bgs10FrfConnPVCEndptInBe		Integer32,
		bgs10FrfConnPVCEndptInCIR		Integer32,
		bgs10FrfConnPVCEndptOutMaxFrameSize
										Integer32,
		bgs10FrfConnPVCEndptOutBc		Integer32,
		bgs10FrfConnPVCEndptOutBe		Integer32,
		bgs10FrfConnPVCEndptOutCIR		Integer32,
		bgs10FrfConnMgtVCSigN391		INTEGER,
		bgs10FrfConnCrossConnectIdentifier
										UShort,
		bgs10FrfConnUse					INTEGER,
		bgs10FrfConnAtmAtmAddress		AtmAddr,
		bgs10FrfConnFrAtmAddress		AtmAddr,		
		bgs10FrfConnEPDFlag				BITS,
		bgs10FrfConnFeeGleanFlag		BITS,
		bgs10FrfConnSvcOrPvcFlag		BITS,
		bgs10FrfConnPmodule				Unsigned32,
		bgs10FrfConnPVCType				Unsigned32,
		bgs10FrfConnManualControl		Unsigned32,
		bgs10FrfConnPport				Unsigned32,
		bgs10FrfConnPswitchType			Unsigned32,
		bgs10FrfConnPOperStatus			Unsigned32,
		bgs10FrfConnPVPI				Unsigned32,
		bgs10FrfConnPOperatingMode		Unsigned32,
		bgs10FrfConnPCPType				Unsigned32,
		bgs10FrfConnPVCI				UShort,
		bgs10FrfConnPAtmAddress			AtmAddr,
		bgs10FrfConnGroupid				UShort,
		bgs10FrfConnAlarmStatus			UShort,
		bgs10FrfConnPolicing			UCHAR
	}
	
bgs10FrfConnRowStatus	OBJECT-TYPE
	SYNTAX		RowStatus
	MAX-ACCESS	read-create
	STATUS		current
	DESCRIPTION
		"The status of the conceptual row."
	::= { bgs10FrfConnectionEntry 1}
	
bgs10FrfConnServiceIndex	OBJECT-TYPE
	SYNTAX		INTEGER
	MAX-ACCESS	read-create
	STATUS		current
	DESCRIPTION
		"The arbitray integer vaule ."
	::= { bgs10FrfConnectionEntry 2}
	
bgs10FrfConnModule	OBJECT-TYPE
	SYNTAX		INTEGER
	MAX-ACCESS	read-create
	STATUS		current
	DESCRIPTION
		"The Module in which the frame relay is located."
	::= { bgs10FrfConnectionEntry 3}
	
bgs10FrfConnHighModule	OBJECT-TYPE
	SYNTAX		INTEGER
	MAX-ACCESS	read-create
	STATUS		current
	DESCRIPTION
		"The Module in which the frame relay is located."
	::= { bgs10FrfConnectionEntry 4}
	
bgs10FrfConnDLCI		OBJECT-TYPE
	SYNTAX		Unsigned32
	MAX-ACCESS	read-create
	STATUS		current
	DESCRIPTION
		"The hypoKey word of the frame relay connection."
	::= { bgs10FrfConnectionEntry 5}
	
bgs10FrfConnMgtVCSigN392	OBJECT-TYPE
	SYNTAX		INTEGER(1..10)
	MAX-ACCESS	read-create
	STATUS		current
	DESCRIPTION
		""
	DEFVAL		{3}
	::= { bgs10FrfConnectionEntry 6}
	
bgs10FrfConnMgtVCSigN393	OBJECT-TYPE
	SYNTAX		INTEGER(1..10)
	MAX-ACCESS	read-create
	STATUS		current
	DESCRIPTION
		""
	DEFVAL		{4}
	::= { bgs10FrfConnectionEntry 7}
	
bgs10FrfConnHighPort	OBJECT-TYPE
	SYNTAX		INTEGER
	MAX-ACCESS	read-create
	STATUS		current
	DESCRIPTION
		"The high port."
	::= { bgs10FrfConnectionEntry 8}
	
bgs10FrfConnDLCILength	OBJECT-TYPE
	SYNTAX		INTEGER
	MAX-ACCESS	read-create
	STATUS		current
	DESCRIPTION
		"The DLCI length."
	::= { bgs10FrfConnectionEntry 9}
	
bgs10FrfConnHighVPI		OBJECT-TYPE
	SYNTAX		INTEGER
	MAX-ACCESS	read-create
	STATUS		current
	DESCRIPTION
		"The high VPI."
	::= { bgs10FrfConnectionEntry 10}

bgs10FrfConnTransparentMode	OBJECT-TYPE
	SYNTAX		INTEGER { 	transparent(1),
							unPacket(2)
						}
	MAX-ACCESS	read-create
	STATUS		current	
	DESCRIPTION
		"the mode of the transparent mode."
	::= { bgs10FrfConnectionEntry 11}
		
bgs10FrfConnInterworkingType	OBJECT-TYPE
	SYNTAX		BITS {  net(0),
						service(1)}
	MAX-ACCESS	read-create
	STATUS		current
	DESCRIPTION
		"The type of the interworking."
	::= { bgs10FrfConnectionEntry 12}
	
bgs10FrfConnHighVCI		OBJECT-TYPE
	SYNTAX		Integer32
	MAX-ACCESS	read-create
	STATUS		current
	DESCRIPTION
		"The high VCI."
	::= { bgs10FrfConnectionEntry 13}
		
bgs10FrfConnHCpType	OBJECT-TYPE
	SYNTAX		UChar
	MAX-ACCESS	read-create
	STATUS		current
	DESCRIPTION
		"The high CP type."
	::= { bgs10FrfConnectionEntry 14}
		
bgs10FrfConnCreateTime	OBJECT-TYPE
	SYNTAX		TimeTicks
	MAX-ACCESS	read-create
	STATUS		current
	DESCRIPTION
		"The creating time."
	::= { bgs10FrfConnectionEntry 15}
		
bgs10FrfConnTimeChange	OBJECT-TYPE
	SYNTAX		TimeTicks
	MAX-ACCESS	read-create
	STATUS		current
	DESCRIPTION
		"The time change."
	::= { bgs10FrfConnectionEntry 16}
	
bgs10FrfConnCatchRM	OBJECT-TYPE
	SYNTAX		BITS {  not-catch(0),
						catch(1)
					 }
	MAX-ACCESS	read-create
	STATUS		current
	DESCRIPTION
		"."
	::= { bgs10FrfConnectionEntry 17}
	
bgs10FrfConnSubAdress	OBJECT-TYPE
	SYNTAX		AtmAddr
	MAX-ACCESS	read-create
	STATUS		current
	DESCRIPTION
		"The calling subaddress."
	::= { bgs10FrfConnectionEntry 18}
		
bgs10FrfConnAllowEFC	OBJECT-TYPE
	SYNTAX		BITS {  not-allow(0),
						allow(1)
					 }
	MAX-ACCESS	read-create
	STATUS		current
	DESCRIPTION
		"."
	::= { bgs10FrfConnectionEntry 19}
		
bgs10FrfConnAddressType		OBJECT-TYPE
	SYNTAX		INTEGER {	null(1),
							e164(2),
							nsap(3)}
	MAX-ACCESS	read-create
	STATUS		current
	DESCRIPTION
		"The calling addres type."
	::= { bgs10FrfConnectionEntry 20}
	
bgs10FrfConnSubAddressType	OBJECT-TYPE
	SYNTAX		INTEGER	{	null(1),
							e164(2),
							nsap(3)}
	MAX-ACCESS	read-create
	STATUS		current
	DESCRIPTION
		"The calling subaddress type."
	::= { bgs10FrfConnectionEntry 21}
	
bgs10FrfConnFrameAddressType	OBJECT-TYPE
	SYNTAX		INTEGER	{	null(1),
							e164(2)}
	MAX-ACCESS	read-create
	STATUS		current
	DESCRIPTION
		"The called address type."
	::= { bgs10FrfConnectionEntry 22}
	
bgs10FrfConnAdminstrorStatus	OBJECT-TYPE
	SYNTAX		INTEGER {	up(10),
							down(2),
							testing(3)}
	MAX-ACCESS	read-create
	STATUS		current
	DESCRIPTION
		"The adminstror status"
	::= { bgs10FrfConnectionEntry 23}
	
bgs10FrfConnPVCEndptRcvdSigStatus	OBJECT-TYPE
	SYNTAX		INTEGER { 	deleted(1),
							active(2),
							inactive(3),
							none(4)}
	MAX-ACCESS	read-create
	STATUS		current
	DESCRIPTION
		"."
	::= { bgs10FrfConnectionEntry  24}
										
bgs10FrfConnOperateStatus	OBJECT-TYPE
	SYNTAX		INTEGER { 	up(1),
							down(2)}
	MAX-ACCESS	read-create
	STATUS		current
	DESCRIPTION
		"The operate status."
	::= { bgs10FrfConnectionEntry 25}
	
bgs10FrfConnPVCAlarmReason	OBJECT-TYPE
	SYNTAX		INTEGER {	nodetect(1),
							frameAlarmed(2),
							frameClear(3),
							aisAlarmed(4),
							aisClear(5),
							rdiAlarmed(6),
							rdiClear(7)}
							
	MAX-ACCESS	read-create
	STATUS		current
	DESCRIPTION
		"The Alarm reason."
	::= { bgs10FrfConnectionEntry 26}
	
bgs10FrfConnMgtVCSigT391	OBJECT-TYPE
	SYNTAX		INTEGER
	MAX-ACCESS	read-create
	STATUS		current
	DESCRIPTION
		"."
	DEFVAL	{ 180 }
	::= { bgs10FrfConnectionEntry 27}
	
bgs10FrfConnMgtVCSigT392	OBJECT-TYPE
	SYNTAX		INTEGER
	MAX-ACCESS	read-create
	STATUS		current
	DESCRIPTION
		"."
	DEFVAL { 200 }
	::= { bgs10FrfConnectionEntry 28}
		
bgs10FrfConnPVCEndptInMaxFrameSize	OBJECT-TYPE
	SYNTAX		Integer32
	MAX-ACCESS	read-create
	STATUS		current
	DESCRIPTION
		"."
	::= { bgs10FrfConnectionEntry 29}
										
bgs10FrfConnPVCEndptInBc	OBJECT-TYPE
	SYNTAX		Integer32
	MAX-ACCESS	read-create
	STATUS		current
	DESCRIPTION
		"."
	::= { bgs10FrfConnectionEntry 30}
		
bgs10FrfConnPVCEndptInBe	OBJECT-TYPE
	SYNTAX		Integer32
	MAX-ACCESS	read-create
	STATUS		current
	DESCRIPTION
		"."
	::= { bgs10FrfConnectionEntry 31}
		
bgs10FrfConnPVCEndptInCIR	OBJECT-TYPE
	SYNTAX		Integer32
	MAX-ACCESS	read-create
	STATUS		current
	DESCRIPTION
		"."
	::= { bgs10FrfConnectionEntry 32}

bgs10FrfConnPVCEndptOutMaxFrameSize	OBJECT-TYPE
	SYNTAX		Integer32
	MAX-ACCESS	read-create
	STATUS		current
	DESCRIPTION
		"."
	::= { bgs10FrfConnectionEntry 33}
								
bgs10FrfConnPVCEndptOutBc	OBJECT-TYPE
	SYNTAX		Integer32
	MAX-ACCESS	read-create
	STATUS		current
	DESCRIPTION
		"."
	::= { bgs10FrfConnectionEntry 34}
	
bgs10FrfConnPVCEndptOutBe	OBJECT-TYPE
	SYNTAX		Integer32
	MAX-ACCESS	read-create
	STATUS		current
	DESCRIPTION
		"."
	::= { bgs10FrfConnectionEntry 35}
	
bgs10FrfConnPVCEndptOutCIR	OBJECT-TYPE
	SYNTAX		Integer32
	MAX-ACCESS	read-create
	STATUS		current
	DESCRIPTION
		"."
	::= { bgs10FrfConnectionEntry 36}
	
bgs10FrfConnMgtVCSigN391	OBJECT-TYPE
	SYNTAX		INTEGER
	MAX-ACCESS	read-create
	STATUS		current
	DESCRIPTION
		"."
	::= { bgs10FrfConnectionEntry 37}

bgs10FrfConnCrossConnectIdentifier	OBJECT-TYPE
	SYNTAX		UShort
	MAX-ACCESS	read-create
	STATUS		current
	DESCRIPTION
		"the cross connection identifier."
	::= { bgs10FrfConnectionEntry 	38 }
	
bgs10FrfConnUse		OBJECT-TYPE
	SYNTAX		INTEGER { normal(0),
						  sarnipvc(1)
						}
	MAX-ACCESS	read-create
	STATUS		current
	DESCRIPTION
		" the use type."
	::= { bgs10FrfConnectionEntry 	39 }
		
bgs10FrfConnAtmAtmAddress	OBJECT-TYPE
	SYNTAX		AtmAddr
	MAX-ACCESS	read-create
	STATUS		current
	DESCRIPTION
		"the source ATM address."
	::= { bgs10FrfConnectionEntry 	40 }
	
bgs10FrfConnFrAtmAddress		OBJECT-TYPE
	SYNTAX		AtmAddr
	MAX-ACCESS	read-create
	STATUS		current
	DESCRIPTION
		"the source ATM address."
	::= { bgs10FrfConnectionEntry 	41 }
	
bgs10FrfConnEPDFlag	OBJECT-TYPE
	SYNTAX		BITS {  not-set(0),
						set(1)
					 }
	MAX-ACCESS	read-create
	STATUS		current
	DESCRIPTION
		"."
	::= { bgs10FrfConnectionEntry 42}
	
bgs10FrfConnFeeGleanFlag	OBJECT-TYPE
	SYNTAX		BITS {  not-glean(0),
						glean(1)
					 }
	MAX-ACCESS	read-create
	STATUS		current
	DESCRIPTION
		"."
	::= { bgs10FrfConnectionEntry 43}
	
bgs10FrfConnSvcOrPvcFlag	OBJECT-TYPE
	SYNTAX		BITS {  pvc(0),
						svc(1)
					 }
	MAX-ACCESS	read-create
	STATUS		current
	DESCRIPTION
		"."
	::= { bgs10FrfConnectionEntry 44}
	
bgs10FrfConnPmodule	OBJECT-TYPE
	SYNTAX		Unsigned32
	MAX-ACCESS	read-create
	STATUS		current
	DESCRIPTION
		"."
	::= { bgs10FrfConnectionEntry 45}

bgs10FrfConnPVCType	OBJECT-TYPE
	SYNTAX		Unsigned32
	MAX-ACCESS	read-create
	STATUS		current
	DESCRIPTION
		"."
	::= { bgs10FrfConnectionEntry 46}

bgs10FrfConnManualControl	OBJECT-TYPE
	SYNTAX		Unsigned32
	MAX-ACCESS	read-create
	STATUS		current
	DESCRIPTION
		"."
	::= { bgs10FrfConnectionEntry 47}

bgs10FrfConnPport	OBJECT-TYPE
	SYNTAX		Unsigned32
	MAX-ACCESS	read-create
	STATUS		current
	DESCRIPTION
		"."
	::= { bgs10FrfConnectionEntry 48}

bgs10FrfConnPswitchType	OBJECT-TYPE
	SYNTAX		Unsigned32
	MAX-ACCESS	read-create
	STATUS		current
	DESCRIPTION
		"."
	::= { bgs10FrfConnectionEntry 49}

bgs10FrfConnPOperStatus OBJECT-TYPE
	SYNTAX		Unsigned32
	MAX-ACCESS	read-create
	STATUS		current
	DESCRIPTION
		"."
	::= { bgs10FrfConnectionEntry 50}

bgs10FrfConnPVPI	OBJECT-TYPE
	SYNTAX		Unsigned32
	MAX-ACCESS	read-create
	STATUS		current
	DESCRIPTION
		"."
	::= { bgs10FrfConnectionEntry 51}

bgs10FrfConnPOperatingMode	OBJECT-TYPE
	SYNTAX		Unsigned32
	MAX-ACCESS	read-create
	STATUS		current
	DESCRIPTION
		"."
	::= { bgs10FrfConnectionEntry 52}
	
bgs10FrfConnPCPType	OBJECT-TYPE
	SYNTAX		Unsigned32
	MAX-ACCESS	read-create
	STATUS		current
	DESCRIPTION
		"."
	::= { bgs10FrfConnectionEntry 53}

bgs10FrfConnPVCI	OBJECT-TYPE
	SYNTAX		UShort
	MAX-ACCESS	read-create
	STATUS		current
	DESCRIPTION
		"."
	::= { bgs10FrfConnectionEntry 54}

bgs10FrfConnPAtmAddress	OBJECT-TYPE
	SYNTAX		AtmAddr
	MAX-ACCESS	read-create
	STATUS		current
	DESCRIPTION
		"."
	::= { bgs10FrfConnectionEntry 55}

bgs10FrfConnGroupid	OBJECT-TYPE
	SYNTAX		UShort
	MAX-ACCESS	read-create
	STATUS		current
	DESCRIPTION
		"."
	::= { bgs10FrfConnectionEntry 56}
	
bgs10FrfConnAlarmStatus	OBJECT-TYPE
	SYNTAX		UShort
	MAX-ACCESS	read-create
	STATUS		current
	DESCRIPTION
		"."
	::= { bgs10FrfConnectionEntry 57}
	
bgs10FrfConnPolicing	OBJECT-TYPE
	SYNTAX		UCHAR
	MAX-ACCESS	read-create
	STATUS		current
	DESCRIPTION
		"."
	::= { bgs10FrfConnectionEntry 58}
	
	
--The Frame relay  statistics table.

bgs10FrfStatisticsTable	OBJECT-TYPE
	SYNTAX		SEQUENCE OF BGS10FrfStatisticsEntry
	MAX-ACCESS	not-accessible
	STATUS		current
	DESCRIPTION
		"A list of frame relay statistics entries."
	::= { bgs10FrfMIB 2}
	
bgs10FrfStatisticsEntry	OBJECT-TYPE
	SYNTAX		BGS10FrfStatisticsEntry
	MAX-ACCESS	not-accessible
	STATUS		current
	DESCRIPTION
		"An entry in the table."
	INDEX { bgs10FrfStatisticsProtServiceIfIndex,
			bgs10FrfStatisticsProtDLCI}
	::= { bgs10FrfStatisticsTable 1}
	
BGS10FrfStatisticsEntry ::=
	SEQUENCE {
		bgs10FrfStatisticsRowStatus				RowStatus,
		bgs10FrfStatisticsProtServiceIfIndex	INTEGER,
		bgs10FrfStatisticsDLCILength			INTEGER,
		bgs10FrfStatisticsProtDLCI				INTEGER,
		bgs10FrfStatisticsInCorrectFrfs			Counter32,
		bgs10FrfStatisticsInCorrectOcts			Counter32,
		bgs10FrfStatisticsInTotalOcts			Counter32,
		bgs10FrfStatisticsInDE1Frfs				Counter32,
		bgs10FrfStatisticsInFECN1Frfs			Counter32,
		bgs10FrfStatisticsInBECN1Frfs			Counter32,
		bgs10FrfStatisticsInErrDisFrfs			Counter32,
		bgs10FrfStatisticsInUnknownFrfs			Counter32,
		bgs10FrfStatisticsOutCorrectFrfs		Counter32,
		bgs10FrfStatisticsOutCorrectOcts		Counter32,
		bgs10FrfStatisticsOutTotalOcts			Counter32,
		bgs10FrfStatisticsOutDE1Frfs			Counter32,
		bgs10FrfStatisticsOutFECN1Frfs			Counter32,
		bgs10FrfStatisticsOutBECN1Frfs			Counter32,	
		bgs10FrfStatisticsOutErrDisFrfs			Counter32,
		bgs10FrfStatisticsOutUnknownFrfs		Counter32
	}
	
bgs10FrfStatisticsRowStatus		OBJECT-TYPE
	SYNTAX		RowStatus
	MAX-ACCESS	read-only
	STATUS		current
	DESCRIPTION
		"The status of the conceptal rwo."
	::= { bgs10FrfStatisticsEntry 1}
	
bgs10FrfStatisticsProtServiceIfIndex	OBJECT-TYPE
	SYNTAX		INTEGER
	MAX-ACCESS	read-only
	STATUS		current
	DESCRIPTION
		"The interface index of protocl service."
	::= { bgs10FrfStatisticsEntry 2}
	
bgs10FrfStatisticsDLCILength	OBJECT-TYPE
	SYNTAX		INTEGER
	MAX-ACCESS	read-only
	STATUS		current
	DESCRIPTION
		"The interface index of protocl service."
	::= { bgs10FrfStatisticsEntry 3}
	
bgs10FrfStatisticsProtDLCI	OBJECT-TYPE
	SYNTAX		INTEGER
	MAX-ACCESS	read-only
	STATUS		current
	DESCRIPTION
		"The interface index of protocl service."
	::= { bgs10FrfStatisticsEntry 4}

bgs10FrfStatisticsInCorrectFrfs	OBJECT-TYPE
	SYNTAX		Counter32
	MAX-ACCESS	read-only
	STATUS		current
	DESCRIPTION
		"."
	::= { bgs10FrfStatisticsEntry 5}
	
bgs10FrfStatisticsInCorrectOcts	OBJECT-TYPE
	SYNTAX		Counter32
	MAX-ACCESS	read-only
	STATUS		current
	DESCRIPTION
		"."
	::= { bgs10FrfStatisticsEntry 6}
	
bgs10FrfStatisticsInTotalOcts	OBJECT-TYPE
	SYNTAX		Counter32
	MAX-ACCESS	read-only
	STATUS		current
	DESCRIPTION
		"."
	::= { bgs10FrfStatisticsEntry 7}
	
bgs10FrfStatisticsInDE1Frfs	OBJECT-TYPE
	SYNTAX		Counter32
	MAX-ACCESS	read-only
	STATUS		current
	DESCRIPTION
		"."
	::= { bgs10FrfStatisticsEntry 8}
	
bgs10FrfStatisticsInFECN1Frfs	OBJECT-TYPE
	SYNTAX		Counter32
	MAX-ACCESS	read-only
	STATUS		current
	DESCRIPTION
		"."
	::= { bgs10FrfStatisticsEntry 9}
	
bgs10FrfStatisticsInBECN1Frfs	OBJECT-TYPE
	SYNTAX		Counter32
	MAX-ACCESS	read-only
	STATUS		current
	DESCRIPTION
		"."
	::= { bgs10FrfStatisticsEntry 10}
	
bgs10FrfStatisticsInErrDisFrfs	OBJECT-TYPE
	SYNTAX		Counter32
	MAX-ACCESS	read-only
	STATUS		current
	DESCRIPTION
		"."
	::= { bgs10FrfStatisticsEntry 11}
	
bgs10FrfStatisticsInUnknownFrfs	OBJECT-TYPE
	SYNTAX		Counter32
	MAX-ACCESS	read-only
	STATUS		current
	DESCRIPTION
		"."
	::= { bgs10FrfStatisticsEntry 12}
	
bgs10FrfStatisticsOutCorrectFrfs	OBJECT-TYPE
	SYNTAX		Counter32
	MAX-ACCESS	read-only
	STATUS		current
	DESCRIPTION
		"."
	::= { bgs10FrfStatisticsEntry 13}
	
bgs10FrfStatisticsOutCorrectOcts	OBJECT-TYPE
	SYNTAX		Counter32
	MAX-ACCESS	read-only
	STATUS		current
	DESCRIPTION
		"."
	::= { bgs10FrfStatisticsEntry 14}
	
bgs10FrfStatisticsOutTotalOcts	OBJECT-TYPE
	SYNTAX		Counter32
	MAX-ACCESS	read-only
	STATUS		current
	DESCRIPTION
		"."
	::= { bgs10FrfStatisticsEntry 15}
	
bgs10FrfStatisticsOutDE1Frfs	OBJECT-TYPE
	SYNTAX		Counter32
	MAX-ACCESS	read-only
	STATUS		current
	DESCRIPTION
		"."
	::= { bgs10FrfStatisticsEntry 16}
	
bgs10FrfStatisticsOutFECN1Frfs	OBJECT-TYPE
	SYNTAX		Counter32
	MAX-ACCESS	read-only
	STATUS		current
	DESCRIPTION
		"."
	::= { bgs10FrfStatisticsEntry 17}
	
bgs10FrfStatisticsOutBECN1Frfs	OBJECT-TYPE
	SYNTAX		Counter32
	MAX-ACCESS	read-only
	STATUS		current
	DESCRIPTION
		"."
	::= { bgs10FrfStatisticsEntry 18}
	
bgs10FrfStatisticsOutErrDisFrfs	OBJECT-TYPE
	SYNTAX		Counter32
	MAX-ACCESS	read-only
	STATUS		current
	DESCRIPTION
		"."
	::= { bgs10FrfStatisticsEntry 19}
	
bgs10FrfStatisticsOutUnknownFrfs	OBJECT-TYPE
	SYNTAX		Counter32
	MAX-ACCESS	read-only
	STATUS		current
	DESCRIPTION
		"."
	::= { bgs10FrfStatisticsEntry 20}
	
--The Frame Relay OAM F5 Table

bgs10FrfOAMF5Table OBJECT-TYPE
	SYNTAX		SEQUENCE OF BGS10FrfOAMF5Entry
	MAX-ACCESS	not-accessible
	STATUS		current
	DESCRIPTION
		"An list of the frame relay OAM F5 table."
	::= { bgs10FrfMIB	3}
	
bgs10FrfOAMF5Entry	OBJECT-TYPE
	SYNTAX		BGS10FrfOAMF5Entry
	MAX-ACCESS	not-accessible
	STATUS		current
	DESCRIPTION
		"An entry to the table."
	INDEX	{ bgs10FrfOamF5IfIndex,
				bgs10FrfOamF5VPI,
				bgs10FrfOamF5VCI}
	::= { bgs10FrfOAMF5Table 1}
	
BGS10FrfOAMF5Entry ::= 
	SEQUENCE {
		bgs10FrfOamF5RowStatus		RowStatus,
		bgs10FrfOamF5VPI			INTEGER,
		bgs10FrfOamF5VCI			Integer32,
		bgs10FrfOamF5RecieveAISs	Counter32,
		bgs10FrfOamF5RecieveRDIs	Counter32,
		bgs10FrfOamf5endAISs		Counter32,
		bgs10FrfOamF5SendRDIs		Counter32,
		bgs10FrfOamF5IfIndex		INTEGER
	}
	
bgs10FrfOamF5RowStatus	OBJECT-TYPE
	SYNTAX		RowStatus
	MAX-ACCESS	read-only
	STATUS		current
	DESCRIPTION
		"The status of the conceptal rwo."
	::= { bgs10FrfOAMF5Entry 1}
	
bgs10FrfOamF5VPI	OBJECT-TYPE
	SYNTAX		INTEGER
	MAX-ACCESS	read-only
	STATUS		current
	DESCRIPTION
		"VPI"
	::= { bgs10FrfOAMF5Entry 2}
	
bgs10FrfOamF5VCI	OBJECT-TYPE
	SYNTAX		Integer32
	MAX-ACCESS	read-only
	STATUS		current
	DESCRIPTION
		"VCI"
	::= { bgs10FrfOAMF5Entry 3}
	
bgs10FrfOamF5RecieveAISs	OBJECT-TYPE
	SYNTAX		Counter32
	MAX-ACCESS	read-only
	STATUS		current
	DESCRIPTION
		"."
	::= { bgs10FrfOAMF5Entry 4}
	
bgs10FrfOamF5RecieveRDIs	OBJECT-TYPE
	SYNTAX		Counter32
	MAX-ACCESS	read-only
	STATUS		current
	DESCRIPTION
		"."
	::= { bgs10FrfOAMF5Entry 5}
	
bgs10FrfOamf5endAISs	OBJECT-TYPE
	SYNTAX		Counter32
	MAX-ACCESS	read-only
	STATUS		current
	DESCRIPTION
		"."
	::= { bgs10FrfOAMF5Entry 6}
	
bgs10FrfOamF5SendRDIs	OBJECT-TYPE
	SYNTAX		Counter32
	MAX-ACCESS	read-only
	STATUS		current
	DESCRIPTION
		"."
	::= { bgs10FrfOAMF5Entry 7}
	
bgs10FrfOamF5IfIndex	OBJECT-TYPE
	SYNTAX		INTEGER
	MAX-ACCESS	read-only
	STATUS		current
	DESCRIPTION
		"."
	::= { bgs10FrfOAMF5Entry 8}

--the frame relay profile table.

bgs10FrfProfileTable	OBJECT-TYPE
	SYNTAX		SEQUENCE OF BGS10FrfProfileEntry
	MAX-ACCESS	not-accessible
	STATUS		current
	DESCRIPTION
		"A list of the profile information."
	::= { bgs10FrfMIB 4}
	
bgs10FrfProfileEntry OBJECT-TYPE
	SYNTAX		BGS10FrfProfileEntry
	MAX-ACCESS	not-accessible
	STATUS		current
	DESCRIPTION
		" An entry to the table."
	INDEX { FRFPROFINDEX }
	::= { bgs10FrfProfileTable 1}
	
BGS10FrfProfileEntry ::=
	SEQUENCE {
		bgs10FrfProfileRowStatus		RowStatus,
		bgs10FrfProfileFecnMode			INTEGER,
		bgs10FrfProfileDeMode			INTEGER,
		bgs10FrfProfileClpMode			INTEGER,
		bgs10FrfProfileDefaultDe		INTEGER,
		bgs10FrfProfileDefaultClp		INTEGER,
		bgs10FrfProfileProtocols		INTEGER,
		bgs10FrfProfileRefCnt			INTEGER
	}
	
bgs10FrfProfileRowStatus	OBJECT-TYPE
	SYNTAX		RowStatus
	MAX-ACCESS	read-create
	STATUS		current
	DESCRIPTION
		"."
	::= { bgs10FrfProfileEntry 1}
	
bgs10FrfProfileFecnMode		OBJECT-TYPE
	SYNTAX		INTEGER
	MAX-ACCESS	read-create
	STATUS		current
	DESCRIPTION
		"."
	::= { bgs10FrfProfileEntry 2}
		
bgs10FrfProfileDeMode	OBJECT-TYPE
	SYNTAX		INTEGER
	MAX-ACCESS	read-create
	STATUS		current
	DESCRIPTION
		"."
	::= { bgs10FrfProfileEntry 3}	
	
bgs10FrfProfileClpMode	OBJECT-TYPE
	SYNTAX		INTEGER
	MAX-ACCESS	read-create
	STATUS		current
	DESCRIPTION
		"."
	::= { bgs10FrfProfileEntry 4}
		
bgs10FrfProfileDefaultDe	OBJECT-TYPE
	SYNTAX		INTEGER
	MAX-ACCESS	read-create
	STATUS		current
	DESCRIPTION
		"."
	::= { bgs10FrfProfileEntry 5}
		
bgs10FrfProfileDefaultClp	OBJECT-TYPE
	SYNTAX		INTEGER
	MAX-ACCESS	read-create
	STATUS		current
	DESCRIPTION
		"."
	::= { bgs10FrfProfileEntry 6}
		
bgs10FrfProfileProtocols	OBJECT-TYPE
	SYNTAX		INTEGER { 	ethernet(1),
							ethernetFcs(2),
							tokenRing(4),
							tokenRingFcs(8),
							ipRouted(9),
							arp(16)}
	MAX-ACCESS	read-create
	STATUS		current
	DESCRIPTION
		"."
	::= { bgs10FrfProfileEntry 7}
		
bgs10FrfProfileRefCnt	OBJECT-TYPE
	SYNTAX		INTEGER
	MAX-ACCESS	read-create
	STATUS		current
	DESCRIPTION
		"."
	::= { bgs10FrfProfileEntry 8}
	
--The frame relay error table.

bgs10FrfErrorTable OBJECT-TYPE
	SYNTAX		SEQUENCE OF BGS10FrfErrorEntry
	MAX-ACCESS	not-accessible
	STATUS		current
	DESCRIPTION
		"A list of the frame realy error table."
	::= { bgs10FrfMIB 5}
		
bgs10FrfErrorEntry OBJECT-TYPE
	SYNTAX		BGS10FrfErrorEntry
	MAX-ACCESS	not-accessible
	STATUS		current
	DESCRIPTION
		"An entry to the errot table."
	INDEX { bgs10FrfErrIfIndex}
	::= { bgs10FrfErrorTable 1}
	
BGS10FrfErrorEntry ::=
	SEQUENCE {
		bgs10FrfErrRowStatus			RowStatus,
		bgs10FrfErrIfIndex				INTEGER,
		bgs10FrfErrType					INTEGER,
		bgs10FrfErrTime					Unsigned32,
		bgs10FrfErrFaults				Unsigned32,
		bgs10FrfErrFaultTime			Unsigned32
	}
	
bgs10FrfErrRowStatus	OBJECT-TYPE
	SYNTAX		RowStatus
	MAX-ACCESS	read-only
	STATUS		current
	DESCRIPTION
		"."
	::= { bgs10FrfErrorEntry 1}
	
bgs10FrfErrIfIndex	OBJECT-TYPE
	SYNTAX		INTEGER
	MAX-ACCESS	read-only
	STATUS		current
	DESCRIPTION
		"."
	::= { bgs10FrfErrorEntry 2}
	
bgs10FrfErrType	OBJECT-TYPE
	SYNTAX		INTEGER { 	unknownError(1),
							receiveShort(2),
							receiveLong(3),
							illegalAddress(4),
							unknownAddress(5),
							dlcmiProtoErr(7),
							dlcmiUnknownIE(8),
							dlcmiSequenceErr(9),
							dlcmiUnknownRpt(10),
							noErrorSinceReset(11)}
	MAX-ACCESS	read-only
	STATUS		current
	DESCRIPTION
		"."
	::= { bgs10FrfErrorEntry 3}
	
bgs10FrfErrTime	OBJECT-TYPE
	SYNTAX		Unsigned32
	MAX-ACCESS	read-only
	STATUS		current
	DESCRIPTION
		"."
	::= { bgs10FrfErrorEntry 4}
	
bgs10FrfErrFaults	OBJECT-TYPE
	SYNTAX		Unsigned32
	MAX-ACCESS	read-only
	STATUS		current
	DESCRIPTION
		"."
	::= { bgs10FrfErrorEntry 5}
	
bgs10FrfErrFaultTime	OBJECT-TYPE
	SYNTAX		Unsigned32
	MAX-ACCESS	read-only
	STATUS		current
	DESCRIPTION
		"."
	::= { bgs10FrfErrorEntry 6}

--the frame relay port table.

bgs10FrfLPortTable	OBJECT-TYPE
	SYNTAX		SEQUENCE OF BGS10FrfLPortEntry
	MAX-ACCESS	not-accessible
	STATUS		current
	DESCRIPTION
		"A list of the frame realy port table."
	::= { bgs10FrfMIB 6}
		
bgs10FrfLPortEntry OBJECT-TYPE
	SYNTAX		BGS10FrfLPortEntry
	MAX-ACCESS	not-accessible
	STATUS		current
	DESCRIPTION
		"An entry to the port table."
	INDEX { ifIndex}
	::= { bgs10FrfLPortTable 1}
	
BGS10FrfLPortEntry ::=
	SEQUENCE {
		bgs10FrfLPortRowStatus			RowStatus,
		bgs10FrfLPortLportNumPlan		INTEGER,
		bgs10FrfLPortLportType			INTEGER,
		bgs10FrfLPortLportAddrDLCILen	INTEGER,
		bgs10FrfLPortLportVCSigProtocol	INTEGER,
		bgs10FrfLPortLportCodeSet		INTEGER,
		bgs10FrfLPortAdminStatus		INTEGER,
		bgs10FrfLPortOperStatus			INTEGER
	}
	
bgs10FrfLPortRowStatus	OBJECT-TYPE
	SYNTAX		RowStatus
	MAX-ACCESS	read-create
	STATUS		current
	DESCRIPTION
		"."
	::= { bgs10FrfLPortEntry 1}
	
bgs10FrfLPortLportNumPlan	OBJECT-TYPE
	SYNTAX		INTEGER { 	other(1),
							e164(2),
							x121(3),
							none(4)}
	MAX-ACCESS	read-create
	STATUS		current
	DESCRIPTION
		"."
	::= { bgs10FrfLPortEntry 2}
	
bgs10FrfLPortLportType	OBJECT-TYPE
	SYNTAX		INTEGER { uni(1),
						  nni(2)}	
	MAX-ACCESS	read-create
	STATUS		current
	DESCRIPTION
		"."
	::= { bgs10FrfLPortEntry 3}
	
bgs10FrfLPortLportAddrDLCILen	OBJECT-TYPE
	SYNTAX		INTEGER { 	twoOctets10Bits(1),
							threeOctets10Bits(2),
							threeOctets16Bits(3),
							fourOctets17Bits(4),
							fourOctets23Bits(5)}
	MAX-ACCESS	read-create
	STATUS		current
	DESCRIPTION
		"."
	::= { bgs10FrfLPortEntry 4}
	
bgs10FrfLPortLportVCSigProtocol	OBJECT-TYPE
	SYNTAX		INTEGER { 	none(1),
							ilmi(2),
							asniT1617D(3),
							ansiT1617B(4),
							ccittQ933A(5)}
	MAX-ACCESS	read-create
	STATUS		current
	DESCRIPTION
		"."
	::= { bgs10FrfLPortEntry 5}
	
bgs10FrfLPortLportCodeSet	OBJECT-TYPE
	SYNTAX		INTEGER
	MAX-ACCESS	read-create
	STATUS		current
	DESCRIPTION
		"."
	::= { bgs10FrfLPortEntry 6}
	
bgs10FrfLPortAdminStatus			OBJECT-TYPE
	SYNTAX		INTEGER
	MAX-ACCESS	read-create
	STATUS		current
	DESCRIPTION
		"."
	::= { bgs10FrfLPortEntry 7}
	
bgs10FrfLPortOperStatus	OBJECT-TYPE
	SYNTAX		INTEGER
	MAX-ACCESS	read-create
	STATUS		current
	DESCRIPTION
		"."
	::= { bgs10FrfLPortEntry 8}

		
--the frame relay Mgt VC table

bgs10FrfMgtVCSigTable	OBJECT-TYPE
	SYNTAX		SEQUENCE OF BGS10FrfMgtVCSigEntry
	MAX-ACCESS	not-accessible
	STATUS		current
	DESCRIPTION
		"A list of the frame realy port table."
	::= { bgs10FrfMIB 7}
		
bgs10FrfMgtVCSigEntry OBJECT-TYPE
	SYNTAX		BGS10FrfMgtVCSigEntry
	MAX-ACCESS	not-accessible
	STATUS		current
	DESCRIPTION
		"An entry to the port table."
	INDEX { ifIndex}
	::= { bgs10FrfMgtVCSigTable 1}
	
BGS10FrfMgtVCSigEntry ::=
	SEQUENCE {
		bgs10FrfMgtVCSigRowStatus		RowStatus,
		bgs10FrfMgtVCSigNetnT3			INTEGER,			
		bgs10FrfMgtVCSigT391			INTEGER,
		bgs10FrfMgtVCSigT392			INTEGER,
		bgs10FrfMgtVCSigProced			INTEGER,
		bgs10FrfMgtVCSigN393			INTEGER,
		bgs10FrfMgtVCSigN392			INTEGER,
		bgs10FrfMgtVCSigN391			INTEGER,
		bgs10FrfMgtVCSigNetnN4			INTEGER
	}

bgs10FrfMgtVCSigRowStatus	OBJECT-TYPE
	SYNTAX		RowStatus
	MAX-ACCESS	read-create
	STATUS		current
	DESCRIPTION
		"."
	::= { bgs10FrfMgtVCSigEntry 1}
	
bgs10FrfMgtVCSigNetnT3	OBJECT-TYPE
	SYNTAX		INTEGER { 	nt3P5(1),
							nt3P10(2),
							nt3P15(3),
							nt3P20(4),
							nt3P25(5),
							nt3P30(6)}
	MAX-ACCESS	read-create
	STATUS		current
	DESCRIPTION
		"."
	::= { bgs10FrfMgtVCSigEntry 2}
	
bgs10FrfMgtVCSigT391	OBJECT-TYPE
	SYNTAX		INTEGER (5..30)
	MAX-ACCESS	read-create
	STATUS		current
	DESCRIPTION
		"."
	DEFVAL { 10 }
	::= { bgs10FrfMgtVCSigEntry 3}
	
bgs10FrfMgtVCSigT392	OBJECT-TYPE
	SYNTAX		INTEGER (5..30)
	MAX-ACCESS	read-create
	STATUS		current
	DESCRIPTION
		"."
	DEFVAL { 15 }
	::= { bgs10FrfMgtVCSigEntry 4}
	
bgs10FrfMgtVCSigProced	OBJECT-TYPE
	SYNTAX		INTEGER { 	u2nnet(1),
							bidirect(2)}
	MAX-ACCESS	read-create
	STATUS		current
	DESCRIPTION
		"."
	::= { bgs10FrfMgtVCSigEntry 5}
	
bgs10FrfMgtVCSigN393	OBJECT-TYPE
	SYNTAX		INTEGER (1..10)
	MAX-ACCESS	read-create
	STATUS		current
	DESCRIPTION
		"."
	DEFVAL { 4 }
	::= { bgs10FrfMgtVCSigEntry 6}
	
bgs10FrfMgtVCSigN392	OBJECT-TYPE
	SYNTAX		INTEGER (1..10)
	MAX-ACCESS	read-create
	STATUS		current
	DESCRIPTION
		"."
	DEFVAL { 3 }
	::= { bgs10FrfMgtVCSigEntry 7}
	
bgs10FrfMgtVCSigN391	OBJECT-TYPE
	SYNTAX		INTEGER
	MAX-ACCESS	read-create
	STATUS		current
	DESCRIPTION
		"."
	::= { bgs10FrfMgtVCSigEntry 8}
	
bgs10FrfMgtVCSigNetnN4	OBJECT-TYPE
	SYNTAX		INTEGER
	MAX-ACCESS	read-create
	STATUS		current
	DESCRIPTION
		"It ha the constant value 5."
	::= { bgs10FrfMgtVCSigEntry 9}
	
-- the frame relay Mgt VC signal state table.

bgs10FrfMgtVCSigStatTable	OBJECT-TYPE
	SYNTAX		SEQUENCE OF BGS10FrfMgtVCSigStatEntry
	MAX-ACCESS	not-accessible
	STATUS		current
	DESCRIPTION
		"A list of the frame realy port table."
	::= { bgs10FrfMIB 8}
		
bgs10FrfMgtVCSigStatEntry OBJECT-TYPE
	SYNTAX		BGS10FrfMgtVCSigStatEntry
	MAX-ACCESS	not-accessible
	STATUS		current
	DESCRIPTION
		"An entry to the port table."
	INDEX { ifIndex}
	::= { bgs10FrfMgtVCSigStatTable 1}
	
BGS10FrfMgtVCSigStatEntry ::=
	SEQUENCE {
		bgs10FrfMgtVCSigStatRowStatus			RowStatus,
		bgs10FrfMgtVCSigStatUserLinkRelErrors	Counter32,
		bgs10FrfMgtVCSigStatUserProtErrors		Counter32,
		bgs10FrfMgtVCSigStatUserChanInactive	Counter32,
		bgs10FrfMgtVCSigStatNetLinkRelErrors	Counter32,
		bgs10FrfMgtVCSigStatNetProtErrors		Counter32,
		bgs10FrfMgtVCSigStatNetChanInactive		Counter32
	}
	
bgs10FrfMgtVCSigStatRowStatus	OBJECT-TYPE
	SYNTAX		RowStatus
	MAX-ACCESS	read-only
	STATUS		current
	DESCRIPTION
		"."
	::= { bgs10FrfMgtVCSigStatEntry 1}
	
bgs10FrfMgtVCSigStatUserLinkRelErrors	OBJECT-TYPE
	SYNTAX		Counter32
	MAX-ACCESS	read-only
	STATUS		current
	DESCRIPTION
		"."
	::= { bgs10FrfMgtVCSigStatEntry 2}
	
bgs10FrfMgtVCSigStatUserProtErrors	OBJECT-TYPE
	SYNTAX		Counter32
	MAX-ACCESS	read-only
	STATUS		current
	DESCRIPTION
		"."
	::= { bgs10FrfMgtVCSigStatEntry 3}
	
bgs10FrfMgtVCSigStatUserChanInactive	OBJECT-TYPE
	SYNTAX		Counter32
	MAX-ACCESS	read-only
	STATUS		current
	DESCRIPTION
		"."
	::= { bgs10FrfMgtVCSigStatEntry 4}
	
bgs10FrfMgtVCSigStatNetLinkRelErrors	OBJECT-TYPE
	SYNTAX		Counter32
	MAX-ACCESS	read-only
	STATUS		current
	DESCRIPTION
		"."
	::= { bgs10FrfMgtVCSigStatEntry 5}
	
bgs10FrfMgtVCSigStatNetProtErrors	OBJECT-TYPE
	SYNTAX		Counter32
	MAX-ACCESS	read-only
	STATUS		current
	DESCRIPTION
		"."
	::= { bgs10FrfMgtVCSigStatEntry 6}
	
bgs10FrfMgtVCSigStatNetChanInactive	OBJECT-TYPE
	SYNTAX		Counter32
	MAX-ACCESS	read-only
	STATUS		current
	DESCRIPTION
		"."
	::= { bgs10FrfMgtVCSigStatEntry 7}
	
--The Frame Relay SPVC Connection Table.
bgs10FrfSPVCConnectionTable OBJECT-TYPE
	SYNTAX		SEQUENCE OF BGS10FrfSPVCConnectionEntry
	MAX-ACCESS	not-accessible
	STATUS		current
	DESCRIPTION
		"A list of frame relay information entries."
	::= { bgs10FrfMIB 9}
	
bgs10FrfSPVCConnectionEntry	OBJECT-TYPE
	SYNTAX		BGS10FrfSPVCConnectionEntry
	MAX-ACCESS	not-accessible
	STATUS		current
	DESCRIPTION
		"An entry in the table."
	INDEX {	bgs10FrfSPVCConnModule,
			bgs10FrfSPVCConnServiceIndex,
			bgs10FrfSPVCConnDLCI,
			bgs10FrfSPVCConnAtmAtmAddress
		}
	::= { bgs10FrfSPVCConnectionTable 1}
	
BGS10FrfSPVCConnectionEntry ::=
	SEQUENCE {
		bgs10FrfSPVCConnRowStatus			RowStatus,
		bgs10FrfSPVCConnServiceIndex		INTEGER,
		bgs10FrfSPVCConnModule				INTEGER,
		bgs10FrfSPVCConnHighModule			INTEGER,
		bgs10FrfSPVCConnDLCI				Unsigned32,
		bgs10FrfSPVCConnMgtVCSigN392		INTEGER,
		bgs10FrfSPVCConnMgtVCSigN393		INTEGER,
		bgs10FrfSPVCConnHighPort			INTEGER,
		bgs10FrfSPVCConnDLCILength			INTEGER,
		bgs10FrfSPVCConnHighVPI				INTEGER,
		bgs10FrfSPVCConnTransparentMode		INTEGER,
		bgs10FrfSPVCConnInterworkingType	BITS,
		bgs10FrfSPVCConnHighVCI				Integer32,
		bgs10FrfSPVCConnHCpType				UChar,
		bgs10FrfSPVCConnCreateTime			TimeTicks,
		bgs10FrfSPVCConnTimeChange			TimeTicks,
		bgs10FrfSPVCConnCatchRM				BITS,
		bgs10FrfSPVCConnSubAdress			AtmAddr,
		bgs10FrfSPVCConnAllowEFC			BITS,
		bgs10FrfSPVCConnAddressType			INTEGER,
		bgs10FrfSPVCConnSubAddressType		INTEGER,
		bgs10FrfSPVCConnFrameAddressType	INTEGER,
		bgs10FrfSPVCConnAdminstrorStatus	INTEGER,
		bgs10FrfSPVCConnPVCEndptRcvdSigStatus
											INTEGER,
		bgs10FrfSPVCConnOperateStatus		INTEGER,
		bgs10FrfSPVCConnPVCAlarmReason		INTEGER,
		bgs10FrfSPVCConnMgtVCSigT391		INTEGER,
		bgs10FrfSPVCConnMgtVCSigT392		INTEGER,
		bgs10FrfSPVCConnPVCEndptInMaxFrameSize
											Integer32,
		bgs10FrfSPVCConnPVCEndptInBc		Integer32,
		bgs10FrfSPVCConnPVCEndptInBe		Integer32,
		bgs10FrfSPVCConnPVCEndptInCIR		Integer32,
		bgs10FrfSPVCConnPVCEndptOutMaxFrameSize
											Integer32,
		bgs10FrfSPVCConnPVCEndptOutBc		Integer32,
		bgs10FrfSPVCConnPVCEndptOutBe		Integer32,
		bgs10FrfSPVCConnPVCEndptOutCIR		Integer32,
		bgs10FrfSPVCConnMgtVCSigN391		INTEGER,
		bgs10FrfSPVCConnCrossConnectIdentifier
											UShort,
		bgs10FrfSPVCConnUse					INTEGER,
		bgs10FrfSPVCConnAtmAtmAddress		AtmAddr,
		bgs10FrfSPVCConnFrAtmAddress		AtmAddr,		
		bgs10FrfSPVCConnEPDFlag				BITS,
		bgs10FrfSPVCConnFeeGleanFlag		BITS,
		bgs10FrfSPVCConnSvcOrPvcFlag		BITS,
		bgs10FrfSPVCConnRetries				UShort,
		bgs10FrfSPVCConnInterval			UShort,
		bgs10FrfSPVCConnPVCType				Unsigned32,
		
		bgs10FrfSPVCProfileFecnMode			INTEGER,
		bgs10FrfSPVCProfileDeMode			INTEGER,
		bgs10FrfSPVCProfileClpMode			INTEGER,
		bgs10FrfSPVCProfileDefaultDe		INTEGER,
		bgs10FrfSPVCProfileDefaultClp		INTEGER,
		bgs10FrfSPVCProfileProtocols		INTEGER,
		bgs10FrfSPVCProfileRefCnt			INTEGER,
		bgs10FrfSPVCConnAlarmStatus			UShort		
	}
	
bgs10FrfSPVCConnRowStatus	OBJECT-TYPE
	SYNTAX		RowStatus
	MAX-ACCESS	read-create
	STATUS		current
	DESCRIPTION
		"The status of the conceptual row."
	::= { bgs10FrfSPVCConnectionEntry 1}
	
bgs10FrfSPVCConnServiceIndex	OBJECT-TYPE
	SYNTAX		INTEGER
	MAX-ACCESS	read-create
	STATUS		current
	DESCRIPTION
		"The arbitray integer vaule ."
	::= { bgs10FrfSPVCConnectionEntry 2}
	
bgs10FrfSPVCConnModule	OBJECT-TYPE
	SYNTAX		INTEGER
	MAX-ACCESS	read-create
	STATUS		current
	DESCRIPTION
		"The Module in which the frame relay is located."
	::= { bgs10FrfSPVCConnectionEntry 3}
	
bgs10FrfSPVCConnHighModule	OBJECT-TYPE
	SYNTAX		INTEGER
	MAX-ACCESS	read-create
	STATUS		current
	DESCRIPTION
		"The Module in which the frame relay is located."
	::= { bgs10FrfSPVCConnectionEntry 4}
	
bgs10FrfSPVCConnDLCI		OBJECT-TYPE
	SYNTAX		Unsigned32
	MAX-ACCESS	read-create
	STATUS		current
	DESCRIPTION
		"The hypoKey word of the frame relay connection."
	::= { bgs10FrfSPVCConnectionEntry 5}
	
bgs10FrfSPVCConnMgtVCSigN392	OBJECT-TYPE
	SYNTAX		INTEGER(1..10)
	MAX-ACCESS	read-create
	STATUS		current
	DESCRIPTION
		""
	DEFVAL		{3}
	::= { bgs10FrfSPVCConnectionEntry 6}
	
bgs10FrfSPVCConnMgtVCSigN393	OBJECT-TYPE
	SYNTAX		INTEGER(1..10)
	MAX-ACCESS	read-create
	STATUS		current
	DESCRIPTION
		""
	DEFVAL		{4}
	::= { bgs10FrfSPVCConnectionEntry 7}
	
bgs10FrfSPVCConnHighPort	OBJECT-TYPE
	SYNTAX		INTEGER
	MAX-ACCESS	read-create
	STATUS		current
	DESCRIPTION
		"The high port."
	::= { bgs10FrfSPVCConnectionEntry 8}
	
bgs10FrfSPVCConnDLCILength	OBJECT-TYPE
	SYNTAX		INTEGER
	MAX-ACCESS	read-create
	STATUS		current
	DESCRIPTION
		"The DLCI length."
	::= { bgs10FrfSPVCConnectionEntry 9}
	
bgs10FrfSPVCConnHighVPI		OBJECT-TYPE
	SYNTAX		INTEGER
	MAX-ACCESS	read-create
	STATUS		current
	DESCRIPTION
		"The high VPI."
	::= { bgs10FrfSPVCConnectionEntry 10}

bgs10FrfSPVCConnTransparentMode	OBJECT-TYPE
	SYNTAX		INTEGER { 	transparent(1),
							unPacket(2)
						}
	MAX-ACCESS	read-create
	STATUS		current	
	DESCRIPTION
		"the mode of the transparent mode."
	::= { bgs10FrfSPVCConnectionEntry 11}
		
bgs10FrfSPVCConnInterworkingType	OBJECT-TYPE
	SYNTAX		BITS {  net(0),
						service(1)}
	MAX-ACCESS	read-create
	STATUS		current
	DESCRIPTION
		"The type of the interworking."
	::= { bgs10FrfSPVCConnectionEntry 12}
	
bgs10FrfSPVCConnHighVCI		OBJECT-TYPE
	SYNTAX		Integer32
	MAX-ACCESS	read-create
	STATUS		current
	DESCRIPTION
		"The high VCI."
	::= { bgs10FrfSPVCConnectionEntry 13}
		
bgs10FrfSPVCConnHCpType	OBJECT-TYPE
	SYNTAX		UChar
	MAX-ACCESS	read-create
	STATUS		current
	DESCRIPTION
		"The high CP type."
	::= { bgs10FrfSPVCConnectionEntry 14}
		
bgs10FrfSPVCConnCreateTime	OBJECT-TYPE
	SYNTAX		TimeTicks
	MAX-ACCESS	read-create
	STATUS		current
	DESCRIPTION
		"The creating time."
	::= { bgs10FrfSPVCConnectionEntry 15}
		
bgs10FrfSPVCConnTimeChange	OBJECT-TYPE
	SYNTAX		TimeTicks
	MAX-ACCESS	read-create
	STATUS		current
	DESCRIPTION
		"The time change."
	::= { bgs10FrfSPVCConnectionEntry 16}
	
bgs10FrfSPVCConnCatchRM	OBJECT-TYPE
	SYNTAX		BITS {  not-catch(0),
						catch(1)
					 }
	MAX-ACCESS	read-create
	STATUS		current
	DESCRIPTION
		"."
	::= { bgs10FrfSPVCConnectionEntry 17}
	
bgs10FrfSPVCConnSubAdress	OBJECT-TYPE
	SYNTAX		AtmAddr
	MAX-ACCESS	read-create
	STATUS		current
	DESCRIPTION
		"The calling subaddress."
	::= { bgs10FrfSPVCConnectionEntry 18}
		
bgs10FrfSPVCConnAllowEFC	OBJECT-TYPE
	SYNTAX		BITS {  not-allow(0),
						allow(1)
					 }
	MAX-ACCESS	read-create
	STATUS		current
	DESCRIPTION
		"."
	::= { bgs10FrfSPVCConnectionEntry 19}
		
bgs10FrfSPVCConnAddressType		OBJECT-TYPE
	SYNTAX		INTEGER {	null(1),
							e164(2),
							nsap(3)}
	MAX-ACCESS	read-create
	STATUS		current
	DESCRIPTION
		"The calling addres type."
	::= { bgs10FrfSPVCConnectionEntry 20}
	
bgs10FrfSPVCConnSubAddressType	OBJECT-TYPE
	SYNTAX		INTEGER	{	null(1),
							e164(2),
							nsap(3)}
	MAX-ACCESS	read-create
	STATUS		current
	DESCRIPTION
		"The calling subaddress type."
	::= { bgs10FrfSPVCConnectionEntry 21}
	
bgs10FrfSPVCConnFrameAddressType	OBJECT-TYPE
	SYNTAX		INTEGER	{	null(1),
							e164(2)}
	MAX-ACCESS	read-create
	STATUS		current
	DESCRIPTION
		"The called address type."
	::= { bgs10FrfSPVCConnectionEntry 22}
	
bgs10FrfSPVCConnAdminstrorStatus	OBJECT-TYPE
	SYNTAX		INTEGER {	up(10),
							down(2),
							testing(3)}
	MAX-ACCESS	read-create
	STATUS		current
	DESCRIPTION
		"The adminstror status"
	::= { bgs10FrfSPVCConnectionEntry 23}
	
bgs10FrfSPVCConnPVCEndptRcvdSigStatus	OBJECT-TYPE
	SYNTAX		INTEGER { 	deleted(1),
							active(2),
							inactive(3),
							none(4)}
	MAX-ACCESS	read-create
	STATUS		current
	DESCRIPTION
		"."
	::= { bgs10FrfSPVCConnectionEntry  24}
										
bgs10FrfSPVCConnOperateStatus	OBJECT-TYPE
	SYNTAX		INTEGER { 	up(1),
							down(2)}
	MAX-ACCESS	read-create
	STATUS		current
	DESCRIPTION
		"The operate status."
	::= { bgs10FrfSPVCConnectionEntry 25}
	
bgs10FrfSPVCConnPVCAlarmReason	OBJECT-TYPE
	SYNTAX		INTEGER {	nodetect(1),
							frameAlarmed(2),
							frameClear(3),
							aisAlarmed(4),
							aisClear(5),
							rdiAlarmed(6),
							rdiClear(7)}
							
	MAX-ACCESS	read-create
	STATUS		current
	DESCRIPTION
		"The Alarm reason."
	::= { bgs10FrfSPVCConnectionEntry 26}
	
bgs10FrfSPVCConnMgtVCSigT391	OBJECT-TYPE
	SYNTAX		INTEGER
	MAX-ACCESS	read-create
	STATUS		current
	DESCRIPTION
		"."
	DEFVAL	{ 180 }
	::= { bgs10FrfSPVCConnectionEntry 27}
	
bgs10FrfSPVCConnMgtVCSigT392	OBJECT-TYPE
	SYNTAX		INTEGER
	MAX-ACCESS	read-create
	STATUS		current
	DESCRIPTION
		"."
	DEFVAL { 200 }
	::= { bgs10FrfSPVCConnectionEntry 28}
		
bgs10FrfSPVCConnPVCEndptInMaxFrameSize	OBJECT-TYPE
	SYNTAX		Integer32
	MAX-ACCESS	read-create
	STATUS		current
	DESCRIPTION
		"."
	::= { bgs10FrfSPVCConnectionEntry 29}
										
bgs10FrfSPVCConnPVCEndptInBc	OBJECT-TYPE
	SYNTAX		Integer32
	MAX-ACCESS	read-create
	STATUS		current
	DESCRIPTION
		"."
	::= { bgs10FrfSPVCConnectionEntry 30}
		
bgs10FrfSPVCConnPVCEndptInBe	OBJECT-TYPE
	SYNTAX		Integer32
	MAX-ACCESS	read-create
	STATUS		current
	DESCRIPTION
		"."
	::= { bgs10FrfSPVCConnectionEntry 31}
		
bgs10FrfSPVCConnPVCEndptInCIR	OBJECT-TYPE
	SYNTAX		Integer32
	MAX-ACCESS	read-create
	STATUS		current
	DESCRIPTION
		"."
	::= { bgs10FrfSPVCConnectionEntry 32}

bgs10FrfSPVCConnPVCEndptOutMaxFrameSize	OBJECT-TYPE
	SYNTAX		Integer32
	MAX-ACCESS	read-create
	STATUS		current
	DESCRIPTION
		"."
	::= { bgs10FrfSPVCConnectionEntry 33}
								
bgs10FrfSPVCConnPVCEndptOutBc	OBJECT-TYPE
	SYNTAX		Integer32
	MAX-ACCESS	read-create
	STATUS		current
	DESCRIPTION
		"."
	::= { bgs10FrfSPVCConnectionEntry 34}
	
bgs10FrfSPVCConnPVCEndptOutBe	OBJECT-TYPE
	SYNTAX		Integer32
	MAX-ACCESS	read-create
	STATUS		current
	DESCRIPTION
		"."
	::= { bgs10FrfSPVCConnectionEntry 35}
	
bgs10FrfSPVCConnPVCEndptOutCIR	OBJECT-TYPE
	SYNTAX		Integer32
	MAX-ACCESS	read-create
	STATUS		current
	DESCRIPTION
		"."
	::= { bgs10FrfSPVCConnectionEntry 36}
	
bgs10FrfSPVCConnMgtVCSigN391	OBJECT-TYPE
	SYNTAX		INTEGER
	MAX-ACCESS	read-create
	STATUS		current
	DESCRIPTION
		"."
	::= { bgs10FrfSPVCConnectionEntry 37}

bgs10FrfSPVCConnCrossConnectIdentifier	OBJECT-TYPE
	SYNTAX		UShort
	MAX-ACCESS	read-create
	STATUS		current
	DESCRIPTION
		"the cross connection identifier."
	::= { bgs10FrfSPVCConnectionEntry 	38 }
	
bgs10FrfSPVCConnUse		OBJECT-TYPE
	SYNTAX		INTEGER { normal(0),
						  sarnipvc(1)
						}
	MAX-ACCESS	read-create
	STATUS		current
	DESCRIPTION
		" the use type."
	::= { bgs10FrfSPVCConnectionEntry 	39 }
		
bgs10FrfSPVCConnAtmAtmAddress	OBJECT-TYPE
	SYNTAX		AtmAddr
	MAX-ACCESS	read-create
	STATUS		current
	DESCRIPTION
		"the source ATM address."
	::= { bgs10FrfSPVCConnectionEntry 	40 }
	
bgs10FrfSPVCConnFrAtmAddress		OBJECT-TYPE
	SYNTAX		AtmAddr
	MAX-ACCESS	read-create
	STATUS		current
	DESCRIPTION
		"the source ATM address."
	::= { bgs10FrfSPVCConnectionEntry 	41 }
	
bgs10FrfSPVCConnEPDFlag	OBJECT-TYPE
	SYNTAX		BITS {  not-set(0),
						set(1)
					 }
	MAX-ACCESS	read-create
	STATUS		current
	DESCRIPTION
		"."
	::= { bgs10FrfSPVCConnectionEntry 42}
	
bgs10FrfSPVCConnFeeGleanFlag	OBJECT-TYPE
	SYNTAX		BITS {  not-glean(0),
						glean(1)
					 }
	MAX-ACCESS	read-create
	STATUS		current
	DESCRIPTION
		"."
	::= { bgs10FrfSPVCConnectionEntry 43}
	
bgs10FrfSPVCConnSvcOrPvcFlag	OBJECT-TYPE
	SYNTAX		BITS {  pvc(0),
						svc(1)
					 }
	MAX-ACCESS	read-create
	STATUS		current
	DESCRIPTION
		"."
	::= { bgs10FrfSPVCConnectionEntry 44}
	
bgs10FrfSPVCConnRetries		OBJECT-TYPE
	SYNTAX		UShort
	MAX-ACCESS	read-create
	STATUS		current
	DESCRIPTION
		"."
	::= { bgs10FrfSPVCConnectionEntry 45}

bgs10FrfSPVCConnInterval	OBJECT-TYPE
	SYNTAX		UShort
	MAX-ACCESS	read-create
	STATUS		current
	DESCRIPTION
		"."
	::= { bgs10FrfSPVCConnectionEntry 46}

bgs10FrfSPVCConnPVCType	OBJECT-TYPE
	SYNTAX		Unsigned32
	MAX-ACCESS	read-create
	STATUS		current
	DESCRIPTION
		"."
	::= { bgs10FrfSPVCConnectionEntry 47}

bgs10FrfSPVCProfileFecnMode		OBJECT-TYPE
	SYNTAX		INTEGER
	MAX-ACCESS	read-create
	STATUS		current
	DESCRIPTION
		"."
	::= { bgs10FrfSPVCConnectionEntry 48}
		
bgs10FrfSPVCProfileDeMode	OBJECT-TYPE
	SYNTAX		INTEGER
	MAX-ACCESS	read-create
	STATUS		current
	DESCRIPTION
		"."
	::= { bgs10FrfSPVCConnectionEntry 49}	
	
bgs10FrfSPVCProfileClpMode	OBJECT-TYPE
	SYNTAX		INTEGER
	MAX-ACCESS	read-create
	STATUS		current
	DESCRIPTION
		"."
	::= { bgs10FrfSPVCConnectionEntry 50}
		
bgs10FrfSPVCProfileDefaultDe	OBJECT-TYPE
	SYNTAX		INTEGER
	MAX-ACCESS	read-create
	STATUS		current
	DESCRIPTION
		"."
	::= { bgs10FrfSPVCConnectionEntry 51}
		
bgs10FrfSPVCProfileDefaultClp	OBJECT-TYPE
	SYNTAX		INTEGER
	MAX-ACCESS	read-create
	STATUS		current
	DESCRIPTION
		"."
	::= { bgs10FrfSPVCConnectionEntry 52}
		
bgs10FrfSPVCProfileProtocols	OBJECT-TYPE
	SYNTAX		INTEGER { 	ethernet(1),
							ethernetFcs(2),
							tokenRing(4),
							tokenRingFcs(8),
							ipRouted(9),
							arp(16)}
	MAX-ACCESS	read-create
	STATUS		current
	DESCRIPTION
		"."
	::= { bgs10FrfSPVCConnectionEntry 53}
		
bgs10FrfSPVCProfileRefCnt	OBJECT-TYPE
	SYNTAX		INTEGER
	MAX-ACCESS	read-create
	STATUS		current
	DESCRIPTION
		"."
	::= { bgs10FrfSPVCConnectionEntry 54}

bgs10FrfSPVCConnAlarmStatus	OBJECT-TYPE
	SYNTAX		UShort
	MAX-ACCESS	read-create
	STATUS		current
	DESCRIPTION
		"."
	::= { bgs10FrfSPVCConnectionEntry 55}


--The IMA Table.
bgs10IMA				OBJECT IDENTIFIER	::= { zxbgs10mib 12}

--The IMA PVP configure table.
bgs10IMAPvpTable	OBJECT-TYPE
	SYNTAX		SEQUENCE OF BGS10IMAPvpEntry
	MAX-ACCESS	not-accessible
	STATUS		current
	DESCRIPTION
		"A list of IMA Pvp table."
	::= { bgs10IMA 1}
	
bgs10IMAPvpEntry	OBJECT-TYPE
	SYNTAX		BGS10IMAPvpEntry
	MAX-ACCESS	not-accessible
	STATUS		current
	DESCRIPTION
		"An entry in the table."
	INDEX { bgs10IMAPvpModule,
			bgs10IMAPvpLPort,
			bgs10IMAPvpLVPI
		 }
	::= { bgs10IMAPvpTable	1}
	
BGS10IMAPvpEntry ::=
	SEQUENCE {
		bgs10IMAPvpRowStatus		RowStatus,
		bgs10IMAPvpModule			UChar,
		bgs10IMAPvpLPort			UShort,
		bgs10IMAPvpLVPI				UShort,
		bgs10IMAPvpHVPI				UShort,
		bgs10IMAPvpAdminStatus		UChar,
		bgs10IMAPvpOperStatus		UChar,
		bgs10IMAPvpPortType			INTEGER
	}
	
bgs10IMAPvpRowStatus	OBJECT-TYPE
	SYNTAX		RowStatus
	MAX-ACCESS	read-create
	STATUS		current
	DESCRIPTION
		"The status of the conceptual row."
	::= { bgs10IMAPvpEntry 1}
	
bgs10IMAPvpModule		OBJECT-TYPE
	SYNTAX		UChar
	MAX-ACCESS	read-create
	STATUS		current
	DESCRIPTION
		"The module No.."
	::= { bgs10IMAPvpEntry 2}
	
bgs10IMAPvpLPort	OBJECT-TYPE
	SYNTAX		UShort
	MAX-ACCESS	read-create
	STATUS		current
	DESCRIPTION
		"The port No.."
	::= { bgs10IMAPvpEntry 3}
	
bgs10IMAPvpLVPI		OBJECT-TYPE
	SYNTAX		UShort
	MAX-ACCESS	read-create
	STATUS		current
	DESCRIPTION
		"The low VPI No.."
	::= { bgs10IMAPvpEntry 4}
	
bgs10IMAPvpHVPI		OBJECT-TYPE
	SYNTAX		UShort
	MAX-ACCESS	read-create
	STATUS		current
	DESCRIPTION
		"The high VPI No.."
	::= { bgs10IMAPvpEntry 5}
	
bgs10IMAPvpAdminStatus	OBJECT-TYPE
	SYNTAX		UChar
	MAX-ACCESS	read-create
	STATUS		current
	DESCRIPTION
		"The adminstrator's status."
	::= { bgs10IMAPvpEntry 6}
	
bgs10IMAPvpOperStatus	OBJECT-TYPE
	SYNTAX		UChar
	MAX-ACCESS	read-create
	STATUS		current
	DESCRIPTION
		"The operator's status."
	::= { bgs10IMAPvpEntry 7}
	
bgs10IMAPvpPortType		OBJECT-TYPE
	SYNTAX		INTEGER
	MAX-ACCESS	read-create
	STATUS		current
	DESCRIPTION
		"The port's type."
	::= { bgs10IMAPvpEntry 8}
	
			
--The ZXBGS10  performace MIB.
bgs10PerformanceMIB		OBJECT IDENTIFIER	::= { zxbgs10mib 15}

--The TimerUnit
TimerUnit ::= TEXTUAL-CONVENTION
	STATUS		current
	DESCRIPTION
		"It si two octet strings:the first bit indicates the tirner's unit:second
		(0),millisecond(1),the follwing 15 bits is for its value."
	SYNTAX		OCTET STRING (SIZE(2))

--PortType
PortType ::= TEXTUAL-CONVENTION
	STATUS	current
	DESCRIPTION
		"the port type."
	SYNTAX	INTEGER
	
--TimerType
TimerType ::= TEXTUAL-CONVENTION
	STATUS	current
	DESCRIPTION
		"the timer's type."
	SYNTAX	INTEGER
	
--The Performance Parameter Table.

bgs10PerformanceParamTable	OBJECT-TYPE
	SYNTAX		SEQUENCE OF BGS10PerformanceParamEntry
	MAX-ACCESS	not-accessible
	STATUS		current
	DESCRIPTION
		"A list of DAS information entries."
	::= { bgs10PerformanceMIB 1}
	
bgs10PerformanceParamEntry OBJECT-TYPE
	SYNTAX		BGS10PerformanceParamEntry
	MAX-ACCESS	not-accessible
	STATUS		current
	DESCRIPTION
		"An entry in the table."
	INDEX { PortType }
	::= { bgs10PerformanceParamTable	1}
	
BGS10PerformanceParamEntry ::=
	SEQUENCE {
		bgs10PerformanceParamRowStatus		RowStatus,
		bgs10PerformanceParamQos			INTEGER,
		bgs10PerformanceParamClrClp0		INTEGER,
		bgs10PerformanceParamClrClp1		INTEGER,
		bgs10PerformanceParamCer			INTEGER,
		bgs10PerformanceParamCtd			INTEGER,
		bgs10PerformanceParamCdv10			INTEGER,
		bgs10PerformanceParamCv7			INTEGER
	}

bgs10PerformanceParamRowStatus	OBJECT-TYPE
	SYNTAX		RowStatus
	MAX-ACCESS	read-create
	STATUS		current
	DESCRIPTION
		"The status of the conceptual row."
	::= { bgs10PerformanceParamEntry 1}
	
bgs10PerformanceParamQos	OBJECT-TYPE
	SYNTAX		INTEGER
	MAX-ACCESS	read-create
	STATUS		current
	DESCRIPTION
		"The status of the conceptual row."
	::= { bgs10PerformanceParamEntry 2}
	
bgs10PerformanceParamClrClp0	OBJECT-TYPE
	SYNTAX		INTEGER
	MAX-ACCESS	read-create
	STATUS		current
	DESCRIPTION
		"The status of the conceptual row."
	::= { bgs10PerformanceParamEntry 3}
	
bgs10PerformanceParamClrClp1	OBJECT-TYPE
	SYNTAX		INTEGER
	MAX-ACCESS	read-create
	STATUS		current
	DESCRIPTION
		"The status of the conceptual row."
	::= { bgs10PerformanceParamEntry 4}
	
bgs10PerformanceParamCer	OBJECT-TYPE
	SYNTAX		INTEGER
	MAX-ACCESS	read-create
	STATUS		current
	DESCRIPTION
		"The status of the conceptual row."
	::= { bgs10PerformanceParamEntry 5}
	
bgs10PerformanceParamCtd	OBJECT-TYPE
	SYNTAX		INTEGER
	MAX-ACCESS	read-create
	STATUS		current
	DESCRIPTION
		"The status of the conceptual row."
	::= { bgs10PerformanceParamEntry 6}
	
bgs10PerformanceParamCdv10	OBJECT-TYPE
	SYNTAX		INTEGER
	MAX-ACCESS	read-create
	STATUS		current
	DESCRIPTION
		"The status of the conceptual row."
	::= { bgs10PerformanceParamEntry 7}
	
bgs10PerformanceParamCv7	OBJECT-TYPE
	SYNTAX		INTEGER
	MAX-ACCESS	read-create
	STATUS		current
	DESCRIPTION
		"The status of the conceptual row."
	::= { bgs10PerformanceParamEntry 8}
	
--the signal timer table.

bgs10SignalTimerTable	OBJECT-TYPE
	SYNTAX		SEQUENCE OF BGS10SignalTimerEntry
	MAX-ACCESS	not-accessible
	STATUS		current
	DESCRIPTION
		"A list of DAS information entries."
	::= { bgs10PerformanceMIB 2}
	
bgs10SignalTimerEntry OBJECT-TYPE
	SYNTAX		BGS10SignalTimerEntry
	MAX-ACCESS	not-accessible
	STATUS		current
	DESCRIPTION
		"An entry in the table."
	INDEX { TimerType }
	::= { bgs10SignalTimerTable	1}
	
BGS10SignalTimerEntry ::=
	SEQUENCE {
		bgs10SignalTimerRowStatus		RowStatus,
		bgs10SignalTimerT301OrTmu1		TimerUnit,
		bgs10SignalTimerT303OrTmu2		TimerUnit,
		bgs10SignalTimerT308OrTmn1		TimerUnit,
		bgs10SignalTimerT309			TimerUnit,
		bgs10SignalTimerT310			TimerUnit,
		bgs10SignalTimerT316			TimerUnit,
		bgs10SignalTimerT317			TimerUnit,
		bgs10SignalTimerT322			TimerUnit,
		bgs10SignalTimerT302			TimerUnit,
		bgs10SignalTimerT304			TimerUnit,
		bgs10SignalTimerT306			TimerUnit,
		bgs10SignalTimerUT301			TimerUnit,
		bgs10SignalTimerUT303			TimerUnit,
		bgs10SignalTimerUT308			TimerUnit,
		bgs10SignalTimerUT309			TimerUnit,
		bgs10SignalTimerUT310			TimerUnit,
		bgs10SignalTimerUT313			TimerUnit,
		bgs10SignalTimerUT316			TimerUnit,
		bgs10SignalTimerUT317			TimerUnit,
		bgs10SignalTimerUT322			TimerUnit,
		bgs10SignalTimerUT302			TimerUnit,
		bgs10SignalTimerUT304			TimerUnit
	}
	
bgs10SignalTimerRowStatus	OBJECT-TYPE
	SYNTAX		RowStatus
	MAX-ACCESS	read-only
	STATUS		current
	DESCRIPTION
		"The status of the conceptual row."
	::= { bgs10SignalTimerEntry 1}
	
bgs10SignalTimerT301OrTmu1	OBJECT-TYPE
	SYNTAX		TimerUnit
	MAX-ACCESS	read-only
	STATUS		current
	DESCRIPTION
		"for Q2931 and Meta."
	::= { bgs10SignalTimerEntry 2}
	
bgs10SignalTimerT303OrTmu2	OBJECT-TYPE
	SYNTAX		TimerUnit
	MAX-ACCESS	read-only
	STATUS		current
	DESCRIPTION
		"for Q2931 and Meta."
	::= { bgs10SignalTimerEntry 3}
	
bgs10SignalTimerT308OrTmn1	OBJECT-TYPE
	SYNTAX		TimerUnit
	MAX-ACCESS	read-only
	STATUS		current
	DESCRIPTION
		"for Q2931 and Meta."
	::= { bgs10SignalTimerEntry 4}
	
bgs10SignalTimerT309	OBJECT-TYPE
	SYNTAX		TimerUnit
	MAX-ACCESS	read-only
	STATUS		current
	DESCRIPTION
		"only for Q2931."
	::= { bgs10SignalTimerEntry 5}

bgs10SignalTimerT310	OBJECT-TYPE
	SYNTAX		TimerUnit
	MAX-ACCESS	read-only
	STATUS		current
	DESCRIPTION
		"only for Q2931."
	::= { bgs10SignalTimerEntry 6}
	
bgs10SignalTimerT316	OBJECT-TYPE
	SYNTAX		TimerUnit
	MAX-ACCESS	read-only
	STATUS		current
	DESCRIPTION
		"only for Q2931."
	::= { bgs10SignalTimerEntry 7}
	
bgs10SignalTimerT317	OBJECT-TYPE
	SYNTAX		TimerUnit
	MAX-ACCESS	read-only
	STATUS		current
	DESCRIPTION
		"only for Q2931."
	::= { bgs10SignalTimerEntry 8}
	
bgs10SignalTimerT322	OBJECT-TYPE
	SYNTAX		TimerUnit
	MAX-ACCESS	read-only
	STATUS		current
	DESCRIPTION
		"only for Q2931."
	::= { bgs10SignalTimerEntry 9}
	
bgs10SignalTimerT302	OBJECT-TYPE
	SYNTAX		TimerUnit
	MAX-ACCESS	read-only
	STATUS		current
	DESCRIPTION
		"only for Q2931."
	::= { bgs10SignalTimerEntry 10}
	
bgs10SignalTimerT304	OBJECT-TYPE
	SYNTAX		TimerUnit
	MAX-ACCESS	read-only
	STATUS		current
	DESCRIPTION
		"only for Q2931."
	::= { bgs10SignalTimerEntry 11}
	
bgs10SignalTimerT306	OBJECT-TYPE
	SYNTAX		TimerUnit
	MAX-ACCESS	read-only
	STATUS		current
	DESCRIPTION
		"only for Q2931."
	::= { bgs10SignalTimerEntry 12}
	
bgs10SignalTimerUT301	OBJECT-TYPE
	SYNTAX		TimerUnit
	MAX-ACCESS	read-only
	STATUS		current
	DESCRIPTION
		"only for Q2931."
	::= { bgs10SignalTimerEntry 13}
	
bgs10SignalTimerUT303	OBJECT-TYPE
	SYNTAX		TimerUnit
	MAX-ACCESS	read-only
	STATUS		current
	DESCRIPTION
		"only for Q2931."
	::= { bgs10SignalTimerEntry 14}
	
bgs10SignalTimerUT308	OBJECT-TYPE
	SYNTAX		TimerUnit
	MAX-ACCESS	read-only
	STATUS		current
	DESCRIPTION
		"only for Q2931."
	::= { bgs10SignalTimerEntry 15}
	
bgs10SignalTimerUT309	OBJECT-TYPE
	SYNTAX		TimerUnit
	MAX-ACCESS	read-only
	STATUS		current
	DESCRIPTION
		"only for Q2931."
	::= { bgs10SignalTimerEntry 16}
	
bgs10SignalTimerUT310	OBJECT-TYPE
	SYNTAX		TimerUnit
	MAX-ACCESS	read-only
	STATUS		current
	DESCRIPTION
		"only for Q2931."
	::= { bgs10SignalTimerEntry 17}
	
bgs10SignalTimerUT313	OBJECT-TYPE
	SYNTAX		TimerUnit
	MAX-ACCESS	read-only
	STATUS		current
	DESCRIPTION
		"only for Q2931."
	::= { bgs10SignalTimerEntry 18}
	
bgs10SignalTimerUT316	OBJECT-TYPE
	SYNTAX		TimerUnit
	MAX-ACCESS	read-only
	STATUS		current
	DESCRIPTION
		"only for Q2931."
	::= { bgs10SignalTimerEntry 19}
	
bgs10SignalTimerUT317	OBJECT-TYPE
	SYNTAX		TimerUnit
	MAX-ACCESS	read-only
	STATUS		current
	DESCRIPTION
		"only for Q2931."
	::= { bgs10SignalTimerEntry 20}
	
bgs10SignalTimerUT322	OBJECT-TYPE
	SYNTAX		TimerUnit
	MAX-ACCESS	read-only
	STATUS		current
	DESCRIPTION
		"only for Q2931."
	::= { bgs10SignalTimerEntry 21}
	
bgs10SignalTimerUT302	OBJECT-TYPE
	SYNTAX		TimerUnit
	MAX-ACCESS	read-only
	STATUS		current
	DESCRIPTION
		"only for Q2931."
	::= { bgs10SignalTimerEntry 22}
	
bgs10SignalTimerUT304	OBJECT-TYPE
	SYNTAX		TimerUnit
	MAX-ACCESS	read-only
	STATUS		current
	DESCRIPTION
		"only for Q2931."
	::= { bgs10SignalTimerEntry 23}
	
--the ZXBGS10 signal configuration table.

bgs10SignalConfigTable	OBJECT-TYPE
	SYNTAX		SEQUENCE OF BGS10SignalConfigEntry
	MAX-ACCESS	not-accessible
	STATUS		current
	DESCRIPTION
		"A list of DAS information entries."
	::= { bgs10PerformanceMIB 3}
	
bgs10SignalConfigEntry OBJECT-TYPE
	SYNTAX		BGS10SignalConfigEntry
	MAX-ACCESS	not-accessible
	STATUS		current
	DESCRIPTION
		"An entry in the table."
	INDEX { ifIndex }
	::= { bgs10SignalConfigTable 1}
	
BGS10SignalConfigEntry ::=
	SEQUENCE {
		bgs10SignalConfigrowStatus		RowStatus,
		bgs10SignalConfigMaxCC			INTEGER,
		bgs10SignalConfigMaxPD			INTEGER,
		bgs10SignalConfigMaxSTAT		INTEGER,
		bgs10SignalConfigK				INTEGER,
		bgs10SignalConfigJ				INTEGER,
		bgs10SignalConfigTimerCC		TimerUnit,
		bgs10SignalConfigTimerKeepAlive	TimerUnit,
		bgs10SignalConfigTimerResponse	TimerUnit,
		bgs10SignalConfigTimerPoll		TimerUnit,
		bgs10SignalConfigTimerIdle		TimerUnit,
		bgs10SignalConfigSignalRate		INTEGER
	}
	
bgs10SignalConfigrowStatus	OBJECT-TYPE
	SYNTAX		RowStatus
	MAX-ACCESS	read-create
	STATUS		current
	DESCRIPTION
		"The status of the conceptual row."
	::= { bgs10SignalConfigEntry 1}
	
bgs10SignalConfigMaxCC	OBJECT-TYPE
	SYNTAX		INTEGER
	MAX-ACCESS	read-create
	STATUS		current
	DESCRIPTION
		"."
	::= { bgs10SignalConfigEntry 2}
	
bgs10SignalConfigMaxPD	OBJECT-TYPE
	SYNTAX		INTEGER
	MAX-ACCESS	read-create
	STATUS		current
	DESCRIPTION
		"."
	::= { bgs10SignalConfigEntry 3}
	
bgs10SignalConfigMaxSTAT	OBJECT-TYPE
	SYNTAX		INTEGER
	MAX-ACCESS	read-create
	STATUS		current
	DESCRIPTION
		"."
	::= { bgs10SignalConfigEntry 4}
	
bgs10SignalConfigK	OBJECT-TYPE
	SYNTAX		INTEGER
	MAX-ACCESS	read-create
	STATUS		current
	DESCRIPTION
		"."
	::= { bgs10SignalConfigEntry 5}
	
bgs10SignalConfigJ	OBJECT-TYPE
	SYNTAX		INTEGER
	MAX-ACCESS	read-create
	STATUS		current
	DESCRIPTION
		"."
	::= { bgs10SignalConfigEntry 6}
	
bgs10SignalConfigTimerCC	OBJECT-TYPE
	SYNTAX		TimerUnit
	MAX-ACCESS	read-create
	STATUS		current
	DESCRIPTION
		"."
	::= { bgs10SignalConfigEntry 7}
	
bgs10SignalConfigTimerKeepAlive	OBJECT-TYPE
	SYNTAX		TimerUnit
	MAX-ACCESS	read-create
	STATUS		current
	DESCRIPTION
		"."
	::= { bgs10SignalConfigEntry 8}
	
bgs10SignalConfigTimerResponse	OBJECT-TYPE
	SYNTAX		TimerUnit
	MAX-ACCESS	read-create
	STATUS		current
	DESCRIPTION
		"."
	::= { bgs10SignalConfigEntry 9}
	
bgs10SignalConfigTimerPoll	OBJECT-TYPE
	SYNTAX		TimerUnit
	MAX-ACCESS	read-create
	STATUS		current
	DESCRIPTION
		"."
	::= { bgs10SignalConfigEntry 10}
	
bgs10SignalConfigTimerIdle	OBJECT-TYPE
	SYNTAX		TimerUnit
	MAX-ACCESS	read-create
	STATUS		current
	DESCRIPTION
		"."
	::= { bgs10SignalConfigEntry 11}
	
bgs10SignalConfigSignalRate	OBJECT-TYPE
	SYNTAX		INTEGER
	MAX-ACCESS	read-create
	STATUS		current
	DESCRIPTION
		"."
	::= { bgs10SignalConfigEntry 12}
	
--the ZXBGS10 ISP table
bgs10IspMIB				OBJECT IDENTIFIER	::= { zxbgs10mib 16}

bgs10IspTable	OBJECT-TYPE
	SYNTAX		SEQUENCE OF BGS10IspEntry
	MAX-ACCESS	not-accessible
	STATUS		current
	DESCRIPTION
		"A list of DAS information entries."
	::= { bgs10IspMIB 1}
	
bgs10IspEntry OBJECT-TYPE
	SYNTAX		BGS10IspEntry
	MAX-ACCESS	not-accessible
	STATUS		current
	DESCRIPTION
		"An entry in the table."
	INDEX { ifIndex }
	::= { bgs10IspTable	1}
	
BGS10IspEntry ::=
	SEQUENCE {
		bgs10IspRowStatus		RowStatus,
		bgs10IspIfIndex			INTEGER,
		bgs10IspOperation		INTEGER,
		bgs10IspOperStatus		INTEGER,
		bgs10IspCommunityName	OCTET STRING
	}
	
bgs10IspRowStatus OBJECT-TYPE
	SYNTAX		RowStatus
	MAX-ACCESS	read-create
	STATUS		current
	DESCRIPTION
		"The status of the conceptual row."
	::= { bgs10IspEntry 1}
	
bgs10IspIfIndex	OBJECT-TYPE
	SYNTAX		INTEGER
	MAX-ACCESS	read-create
	STATUS		current
	DESCRIPTION
		"."
	::= { bgs10IspEntry 2}
	
bgs10IspOperation	OBJECT-TYPE
	SYNTAX		INTEGER
	MAX-ACCESS	read-create
	STATUS		current
	DESCRIPTION
		"."
	::= { bgs10IspEntry 3}
	
bgs10IspOperStatus	OBJECT-TYPE
	SYNTAX		INTEGER
	MAX-ACCESS	read-only
	STATUS		current
	DESCRIPTION
		"."
	::= { bgs10IspEntry 4}
	
bgs10IspCommunityName	OBJECT-TYPE
	SYNTAX		OCTET STRING (SIZE(20))
	MAX-ACCESS	read-only
	STATUS		current
	DESCRIPTION
		"."
	::= { bgs10IspEntry 5}

--The M4 network element table extended by ZXBGS10
bgs10M4MIB			OBJECT IDENTIFIER	::= { zxbgs10mib 17}

--The ZXBGS10 M4 NE high Level Table's extension.

bgs10M4NEHighLevelCellProtoCurrElapsedTime OBJECT-TYPE
	SYNTAX		Unsigned32
	MAX-ACCESS	read-only
	STATUS		current
	DESCRIPTION
		"."
	::= { bgs10M4MIB 1}
	
bgs10M4NEHighLevelTCProtoCurrElapsedTime OBJECT-TYPE
	SYNTAX		Unsigned32
	MAX-ACCESS	read-only
	STATUS		current
	DESCRIPTION
		"."
	::= { bgs10M4MIB 2}
	
bgs10M4NEHighLevelUpcNpcCurrElapsedTime	OBJECT-TYPE
	SYNTAX		Unsigned32
	MAX-ACCESS	read-only
	STATUS		current
	DESCRIPTION
		"."
	::= { bgs10M4MIB 3}
	
--The ZXBGS10 Port table's extension

bgs10PortTable	OBJECT-TYPE
	SYNTAX		SEQUENCE OF BGS10PortEntry
	MAX-ACCESS	not-accessible
	STATUS		current
	DESCRIPTION
		"The Port configuration table extensions.This table augments
		the Port table in af-ilmi-0065.00."
	::= { zxbgs10mib 18 }

bgs10PortEntry	OBJECT-TYPE
	SYNTAX		BGS10PortEntry
	MAX-ACCESS	not-accessible
	STATUS		current
	DESCRIPTION
		"Additional columns for the Port table entry."
	AUGMENTS { atmfPortEntry }
	::= { bgs10PortTable 1 }

BGS10PortEntry ::=
	SEQUENCE { 
		bgs10PortRMNode				UChar,
		bgs10PortRType				UChar,
		bgs10PortSpeed				Unsigned32,
		bgs10PortAisRdiActionFlag	UChar,		
		bgs10PortSDHActionFlag		UChar,
		bgs10PortUniFlag			BITS,
		bgs10PortAdminStatus		BITS,
		bgs10PortObserve			BITS,
		bgs10PortLoopFlag			BITS,
		bgs10PortLoopEnable			BITS,
		bgs10PortTransmissionType	INTEGER,
		bgs10PortMediaType			INTEGER,
		bgs10PortRowStatus		RowStatus

	}  
	
bgs10PortRMNode	OBJECT-TYPE
	SYNTAX		UChar
	MAX-ACCESS	read-create
	STATUS		current
	DESCRIPTION
		"The remote main node ."
	::= {  bgs10PortEntry 1 } 
	
bgs10PortRType	OBJECT-TYPE
	SYNTAX		UChar
	MAX-ACCESS	read-create
	STATUS		current
	DESCRIPTION
		"The remote port type."
	::= {  bgs10PortEntry 2 }
	
bgs10PortSpeed	OBJECT-TYPE
	SYNTAX		Unsigned32
	MAX-ACCESS	read-create
	STATUS		current
	DESCRIPTION
		"The speed ."
	::= { bgs10PortEntry 3 }

bgs10PortAisRdiActionFlag	OBJECT-TYPE
	SYNTAX		UChar
	MAX-ACCESS	read-create
	STATUS		current
	DESCRIPTION
		"the AID and RDI action flag."
	::= { bgs10PortEntry 4 }
	
bgs10PortSDHActionFlag		OBJECT-TYPE
	SYNTAX		UChar
	MAX-ACCESS	read-create
	STATUS		current
	DESCRIPTION
		"the SDH action flag."
	::= { bgs10PortEntry 5 }

bgs10PortUniFlag		OBJECT-TYPE
	SYNTAX		BITS { uni(0),
					   nni(1)
					}	
	MAX-ACCESS	read-create
	STATUS		current
	DESCRIPTION
		"."
	::= { bgs10PortEntry 6 }
	
bgs10PortAdminStatus	OBJECT-TYPE
	SYNTAX		BITS { unlock(0),
					   lock(1)
					}	
	MAX-ACCESS	read-create
	STATUS		current
	DESCRIPTION
		"."
	::= {	bgs10PortEntry 7 }

bgs10PortObserve		OBJECT-TYPE
	SYNTAX		BITS { disable(0),
					   enble(1)
					}	
	MAX-ACCESS	read-create
	STATUS		current
	DESCRIPTION
		"."
	::= {	bgs10PortEntry 8 }
	
bgs10PortLoopFlag	OBJECT-TYPE
	SYNTAX		BITS { inner-loop(0),
					   outer-loop(1)
					}	
	MAX-ACCESS	read-create
	STATUS		current
	DESCRIPTION
		"."
	::= {	bgs10PortEntry 9 }
	
bgs10PortLoopEnable	OBJECT-TYPE
	SYNTAX		BITS { disactive(0),
					   active(1)
					}	
	MAX-ACCESS	read-create
	STATUS		current
	DESCRIPTION
		"."
	::= {	bgs10PortEntry 10 }

bgs10PortTransmissionType	OBJECT-TYPE
	SYNTAX		INTEGER { atmfUnknownType (1),
						atmfSonetSTS3c (2),
						atmfDs3 (3),
						atmf4B5B (4),
						atmf8B10B (5),
						atmfSonetSTS12c (6),
						atmfE3 (7),
						atmfT1 (8),
						atmfE1 (9)
					}
	MAX-ACCESS	read-create
	STATUS		current
	DESCRIPTION
		"The transmission type ,refeneced to the ATH formum's port table.."
	::= {	bgs10PortEntry 11 }
	
bgs10PortMediaType		OBJECT-TYPE
	SYNTAX		INTEGER { atmfMediaUnknownType (1),
						atmfMediaCoaxCable (2),
						atmfMediaSingleMode (3),
						atmfMediaMultiMode (4),
						atmfMediaStp (5),
						atmfMediaUtp (6)
					}
	MAX-ACCESS	read-create
	STATUS		current
	DESCRIPTION
		"The mdeia type ,refeneced the ATH formum's port table."
	::= {	bgs10PortEntry 12 }

bgs10PortRowStatus		OBJECT-TYPE
	SYNTAX		RowStatus
	MAX-ACCESS	read-create
	STATUS		current
	DESCRIPTION
		"The mdeia type ,refeneced the ATH formum's port table."
	::= {	bgs10PortEntry 13 }

--The VPI map VPI table.Each tables can be indexed by two: one is
--The Number of the Module, the other is interface Index.
bgs10VpiMapEsVpiMIB		OBJECT IDENTIFIER	::= { zxbgs10mib 19}

--The VpiMapEsVpi table indexed by the Module.

bgs10ModulePortVpiMapEsVpiTable	OBJECT-TYPE
	SYNTAX		SEQUENCE OF BGS10ModulePortVpiMapEsVpiEntry
	MAX-ACCESS	not-accessible
	STATUS		current
	DESCRIPTION
		"A list of VPI Map ES VPI information entries."
	::= { bgs10VpiMapEsVpiMIB 1}
	
bgs10ModulePortVpiMapEsVpiEntry OBJECT-TYPE
	SYNTAX		BGS10ModulePortVpiMapEsVpiEntry
	MAX-ACCESS	not-accessible
	STATUS		current
	DESCRIPTION
		"An entry in the table."
	INDEX { bgs10ModulePortVpiMapEsVpiModule }
	::= { bgs10ModulePortVpiMapEsVpiTable	1}
	
BGS10ModulePortVpiMapEsVpiEntry ::=
	SEQUENCE {
		bgs10ModulePortVpiMapEsVpiRowStatus		RowStatus,
		bgs10ModulePortVpiMapEsVpiPort			INTEGER,
		bgs10ModulePortVpiMapEsVpiSigChannel	BITS,
		bgs10ModulePortVpiMapEsVpiMyVpi			INTEGER,
		bgs10ModulePortVpiMapEsVpiIfIndex		INTEGER,
		bgs10ModulePortVpiMapEsVpiRVpi			INTEGER,
		bgs10ModulePortVpiMapEsVpiModule		INTEGER
	}
	
bgs10ModulePortVpiMapEsVpiRowStatus	OBJECT-TYPE
	SYNTAX		RowStatus
	MAX-ACCESS	read-create
	STATUS		current
	DESCRIPTION
		"The status of the conceptual row."
	::= { bgs10ModulePortVpiMapEsVpiEntry 1}
	
bgs10ModulePortVpiMapEsVpiPort	OBJECT-TYPE
	SYNTAX		INTEGER
	MAX-ACCESS	read-create
	STATUS		current
	DESCRIPTION
		"."
	::= { bgs10ModulePortVpiMapEsVpiEntry 2}
	
bgs10ModulePortVpiMapEsVpiSigChannel	OBJECT-TYPE
	SYNTAX		BITS { 	no(0),
						yes(1)}
	MAX-ACCESS	read-create
	STATUS		current
	DESCRIPTION
		"."
	::= { bgs10ModulePortVpiMapEsVpiEntry 3}
	
bgs10ModulePortVpiMapEsVpiMyVpi	OBJECT-TYPE
	SYNTAX		INTEGER
	MAX-ACCESS	read-create
	STATUS		current
	DESCRIPTION
		"."
	::= { bgs10ModulePortVpiMapEsVpiEntry 4}

bgs10ModulePortVpiMapEsVpiIfIndex	OBJECT-TYPE
	SYNTAX		INTEGER
	MAX-ACCESS	read-create
	STATUS		current
	DESCRIPTION
		"."
	::= { bgs10ModulePortVpiMapEsVpiEntry 5}
	
bgs10ModulePortVpiMapEsVpiRVpi	OBJECT-TYPE
	SYNTAX		INTEGER
	MAX-ACCESS	read-create
	STATUS		current
	DESCRIPTION
		"."
	::= { bgs10ModulePortVpiMapEsVpiEntry 6}
	
bgs10ModulePortVpiMapEsVpiModule	OBJECT-TYPE
	SYNTAX		INTEGER
	MAX-ACCESS	read-create
	STATUS		current
	DESCRIPTION
		"."
	::= { bgs10ModulePortVpiMapEsVpiEntry 7}


--The VPI table indexed by ifIndex.

bgs10IfIndexVpiMapEsVpiTable	OBJECT-TYPE
	SYNTAX		SEQUENCE OF BGS10IfIndexVpiMapEsVpiEntry
	MAX-ACCESS	not-accessible
	STATUS		current
	DESCRIPTION
		"A list of VPI Map ES VPI information entries."
	::= { bgs10VpiMapEsVpiMIB 2}
	
bgs10IfIndexVpiMapEsVpiEntry OBJECT-TYPE
	SYNTAX		BGS10IfIndexVpiMapEsVpiEntry
	MAX-ACCESS	not-accessible
	STATUS		current
	DESCRIPTION
		"An entry in the table."
	INDEX { bgs10IfIndexVpiMapEsVpiMyVpi }
	::= { bgs10IfIndexVpiMapEsVpiTable	1}
	
BGS10IfIndexVpiMapEsVpiEntry ::=
	SEQUENCE {
		bgs10IfIndexVpiMapEsVpiRowStatus	RowStatus,
		bgs10IfIndexVpiMapEsVpiPort			INTEGER,
		bgs10IfIndexVpiMapEsVpiSigChannel	BITS,
		bgs10IfIndexVpiMapEsVpiMyVpi		INTEGER,
		bgs10IfIndexVpiMapEsVpiIfIndex		INTEGER,
		bgs10IfIndexVpiMapEsVpiRVpi			INTEGER,
		bgs10IfIndexVpiMapEsVpiModule		INTEGER
	}
	
bgs10IfIndexVpiMapEsVpiRowStatus	OBJECT-TYPE
	SYNTAX		RowStatus
	MAX-ACCESS	read-create
	STATUS		current
	DESCRIPTION
		"The status of the conceptual row."
	::= { bgs10IfIndexVpiMapEsVpiEntry 1}
	
bgs10IfIndexVpiMapEsVpiPort	OBJECT-TYPE
	SYNTAX		INTEGER
	MAX-ACCESS	read-create
	STATUS		current
	DESCRIPTION
		"."
	::= { bgs10IfIndexVpiMapEsVpiEntry 2}
	
bgs10IfIndexVpiMapEsVpiSigChannel	OBJECT-TYPE
	SYNTAX		BITS { 	no(0),
						yes(1)}
	MAX-ACCESS	read-create
	STATUS		current
	DESCRIPTION
		"."
	::= { bgs10IfIndexVpiMapEsVpiEntry 3}
	
bgs10IfIndexVpiMapEsVpiMyVpi	OBJECT-TYPE
	SYNTAX		INTEGER
	MAX-ACCESS	read-create
	STATUS		current
	DESCRIPTION
		"."
	::= { bgs10IfIndexVpiMapEsVpiEntry 4}

bgs10IfIndexVpiMapEsVpiIfIndex	OBJECT-TYPE
	SYNTAX		INTEGER
	MAX-ACCESS	read-create
	STATUS		current
	DESCRIPTION
		"."
	::= { bgs10IfIndexVpiMapEsVpiEntry 5}
	
bgs10IfIndexVpiMapEsVpiRVpi	OBJECT-TYPE
	SYNTAX		INTEGER
	MAX-ACCESS	read-create
	STATUS		current
	DESCRIPTION
		"."
	::= { bgs10IfIndexVpiMapEsVpiEntry 6}
	
bgs10IfIndexVpiMapEsVpiModule	OBJECT-TYPE
	SYNTAX		INTEGER
	MAX-ACCESS	read-only
	STATUS		current
	DESCRIPTION
		"."
	::= { bgs10IfIndexVpiMapEsVpiEntry 7}
			   	 
--The ZXBGS10 interface Configuration extensions.

bgs10IfConfigureTable	OBJECT-TYPE
	SYNTAX		SEQUENCE OF BGS10IfConfigureEntry
	MAX-ACCESS	not-accessible
	STATUS		current
	DESCRIPTION
		"The ZXBGS10 ATM interface configuration table extensions.This table 
		augments the atm interface configuration table in RFC 1695."
	::= { zxbgs10mib 20 }
	
bgs10IfConfigureEntry	OBJECT-TYPE
	SYNTAX		BGS10IfConfigureEntry
	MAX-ACCESS	not-accessible
	STATUS		current
	DESCRIPTION	
		"Additional columns for the ATM interface configuration table entry."
	AUGMENTS	{ atmInterfaceConfEntry }
	::= { bgs10IfConfigureTable 1}
	
BGS10IfConfigureEntry	::=
	SEQUENCE {
		bgs10IfConfigurePort		UChar,
		bgs10IfConfigureAdminState	UChar,
		bgs10IfConfigureOperState	UChar,
		bgs10IfConfigureSigVpi		INTEGER
	}
	
bgs10IfConfigurePort	OBJECT-TYPE
	SYNTAX		UChar
	MAX-ACCESS	read-write
	STATUS		current
	DESCRIPTION
		"The Port Number."
	::= { bgs10IfConfigureEntry	1 }

bgs10IfConfigureAdminState	OBJECT-TYPE
	SYNTAX		UChar
	MAX-ACCESS	read-write
	STATUS		current
	DESCRIPTION
		"A control object to indicate the administratively desired state of the 
	interface configuration."
	::= { bgs10IfConfigureEntry	2 }

bgs10IfConfigureOperState	OBJECT-TYPE
	SYNTAX		UChar
	MAX-ACCESS	read-only
	STATUS		current
	DESCRIPTION
		"A status object to indicate the operational state of the interface 
	configuration."
	::= { bgs10IfConfigureEntry	3 }
	
bgs10IfConfigureSigVpi		OBJECT-TYPE
	SYNTAX		INTEGER
	MAX-ACCESS	read-only
	STATUS		current
	DESCRIPTION
		""
	::= { bgs10IfConfigureEntry	4 }
	
--The ZXBGS10  the LEC Configuration table extension. 

bgs10LecConfigTable	OBJECT-TYPE
	SYNTAX		SEQUENCE OF BGS10LecConfigEntry
	MAX-ACCESS	not-accessible
	STATUS		current
	DESCRIPTION
		"The LEC configuration table extension,the table augments
		the LEC configuration table in AF-LANE-0057.000."
	::= { zxbgs10mib 21 }
	
bgs10LecConfigEntry	OBJECT-TYPE
	SYNTAX		BGS10LecConfigEntry
	MAX-ACCESS	not-accessible
	STATUS		current
	DESCRIPTION
		"Additional columns  for the LEC configuraton table entry."
	AUGMENTS { lecConfigEntry }
	::= { bgs10LecConfigTable 1}
	
BGS10LecConfigEntry ::= 
    SEQUENCE {
    	bgs10LecConfigModule	UChar
    }
    
bgs10LecConfigModule	OBJECT-TYPE
	SYNTAX		UChar
	MAX-ACCESS	read-create
	STATUS		current
	DESCRIPTION
		"The Module Number of the LEC."
	::= { bgs10LecConfigEntry 1}

--The ZXBGS10 ELAN configuration table extensions.

bgs10ElanConfTable	OBJECT-TYPE
	SYNTAX		SEQUENCE OF BGS10ELANConfEntry
	MAX-ACCESS	not-accessible
	STATUS		current
	DESCRIPTION
		"The ELAN configuration table extension.This table augments the
		ELAN configuration table.This Table augments the ELAN configu-
		ration in af-lane-0057.000."			
	::= { zxbgs10mib 22 }
	
bgs10ElanConfEntry	OBJECT-TYPE
	SYNTAX		BGS10ELANConfEntry
	MAX-ACCESS	not-accessible
	STATUS		current
	DESCRIPTION
		"Additional columns for the ELAN configuration table entry."
	AUGMENTS { elanConfEntry }
	::= { bgs10ElanConfTable 1 }

BGS10ELANConfEntry ::=
	SEQUENCE {
		bgs10ElanConfModule	UChar
	}
	
bgs10ElanConfModule	OBJECT-TYPE
	SYNTAX		UChar
	MAX-ACCESS	read-create
	STATUS		current
	DESCRIPTION
		"The Module of the ELAN."
	::= { bgs10ElanConfEntry 1 }
	
--The ZXBGS10 LECS configuration table extensions.

bgs10LecsConfigTable	OBJECT-TYPE
	SYNTAX		SEQUENCE OF BGS10LECSConfigEntry
	MAX-ACCESS	not-accessible
	STATUS		current
	DESCRIPTION
		"The LECS confugration table extensions.This table augments
		the LESCS table in af-lane-0057.000."
	::= { zxbgs10mib 23 }

bgs10LecsConfigEntry	OBJECT-TYPE
	SYNTAX		BGS10LECSConfigEntry
	MAX-ACCESS	not-accessible
	STATUS		current
	DESCRIPTION
		"Additional columns for the LECS configuration table entry."
	AUGMENTS { lecsConfEntry }
	::= { bgs10LecsConfigTable 1 }

BGS10LECSConfigEntry ::=
	SEQUENCE { 
		bgs10LecsModule		UChar
	}      
	
bgs10LecsModule	OBJECT-TYPE
	SYNTAX		UChar
	MAX-ACCESS	read-create
	STATUS		current
	DESCRIPTION
		"The Module of LECS."
	::= {  bgs10LecsConfigEntry 1 }
	
--The ZXBGS!0 LECS TLV table extensions.

bgs10LecsTLVTable	OBJECT-TYPE
	SYNTAX		SEQUENCE OF BGS10LecsTLVEntry
	MAX-ACCESS	not-accessible
	STATUS		current
	DESCRIPTION
		"The LECS TLV table extensions.This table augments
		the LESCS TLV table in af-lane-0057.000."
	::= { zxbgs10mib 24 }

bgs10LecsTLVEntry	OBJECT-TYPE
	SYNTAX		BGS10LecsTLVEntry
	MAX-ACCESS	not-accessible
	STATUS		current
	DESCRIPTION
		"Additional columns for the LECS TLV table entry."
	AUGMENTS { lecsTlvEntry }
	::= { bgs10LecsTLVTable 1 }

BGS10LecsTLVEntry ::=
	SEQUENCE { 
		bgs10LecsTLVLength		UChar
	} 
	
bgs10LecsTLVLength	OBJECT-TYPE
	SYNTAX		UChar
	MAX-ACCESS	read-create
	STATUS		current
	DESCRIPTION
		"The Length of LECS TLV."
	::= {  bgs10LecsTLVEntry 1 }
 
 --The ZXBGS10 LES configuration table extensions.
 
bgs10LesConfigTable	OBJECT-TYPE
	SYNTAX		SEQUENCE OF BGS10LesConfigEntry
	MAX-ACCESS	not-accessible
	STATUS		current
	DESCRIPTION
		"The LES confugration table extensions.This table augments
		the LES table in af-lane-0057.000."
	::= { zxbgs10mib 25 }

bgs10LesConfigEntry	OBJECT-TYPE
	SYNTAX		BGS10LesConfigEntry
	MAX-ACCESS	not-accessible
	STATUS		current
	DESCRIPTION
		"Additional columns for the LES configuration table entry."
	AUGMENTS { lesConfEntry }
	::= { bgs10LesConfigTable 1 }

BGS10LesConfigEntry ::=
	SEQUENCE { 
		bgs10LesModule		UChar
	}
	
bgs10LesModule	OBJECT-TYPE
	SYNTAX		UChar
	MAX-ACCESS	read-create
	STATUS		current
	DESCRIPTION
		"The Module of LES."
	::= {  bgs10LesConfigEntry 1 }
                  
--The ZXBGS10 BUS configuration table extensions.

bgs10BusConfigureTable	OBJECT-TYPE
	SYNTAX		SEQUENCE OF BGS10BusConfigureEntry
	MAX-ACCESS	not-accessible
	STATUS		current
	DESCRIPTION
		"The Bus confugration table extensions.This table augments
		the Bus table in af-lane-0057.000."
	::= { zxbgs10mib 26 }

bgs10BusConfigureEntry	OBJECT-TYPE
	SYNTAX		BGS10BusConfigureEntry
	MAX-ACCESS	not-accessible
	STATUS		current
	DESCRIPTION
		"Additional columns for the Bus configuration table entry."
	AUGMENTS { busConfEntry }
	::= { bgs10BusConfigureTable 1 }

BGS10BusConfigureEntry ::=
	SEQUENCE { 
		bgs10BusModule		UChar
	}
	
bgs10BusModule	OBJECT-TYPE
	SYNTAX		UChar
	MAX-ACCESS	read-create
	STATUS		current
	DESCRIPTION
		"The Module of BuS."
	::= {  bgs10BusConfigureEntry 1 }
	
bgs10Pvp							OBJECT IDENTIFIER	::= { zxbgs10mib 27 }
bgs10PvpTable	OBJECT-TYPE
	SYNTAX		SEQUENCE OF BGS10PvpEntry
	MAX-ACCESS	not-accessible
	STATUS		current
	DESCRIPTION
		"The PVP Configure information table for zxb10 and its successor."
	::= { bgs10Pvp 1 }

bgs10PvpEntry	OBJECT-TYPE
	SYNTAX		BGS10PvpEntry
	MAX-ACCESS	not-accessible
	STATUS		current
	DESCRIPTION
		"The entry to the PVP configration table."
	INDEX {	bgs10PvpLModule,
			bgs10PvpLPort,
			bgs10PvpLVpi,
			bgs10PvpHModule,
			bgs10PvpHPort,
			bgs10PvpHVpi			
		}
	::= { bgs10PvpTable 1 }

BGS10PvpEntry ::=
	SEQUENCE {
		bgs10PvpRowStatus				RowStatus,
		bgs10PvpLVpi					INTEGER,
		bgs10PvpL2HtrafficDescrType		INTEGER,
		bgs10PvpLModule					INTEGER,
		bgs10PvpHModule					INTEGER,
		bgs10PvpHPort					INTEGER,
		bgs10PvpLPort					INTEGER,
		bgs10PvpHVpi					INTEGER,
		bgs10PvpL2HtrafficQosClass		INTEGER,
		bgs10PvpH2LtrafficDescrType		INTEGER,
		bgs10PvpH2LtrafficQosClass		INTEGER,
		bgs10PvpPvpAdminStatus			INTEGER,
		bgs10PvpConnectStruct			INTEGER,
		bgs10PvpServiceCategory			INTEGER,
		bgs10PvpPvpOperStatus			INTEGER,
		bgs10PvpLCPType					INTEGER,
		bgs10PvpHCPType					INTEGER,
		bgs10PvpConnectType				INTEGER,
		bgs10PvpUse						INTEGER,
		bgs10PvpLAtmAddress				AtmAddr,
		bgs10PvpL2HtrafficDescrParam1	Unsigned32,
		bgs10PvpL2HtrafficDescrParam2	Unsigned32,
		bgs10PvpL2HtrafficDescrParam3	Unsigned32,
		bgs10PvpL2HtrafficDescrParam4	Unsigned32,
		bgs10PvpL2HtrafficDescrParam5	Unsigned32,
		bgs10PvpHAtmAddress				AtmAddr,
		bgs10PvpH2LtrafficDescrParam1	Unsigned32,
		bgs10PvpH2LtrafficDescrParam2	Unsigned32,
		bgs10PvpH2LtrafficDescrParam3	Unsigned32,
		bgs10PvpH2LtrafficDescrParam4	Unsigned32,
		bgs10PvpH2LtrafficDescrParam5	Unsigned32,
		bgs10PvpPMPConnectTag			UShort,
		bgs10PvpCrossConnectIdentifier	UShort,
		bgs10PvpCatchRM					BITS,
		bgs10PvpAllowEFC				BITS,
		bgs10PvpEPDFlag					BITS,
		bgs10PvpFeeGleanFlag			BITS,
		bgs10PvpPmodule					Unsigned32,
		bgs10PvpPVCType					Unsigned32,
		bgs10PvpManualControl			Unsigned32,
		bgs10PvpPport					Unsigned32,
		bgs10PvpPSwitchType				Unsigned32,
		bgs10PvpPvcPOperStatus			Unsigned32,
		bgs10PvpPVPI					Unsigned32,
		bgs10PvpOperatingMode			Unsigned32,
		bgs10PvpPCPType					Unsigned32,
		bgs10PvpPVCI					UShort,
		bgs10PvpPAtmAddress				AtmAddr,
		bgs10PvpGroupid					UShort,
		bgs10PvpAlarmStatus				UShort,
		bgs10PvpPolicing				UCHAR,
		bgs10PvpPacketType				UCHAR,
		bgs10PvpPCSInd					UCHAR		
	}
	
bgs10PvpRowStatus	OBJECT-TYPE
	SYNTAX		RowStatus
	MAX-ACCESS	read-create
	STATUS		current
	DESCRIPTION
		"."
	::= { bgs10PvpEntry 1}
	
bgs10PvpLVpi	OBJECT-TYPE
	SYNTAX		INTEGER
	MAX-ACCESS	read-create
	STATUS		current
	DESCRIPTION
		"VPI connection's VPI."
	::= { bgs10PvpEntry 2}
	
bgs10PvpL2HtrafficDescrType	OBJECT-TYPE
	SYNTAX		INTEGER
	MAX-ACCESS	read-create
	STATUS		current
	DESCRIPTION
		"."
	::= { bgs10PvpEntry 3}
	
bgs10PvpLModule		OBJECT-TYPE
	SYNTAX		INTEGER
	MAX-ACCESS	read-create
	STATUS		current
	DESCRIPTION
		"."
	::= { bgs10PvpEntry 4}
	
bgs10PvpHModule	OBJECT-TYPE
	SYNTAX		INTEGER
	MAX-ACCESS	read-create
	STATUS		current
	DESCRIPTION
		"."
	::= { bgs10PvpEntry 5}
	
bgs10PvpHPort	OBJECT-TYPE
	SYNTAX		INTEGER
	MAX-ACCESS	read-create
	STATUS		current
	DESCRIPTION
		"."
	::= { bgs10PvpEntry 6}
	
bgs10PvpLPort	OBJECT-TYPE
	SYNTAX		INTEGER
	MAX-ACCESS	read-create
	STATUS		current
	DESCRIPTION
		"."
	::= { bgs10PvpEntry 7}
	
bgs10PvpHVpi	OBJECT-TYPE
	SYNTAX		INTEGER
	MAX-ACCESS	read-create
	STATUS		current
	DESCRIPTION
		"."
	::= { bgs10PvpEntry 8}
	
bgs10PvpL2HtrafficQosClass	OBJECT-TYPE
	SYNTAX		INTEGER
	MAX-ACCESS	read-create
	STATUS		current
	DESCRIPTION
		"."
	::= { bgs10PvpEntry 9}
	
bgs10PvpH2LtrafficDescrType	OBJECT-TYPE
	SYNTAX		INTEGER
	MAX-ACCESS	read-create
	STATUS		current
	DESCRIPTION
		"."
	::= { bgs10PvpEntry 10}
	
bgs10PvpH2LtrafficQosClass	OBJECT-TYPE
	SYNTAX		INTEGER
	MAX-ACCESS	read-create
	STATUS		current
	DESCRIPTION
		"."
	::= { bgs10PvpEntry 11}
	
bgs10PvpPvpAdminStatus	OBJECT-TYPE
	SYNTAX		INTEGER
	MAX-ACCESS	read-create
	STATUS		current
	DESCRIPTION
		"."
	::= { bgs10PvpEntry 12}
	
bgs10PvpConnectStruct	OBJECT-TYPE
	SYNTAX		INTEGER { 	bip2p(1),
							sigp2mp(2),
							sigmp2p(3),
							mp2mp(4),
							bip2mp(5)}
	MAX-ACCESS	read-create
	STATUS		current
	DESCRIPTION
		"Pvp Connection type:
		--bi-directional point to point (1)
		--signal directional point to multi-points (2)
		--signal directional multi-points to point (3)
		--multi-points to multi-points (4)
		--bi-dirctional point to multi-points (5)."
	::= { bgs10PvpEntry 13}
	
bgs10PvpServiceCategory	OBJECT-TYPE
	SYNTAX		INTEGER
	MAX-ACCESS	read-create
	STATUS		current
	DESCRIPTION
		"."
	::= { bgs10PvpEntry 14}
	
bgs10PvpPvpOperStatus	OBJECT-TYPE
	SYNTAX		INTEGER
	MAX-ACCESS	read-only
	STATUS		current
	DESCRIPTION
		"."
	::= { bgs10PvpEntry 15}
	
bgs10PvpLCPType	OBJECT-TYPE
	SYNTAX		INTEGER	{	segEndPtNo(0),
							segEndPtYes(1)
						}
	MAX-ACCESS	read-create
	STATUS		current
	DESCRIPTION
		"."
	::= { bgs10PvpEntry 16}
	
bgs10PvpHCPType	OBJECT-TYPE
	SYNTAX		INTEGER	{	segEndPtNo(0),
							segEndPtYes(1)
						}
	MAX-ACCESS	read-create
	STATUS		current
	DESCRIPTION
		"."
	::= { bgs10PvpEntry 17}
	
bgs10PvpConnectType	OBJECT-TYPE
	SYNTAX		INTEGER
	MAX-ACCESS	read-create
	STATUS		current
	DESCRIPTION
		"."
	::= { bgs10PvpEntry 18}
	
bgs10PvpUse	OBJECT-TYPE
	SYNTAX		INTEGER { 	general(0),
							configureDirectVCC(1),
							controlDirectVCC(2),
							controlDistributeVCC(3),
							dataDirectVCC(4),
							multicastSendVCC(5),
							mulitcastForwardVCC(6)}
	MAX-ACCESS	read-create
	STATUS		current
	DESCRIPTION
		"."
	::= { bgs10PvpEntry 19}		
	
bgs10PvpLAtmAddress	OBJECT-TYPE
	SYNTAX		AtmAddr
	MAX-ACCESS	read-create
	STATUS		current
	DESCRIPTION
		"."
	::= { bgs10PvpEntry 20}
				
bgs10PvpL2HtrafficDescrParam1	OBJECT-TYPE
	SYNTAX		Unsigned32
	MAX-ACCESS	read-create
	STATUS		current
	DESCRIPTION
		"."
	::= { bgs10PvpEntry 21}
	
bgs10PvpL2HtrafficDescrParam2	OBJECT-TYPE
	SYNTAX		Unsigned32
	MAX-ACCESS	read-create
	STATUS		current
	DESCRIPTION
		"."
	::= { bgs10PvpEntry 22}
	
bgs10PvpL2HtrafficDescrParam3	OBJECT-TYPE
	SYNTAX		Unsigned32
	MAX-ACCESS	read-create
	STATUS		current
	DESCRIPTION
		"."
	::= { bgs10PvpEntry 23}
	
bgs10PvpL2HtrafficDescrParam4	OBJECT-TYPE
	SYNTAX		Unsigned32
	MAX-ACCESS	read-create
	STATUS		current
	DESCRIPTION
		"."
	::= { bgs10PvpEntry 24}
	
bgs10PvpL2HtrafficDescrParam5	OBJECT-TYPE
	SYNTAX		Unsigned32
	MAX-ACCESS	read-create
	STATUS		current
	DESCRIPTION
		"."
	::= { bgs10PvpEntry 25}
	
bgs10PvpHAtmAddress	OBJECT-TYPE
	SYNTAX		AtmAddr
	MAX-ACCESS	read-create
	STATUS		current
	DESCRIPTION
		"."
	::= { bgs10PvpEntry 26}
	
bgs10PvpH2LtrafficDescrParam1	OBJECT-TYPE
	SYNTAX		Unsigned32
	MAX-ACCESS	read-create
	STATUS		current
	DESCRIPTION
		"."
	::= { bgs10PvpEntry 27}
	
bgs10PvpH2LtrafficDescrParam2	OBJECT-TYPE
	SYNTAX		Unsigned32
	MAX-ACCESS	read-create
	STATUS		current
	DESCRIPTION
		"."
	::= { bgs10PvpEntry 28}
	
bgs10PvpH2LtrafficDescrParam3	OBJECT-TYPE
	SYNTAX		Unsigned32
	MAX-ACCESS	read-create
	STATUS		current
	DESCRIPTION
		"."
	::= { bgs10PvpEntry 29}
	
bgs10PvpH2LtrafficDescrParam4	OBJECT-TYPE
	SYNTAX		Unsigned32
	MAX-ACCESS	read-create
	STATUS		current
	DESCRIPTION
		"."
	::= { bgs10PvpEntry 30}
	
bgs10PvpH2LtrafficDescrParam5	OBJECT-TYPE
	SYNTAX		Unsigned32
	MAX-ACCESS	read-create
	STATUS		current
	DESCRIPTION
		"."
	::= { bgs10PvpEntry 31} 
	
bgs10PvpPMPConnectTag	OBJECT-TYPE
	SYNTAX		UShort
	MAX-ACCESS	read-only
	STATUS		current
	DESCRIPTION
		"the PMP connection tag."
	::= { bgs10PvpEntry 32 }
	
bgs10PvpCrossConnectIdentifier	OBJECT-TYPE
	SYNTAX		UShort
	MAX-ACCESS	read-only
	STATUS		current
	DESCRIPTION
		"the cross connection identifier."
	::= { bgs10PvpEntry 33 } 

bgs10PvpCatchRM	OBJECT-TYPE
	SYNTAX		BITS { not-catch(0),
					   catch(1)
					 }
	MAX-ACCESS	read-only
	STATUS		current
	DESCRIPTION
		"."
	::= { bgs10PvpEntry 34 } 
	
bgs10PvpAllowEFC	OBJECT-TYPE
	SYNTAX		BITS { not-allow(0),
					   allow(1)
					 }
	MAX-ACCESS	read-only
	STATUS		current
	DESCRIPTION
		"."
	::= { bgs10PvpEntry 35 } 
	
bgs10PvpEPDFlag		OBJECT-TYPE
	SYNTAX		BITS { not-set(0),
					   set(1)
					 }
	MAX-ACCESS	read-only
	STATUS		current
	DESCRIPTION
		"."
	::= { bgs10PvpEntry 36 } 
	
bgs10PvpFeeGleanFlag	OBJECT-TYPE
	SYNTAX		BITS { not-glean(0),
					   glean(1)
					 }
	MAX-ACCESS	read-only
	STATUS		current
	DESCRIPTION
		"."
	::= { bgs10PvpEntry 37 } 

bgs10PvpPmodule	OBJECT-TYPE
	SYNTAX		Unsigned32
	MAX-ACCESS	read-only
	STATUS		current
	DESCRIPTION
		"."
	::= { bgs10PvpEntry 38 }

bgs10PvpPVCType	OBJECT-TYPE
	SYNTAX		Unsigned32
	MAX-ACCESS	read-only
	STATUS		current
	DESCRIPTION
		"."
	::= { bgs10PvpEntry 39 }

bgs10PvpManualControl	OBJECT-TYPE
	SYNTAX		Unsigned32
	MAX-ACCESS	read-only
	STATUS		current
	DESCRIPTION
		"."
	::= { bgs10PvpEntry 40 }

bgs10PvpPport	OBJECT-TYPE
	SYNTAX		Unsigned32
	MAX-ACCESS	read-only
	STATUS		current
	DESCRIPTION
		"."
	::= { bgs10PvpEntry 41 }

bgs10PvpPSwitchType	OBJECT-TYPE
	SYNTAX		Unsigned32
	MAX-ACCESS	read-only
	STATUS		current
	DESCRIPTION
		"."
	::= { bgs10PvpEntry 42 }

bgs10PvpPvcPOperStatus	OBJECT-TYPE
	SYNTAX		Unsigned32
	MAX-ACCESS	read-only
	STATUS		current
	DESCRIPTION
		"."
	::= { bgs10PvpEntry 43 }

bgs10PvpPVPI	OBJECT-TYPE
	SYNTAX		Unsigned32
	MAX-ACCESS	read-only
	STATUS		current
	DESCRIPTION
		"."
	::= { bgs10PvpEntry 44 }

bgs10PvpOperatingMode	OBJECT-TYPE
	SYNTAX		Unsigned32
	MAX-ACCESS	read-only
	STATUS		current
	DESCRIPTION
		"."
	::= { bgs10PvpEntry 45 }

bgs10PvpPCPType	OBJECT-TYPE
	SYNTAX		Unsigned32
	MAX-ACCESS	read-only
	STATUS		current
	DESCRIPTION
		"."
	::= { bgs10PvpEntry 46 }

bgs10PvpPVCI	OBJECT-TYPE
	SYNTAX		UShort
	MAX-ACCESS	read-only
	STATUS		current
	DESCRIPTION
		"."
	::= { bgs10PvpEntry 47 }

bgs10PvpPAtmAddress	OBJECT-TYPE
	SYNTAX		AtmAddr
	MAX-ACCESS	read-only
	STATUS		current
	DESCRIPTION
		"."
	::= { bgs10PvpEntry 48 }

bgs10PvpGroupid	OBJECT-TYPE
	SYNTAX		UShort
	MAX-ACCESS	read-only
	STATUS		current
	DESCRIPTION
		"."
	::= { bgs10PvpEntry 49 }

bgs10PvpAlarmStatus	OBJECT-TYPE
	SYNTAX		UShort
	MAX-ACCESS	read-only
	STATUS		current
	DESCRIPTION
		"."
	::= { bgs10PvpEntry 50 }
	
bgs10PvpPolicing	OBJECT-TYPE	
	SYNTAX		UCHAR
	MAX-ACCESS	read-only
	STATUS		current
	DESCRIPTION
		"."
	::= { bgs10PvpEntry 51 }

bgs10PvpPacketType	OBJECT-TYPE	
	SYNTAX		UCHAR
	MAX-ACCESS	read-only
	STATUS		current
	DESCRIPTION
		"."
	::= { bgs10PvpEntry 52 }

bgs10PvpPCSInd	OBJECT-TYPE	
	SYNTAX		UCHAR
	MAX-ACCESS	read-only
	STATUS		current
	DESCRIPTION
		"."
	::= { bgs10PvpEntry 53 }
	

-- The supplyment to the CES confiugration 

bgs10CesConfigTable	OBJECT-TYPE
	SYNTAX		SEQUENCE OF BGS10CesConfigEntry
	MAX-ACCESS	not-accessible
	STATUS		current
	DESCRIPTION
		"The CES confugration table extensions.This table augments
		the LES table in af-?????????."
	::= { zxbgs10mib 28 }

bgs10CesConfigEntry	OBJECT-TYPE
	SYNTAX		BGS10CesConfigEntry
	MAX-ACCESS	not-accessible
	STATUS		current
	DESCRIPTION
		"Additional columns for the CES configuration table entry."
	AUGMENTS { atmfCESConfEntry }
	::= { bgs10CesConfigTable 1 }

BGS10CesConfigEntry ::=
	SEQUENCE { 
		bgs10CesHCpType					UChar,
		bgs10CesCrossConnectIdentifier	UShort,
		bgs10CesCatchRM					BITS,		
		bgs10CesAllowEFC				BITS,
		bgs10CesEPDFlag					BITS,
		bgs10CesFeeGleanFlag			BITS,
		bgs10CesSvcOrPvcFlag			BITS,
		bgs10CesPifIndex				UShort,
		bgs10CesPVPI					UShort,
		bgs10CesPVCType					UShort,
		bgs10CesPSwitchType				UShort,
		bgs10CesatmfCESPOperStatus		UShort,
		bgs10CesManualControl			UShort,
		bgs10CesOperatingMode			UShort,
		bgs10CesPCPType					UShort,
		bgs10CesPVCI					UShort,
		bgs10CesPAtmAddress				AtmAddr,
		bgs10CesGroupid					UShort,
		bgs10CesAlarmStatus				UShort,
		bgs10CesPolicing				UCHAR,
		bgs10CesS20No					UShort
	}
	
bgs10CesHCpType	OBJECT-TYPE
	SYNTAX		UChar
	MAX-ACCESS	read-create
	STATUS		current
	DESCRIPTION
		"The high CP type of CES."
	::= {  bgs10CesConfigEntry 1 }
	
bgs10CesCrossConnectIdentifier	OBJECT-TYPE
	SYNTAX		UShort
	MAX-ACCESS	read-create
	STATUS		current
	DESCRIPTION
		"the cross connection identifier."
	::= {	bgs10CesConfigEntry 2 }

bgs10CesCatchRM	OBJECT-TYPE
	SYNTAX		BITS {  not-catch(0),
						catch(1)
					 }
	MAX-ACCESS	read-create
	STATUS		current
	DESCRIPTION
		"."
	::= { bgs10CesConfigEntry 3}

bgs10CesAllowEFC	OBJECT-TYPE
	SYNTAX		BITS {  not-allow(0),
						allow(1)
					 }
	MAX-ACCESS	read-create
	STATUS		current
	DESCRIPTION
		"."
	::= { bgs10CesConfigEntry 4}

bgs10CesEPDFlag	OBJECT-TYPE
	SYNTAX		BITS {  not-set(0),
						set(1)
					 }
	MAX-ACCESS	read-create
	STATUS		current
	DESCRIPTION
		"."
	::= { bgs10CesConfigEntry 5}
	
bgs10CesFeeGleanFlag	OBJECT-TYPE
	SYNTAX		BITS {  not-glean(0),
						glean(1)
					 }
	MAX-ACCESS	read-create
	STATUS		current
	DESCRIPTION
		"."
	::= { bgs10CesConfigEntry 6}
	
bgs10CesSvcOrPvcFlag	OBJECT-TYPE
	SYNTAX		BITS {  pvc(0),
						svc(1)
					 }
	MAX-ACCESS	read-create
	STATUS		current
	DESCRIPTION
		"."
	::= { bgs10CesConfigEntry 7}

bgs10CesPifIndex	OBJECT-TYPE
	SYNTAX		UShort
	MAX-ACCESS	read-create
	STATUS		current
	DESCRIPTION
		"."
	::= { bgs10CesConfigEntry 8}

bgs10CesPVPI	OBJECT-TYPE
	SYNTAX		UShort
	MAX-ACCESS	read-create
	STATUS		current
	DESCRIPTION
		"."
	::= { bgs10CesConfigEntry 9}

bgs10CesPVCType	OBJECT-TYPE
	SYNTAX		UShort
	MAX-ACCESS	read-create
	STATUS		current
	DESCRIPTION
		"."
	::= { bgs10CesConfigEntry 10}

bgs10CesPSwitchType	OBJECT-TYPE
	SYNTAX		UShort
	MAX-ACCESS	read-create
	STATUS		current
	DESCRIPTION
		"."
	::= { bgs10CesConfigEntry 11}

bgs10CesatmfCESPOperStatus	OBJECT-TYPE
	SYNTAX		UShort
	MAX-ACCESS	read-create
	STATUS		current
	DESCRIPTION
		"."
	::= { bgs10CesConfigEntry 12}

bgs10CesManualControl	OBJECT-TYPE
	SYNTAX		UShort
	MAX-ACCESS	read-create
	STATUS		current
	DESCRIPTION
		"."
	::= { bgs10CesConfigEntry 13}

bgs10CesOperatingMode	OBJECT-TYPE
	SYNTAX		UShort
	MAX-ACCESS	read-create
	STATUS		current
	DESCRIPTION
		"."
	::= { bgs10CesConfigEntry 14}

bgs10CesPCPType	OBJECT-TYPE
	SYNTAX		UShort
	MAX-ACCESS	read-create
	STATUS		current
	DESCRIPTION
		"."
	::= { bgs10CesConfigEntry 15}

bgs10CesPVCI	OBJECT-TYPE
	SYNTAX		UShort
	MAX-ACCESS	read-create
	STATUS		current
	DESCRIPTION
		"."
	::= { bgs10CesConfigEntry 16}

bgs10CesPAtmAddress	OBJECT-TYPE
	SYNTAX		AtmAddr
	MAX-ACCESS	read-create
	STATUS		current
	DESCRIPTION
		"."
	::= { bgs10CesConfigEntry 17}

bgs10CesGroupid	OBJECT-TYPE
	SYNTAX		UShort
	MAX-ACCESS	read-create
	STATUS		current
	DESCRIPTION
		"."
	::= { bgs10CesConfigEntry 18}

bgs10CesAlarmStatus	OBJECT-TYPE
	SYNTAX		UShort
	MAX-ACCESS	read-create
	STATUS		current
	DESCRIPTION
		"."
	::= { bgs10CesConfigEntry 19}

bgs10CesPolicing	OBJECT-TYPE
	SYNTAX		UCHAR
	MAX-ACCESS	read-create
	STATUS		current
	DESCRIPTION
		"."
	::= { bgs10CesConfigEntry 20}

bgs10CesS20No	OBJECT-TYPE
	SYNTAX		UShort
	MAX-ACCESS	read-create
	STATUS		current
	DESCRIPTION
		"."
	::= { bgs10CesConfigEntry 21}

--The E1 Table
bgs10E1MIB		OBJECT IDENTIFIER ::= { zxbgs10mib 29 }

--The E1 link table
bgs10E1LinkTable	OBJECT-TYPE
	SYNTAX		SEQUENCE OF BGS10E1LinkEntry
	MAX-ACCESS	not-accessible
	STATUS		current
	DESCRIPTION
		"the table for E1 link ."
	::= { bgs10E1MIB 1}
	
bgs10E1LinkEntry	OBJECT-TYPE
	SYNTAX		BGS10E1LinkEntry
	MAX-ACCESS	not-accessible
	STATUS		current
	DESCRIPTION
		"THE ENTRY TO THE E1 link table."
	INDEX { bgs10TotalPort}
	::= { bgs10E1LinkTable 1 }
	
BGS10E1LinkEntry	::=
	SEQUENCE {	
		bgs10E1LinkRowStatus		RowStatus,
		bgs10E1LinkAdminStatus		INTEGER,
		bgs10E1LinkOperStatus		INTEGER,
		bgs10E1LinkLineType			INTEGER,
		bgs10E1LinkLineCoding		INTEGER,
		bgs10E1LinkTxClockSource	INTEGER,
		bgs10E1LinkRxScrambling		INTEGER,
		bgs10E1LinkTxScrambling		INTEGER,
		bgs10E1LinkTimeInterval		INTEGER,
		bgs10E1LinkActionType		INTEGER
	}
	
bgs10E1LinkRowStatus	OBJECT-TYPE
	SYNTAX		RowStatus
	MAX-ACCESS	read-create
	STATUS		current
	DESCRIPTION
		"the row status of the E1 link table."
	::= { bgs10E1LinkEntry 1 }
	
bgs10E1LinkAdminStatus	OBJECT-TYPE
	SYNTAX		INTEGER
	MAX-ACCESS	read-create
	STATUS		current
	DESCRIPTION
		"the Adminstrator's status."
	::= { bgs10E1LinkEntry 2 }
	
bgs10E1LinkOperStatus	OBJECT-TYPE
	SYNTAX		INTEGER
	MAX-ACCESS	read-create
	STATUS		current
	DESCRIPTION
		"the operator's status."
	::= { bgs10E1LinkEntry 3 } 
	
bgs10E1LinkLineType		OBJECT-TYPE
	SYNTAX		INTEGER
	MAX-ACCESS	read-create
	STATUS		current
	DESCRIPTION
		"the line's type."
	::= { bgs10E1LinkEntry 4 }
	
bgs10E1LinkLineCoding	OBJECT-TYPE
	SYNTAX		INTEGER
	MAX-ACCESS	read-create
	STATUS		current
	DESCRIPTION
		"the line's codeing form."
	::= { bgs10E1LinkEntry 5 }
	
bgs10E1LinkTxClockSource	OBJECT-TYPE
	SYNTAX		INTEGER
	MAX-ACCESS	read-create
	STATUS		current
	DESCRIPTION
		"the transmitting clock source."
	::= { bgs10E1LinkEntry 6 }
	
bgs10E1LinkRxScrambling		OBJECT-TYPE
	SYNTAX		INTEGER
	MAX-ACCESS	read-create
	STATUS		current
	DESCRIPTION
		"the recieving scrambling."
	::= { bgs10E1LinkEntry 7 }
	
bgs10E1LinkTxScrambling		OBJECT-TYPE
	SYNTAX		INTEGER
	MAX-ACCESS	read-create
	STATUS		current
	DESCRIPTION
		"the transmitting scrambling."
	::= { bgs10E1LinkEntry 8 }
	
bgs10E1LinkTimeInterval		OBJECT-TYPE
	SYNTAX		INTEGER
	MAX-ACCESS	read-create
	STATUS		current
	DESCRIPTION
		"the time interval."
	::= { bgs10E1LinkEntry 9 }
	
bgs10E1LinkActionType		OBJECT-TYPE
	SYNTAX		INTEGER
	MAX-ACCESS	read-create
	STATUS		current
	DESCRIPTION
		"the type of action."
	::= { bgs10E1LinkEntry 10 }
	
--The E1 statistics table
bgs10E1StatTable	OBJECT-TYPE
	SYNTAX		SEQUENCE OF BGS10E1StatEntry
	MAX-ACCESS	not-accessible
	STATUS		current
	DESCRIPTION
		"the table for E1 link ."
	::= { bgs10E1MIB 2}
	
bgs10E1StatEntry	OBJECT-TYPE
	SYNTAX		BGS10E1StatEntry
	MAX-ACCESS	not-accessible
	STATUS		current
	DESCRIPTION
		"THE ENTRY TO THE E1 statistics table."
	INDEX {	bgs10TotalPort}
	::= { bgs10E1StatTable 1 }
	
BGS10E1StatEntry	::=
	SEQUENCE {	
		bgs10E1StatRowStatus	RowStatus,
		bgs10E1StatLCVs			Unsigned32,
		bgs10E1StatFERRs		Unsigned32,
		bgs10E1StatFEBEs		Unsigned32,
		bgs10E1StatCRCs			Unsigned32,
		bgs10E1StatOOFs			Unsigned32,
		bgs10E1StatLOSs			Unsigned32,
		bgs10E1StatAISs			Unsigned32,
		bgs10E1StatAISDs		Unsigned32,
		bgs10E1StatYellowAlarms	Unsigned32,
		bgs10E1StatHCSs			Unsigned32,
		bgs10E1StatRxCells		Unsigned32,
		bgs10E1StatTxCells		Unsigned32,
		bgs10E1StatUHCSs		Unsigned32,
		bgs10E1StatCHCSs		Unsigned32,
		bgs10E1StatLCDs			Unsigned32
	}
	
bgs10E1StatRowStatus	OBJECT-TYPE
	SYNTAX		RowStatus
	MAX-ACCESS	read-create
	STATUS		current
	DESCRIPTION
		"the row status of the E1 statiustics table."
	::= { bgs10E1StatEntry 1 }
	
bgs10E1StatLCVs			OBJECT-TYPE
	SYNTAX		Unsigned32
	MAX-ACCESS	read-create
	STATUS		current
	DESCRIPTION
		"."
	::= { bgs10E1StatEntry 2 }
	
bgs10E1StatFERRs		OBJECT-TYPE
	SYNTAX		Unsigned32
	MAX-ACCESS	read-create
	STATUS		current
	DESCRIPTION
		"."
	::= { bgs10E1StatEntry 3 }
	
bgs10E1StatFEBEs		OBJECT-TYPE
	SYNTAX		Unsigned32
	MAX-ACCESS	read-create
	STATUS		current
	DESCRIPTION
		"."
	::= { bgs10E1StatEntry 4 }
	
bgs10E1StatCRCs			OBJECT-TYPE
	SYNTAX		Unsigned32
	MAX-ACCESS	read-create
	STATUS		current
	DESCRIPTION
		"."
	::= { bgs10E1StatEntry 5 }
	
bgs10E1StatOOFs			OBJECT-TYPE
	SYNTAX		Unsigned32
	MAX-ACCESS	read-create
	STATUS		current
	DESCRIPTION
		"."
	::= { bgs10E1StatEntry 6 }
	
bgs10E1StatLOSs			OBJECT-TYPE
	SYNTAX		Unsigned32
	MAX-ACCESS	read-create
	STATUS		current
	DESCRIPTION
		"."
	::= { bgs10E1StatEntry 7 }
	
bgs10E1StatAISs			OBJECT-TYPE
	SYNTAX		Unsigned32
	MAX-ACCESS	read-create
	STATUS		current
	DESCRIPTION
		"."
	::= { bgs10E1StatEntry 8 }
	
bgs10E1StatAISDs		OBJECT-TYPE
	SYNTAX		Unsigned32
	MAX-ACCESS	read-create
	STATUS		current
	DESCRIPTION
		"."
	::= { bgs10E1StatEntry 9 }
	
bgs10E1StatYellowAlarms	OBJECT-TYPE
	SYNTAX		Unsigned32
	MAX-ACCESS	read-create
	STATUS		current
	DESCRIPTION
		"."
	::= { bgs10E1StatEntry 10 }
	
bgs10E1StatHCSs			OBJECT-TYPE
	SYNTAX		Unsigned32
	MAX-ACCESS	read-create
	STATUS		current
	DESCRIPTION
		"."
	::= { bgs10E1StatEntry 11 }
	
bgs10E1StatRxCells		OBJECT-TYPE
	SYNTAX		Unsigned32
	MAX-ACCESS	read-create
	STATUS		current
	DESCRIPTION
		"."
	::= { bgs10E1StatEntry 12 }
	
bgs10E1StatTxCells		OBJECT-TYPE
	SYNTAX		Unsigned32
	MAX-ACCESS	read-create
	STATUS		current
	DESCRIPTION
		"."
	::= { bgs10E1StatEntry 13 }
	
bgs10E1StatUHCSs		OBJECT-TYPE
	SYNTAX		Unsigned32
	MAX-ACCESS	read-create
	STATUS		current
	DESCRIPTION
		"."
	::= { bgs10E1StatEntry 14 }
	
bgs10E1StatCHCSs		OBJECT-TYPE
	SYNTAX		Unsigned32
	MAX-ACCESS	read-create
	STATUS		current
	DESCRIPTION
		"."
	::= { bgs10E1StatEntry 15 }
	
bgs10E1StatLCDs			OBJECT-TYPE
	SYNTAX		Unsigned32
	MAX-ACCESS	read-create
	STATUS		current
	DESCRIPTION
		"."
	::= { bgs10E1StatEntry 16 }
	
--The M4 Plug-in Unit  	
bgs10Unit		OBJECT IDENTIFIER ::= { zxbgs10mib 30 }

bgs10PowerVoltage	OBJECT-TYPE
	SYNTAX		INTEGER
	MAX-ACCESS	read-write
	STATUS		current
	DESCRIPTION	
		"the voltage of the power."
	::= { bgs10Unit 1 }

--The Performance management MIB
bgs10PmMib		OBJECT IDENTIFIER	::= { zxbgs10mib 31}

--the switcher table for perfermance management
bgs10PmLoopBackTable	OBJECT-TYPE
	SYNTAX		SEQUENCE OF BGS10PmLoopBackEntry
	MAX-ACCESS	not-accessible
	STATUS		current
	DESCRIPTION
		"the table for loop-back action of the perfermance management."
	::= { bgs10PmMib 1}
	
bgs10PmLoopBackEntry	OBJECT-TYPE
	SYNTAX		BGS10PmLoopBackEntry
	MAX-ACCESS	not-accessible
	STATUS		current
	DESCRIPTION
		"THE ENTRY TO THE PM loop-back test."
	INDEX {	bgs10PmLoopBackModule,
			bgs10PmLoopBackPerfPort,
			bgs10PmLoopBackVPI,
			bgs10PmLoopBackVCI
			}
	::= { bgs10PmLoopBackTable 1 }
	
BGS10PmLoopBackEntry	::=
	SEQUENCE {	
		bgs10PmLoopBackRowStatus		RowStatus,
		bgs10PmLoopBackTestType			UChar,
		bgs10PmLoopBackModule			UChar,
		bgs10PmLoopBackPerfPort			UShort,
		bgs10PmLoopBackTestIndex		UShort,
		bgs10PmLoopBackVPI				UShort,
		bgs10PmLoopBackVCI				UShort,
		bgs10PmLoopBackTestNumber		UShort,
		bgs10PmLoopBackID				OCTET STRING,
		bgs10PmLoopBackLoopBackActionFlag
										INTEGER,
		bgs10PmLoopBackPMActionFlag		INTEGER,
		bgs10PmLoopBackTestResult		UCHAR
	}
	
bgs10PmLoopBackRowStatus	OBJECT-TYPE
	SYNTAX		RowStatus
	MAX-ACCESS	read-create
	STATUS		current
	DESCRIPTION
		"the row status of the switcher table."
	::= { bgs10PmLoopBackEntry 1 }
	
bgs10PmLoopBackTestType		OBJECT-TYPE
	SYNTAX		UChar
	MAX-ACCESS	read-create
	STATUS		current
	DESCRIPTION
		"the test type includes :F4 end-to-end/segment-to-segment,F5 end-to-end/
	segment-to-segment."
	::= { bgs10PmLoopBackEntry 2 }
	
bgs10PmLoopBackModule	OBJECT-TYPE
	SYNTAX		UChar
	MAX-ACCESS	read-create
	STATUS		current
	DESCRIPTION
		"the tested Mpdule."
	::= { bgs10PmLoopBackEntry 3 }
	
bgs10PmLoopBackPerfPort	OBJECT-TYPE
	SYNTAX		UShort
	MAX-ACCESS	read-create
	STATUS		current
	DESCRIPTION
		"the tested port."
	::= { bgs10PmLoopBackEntry 4 }
	
bgs10PmLoopBackTestIndex	OBJECT-TYPE
	SYNTAX		UShort
	MAX-ACCESS	read-create
	STATUS		current
	DESCRIPTION
		"the test index."
	::= { bgs10PmLoopBackEntry 5 }
	
bgs10PmLoopBackVPI		OBJECT-TYPE
	SYNTAX		UShort
	MAX-ACCESS	read-create
	STATUS		current
	DESCRIPTION
		"the test VPI."
	::= { bgs10PmLoopBackEntry 6 }

bgs10PmLoopBackVCI		OBJECT-TYPE
	SYNTAX		UShort
	MAX-ACCESS	read-create
	STATUS		current
	DESCRIPTION
		"the test VCI."
	::= { bgs10PmLoopBackEntry 7 }
	
bgs10PmLoopBackTestNumber OBJECT-TYPE
	SYNTAX		UShort
	MAX-ACCESS	read-create
	STATUS		current
	DESCRIPTION
		"the numbers of the loopback test."
	::= { bgs10PmLoopBackEntry 8 }
	
bgs10PmLoopBackID 	OBJECT-TYPE
	SYNTAX		OCTET STRING(SIZE(13))
	MAX-ACCESS	read-create
	STATUS		current
	DESCRIPTION
		"the loop back ID."
	::= { bgs10PmLoopBackEntry 9 }
	
bgs10PmLoopBackLoopBackActionFlag	OBJECT-TYPE
	SYNTAX		INTEGER { down(0),
						up(1),
						close(2)
						}
	MAX-ACCESS	read-create
	STATUS		current
	DESCRIPTION
		"the loop-bakc action flag."
	::= { bgs10PmLoopBackEntry 10 }
	
bgs10PmLoopBackPMActionFlag		OBJECT-TYPE
	SYNTAX		INTEGER { down(0),
						up(1),
						close(2)
						}
	MAX-ACCESS	read-create
	STATUS		current
	DESCRIPTION
	 	" the perfermance management action flag."
	 ::= { bgs10PmLoopBackEntry 11 }
	 
bgs10PmLoopBackTestResult		OBJECT-TYPE
	SYNTAX		UCHAR	
	MAX-ACCESS	read-create
	STATUS		current
	DESCRIPTION
	 	" the OAM Test result."
	 ::= { bgs10PmLoopBackEntry 12 }
	 
--The Plug-in unit table
bgs10PlugInUnit		OBJECT IDENTIFIER	::= { zxbgs10mib 32}
	
bgs10PlugInUnitTable	OBJECT-TYPE
	SYNTAX		SEQUENCE OF BGS10PlugInUnitEntry
	MAX-ACCESS	not-accessible
	STATUS		current
	DESCRIPTION
		"the plug-in unittable."
	::= { bgs10PlugInUnit 1 }
	
bgs10PlugInUnitEntry	OBJECT-TYPE
	SYNTAX		BGS10PlugInUnitEntry
	MAX-ACCESS	not-accessible
	STATUS		current
	DESCRIPTION
		"the entry to the plug-in unit table."
	AUGMENTS { atmfM4PlugInUnitEntry }
	::= { bgs10PlugInUnitTable 1 }
	
BGS10PlugInUnitEntry	::=
	SEQUENCE {
		bgs10PlugInUnitRowStatus		RowStatus,
		bgs10PlugInUnitMasterStatus		INTEGER,
		bgs10PlugInUnitEntPhysicalContainedIn
										INTEGER,
		bgs10PlugInUnitParent			INTEGER,
		bgs10PlugInUnitCardType			INTEGER,
		bgs10PlugInUnitModule			INTEGER,
		bgs10PlugInUnitCardPosition		INTEGER,
		bgs10PlugInUnitPhysicalClass	INTEGER
	}
	
bgs10PlugInUnitRowStatus	OBJECT-TYPE
	SYNTAX		RowStatus
	MAX-ACCESS	read-create
	STATUS		current
	DESCRIPTION
		"the conceptual row status."
	::= { bgs10PlugInUnitEntry 1 }
	
bgs10PlugInUnitMasterStatus	OBJECT-TYPE
	SYNTAX		INTEGER { master(1),
							slave(2)
						}
	MAX-ACCESS	read-create
	STATUS		current
	DESCRIPTION
		"the Unit work status."
	::= { bgs10PlugInUnitEntry 2 }
	
bgs10PlugInUnitEntPhysicalContainedIn	OBJECT-TYPE
	SYNTAX		INTEGER
	MAX-ACCESS	read-create
	STATUS		current
	DESCRIPTION
		"the physical contained position."
	::= { bgs10PlugInUnitEntry 3 }
	
bgs10PlugInUnitParent	OBJECT-TYPE
	SYNTAX		INTEGER
	MAX-ACCESS	read-create
	STATUS		current
	DESCRIPTION
		"the neighbor service card type."
	::= { bgs10PlugInUnitEntry 4 }
	
bgs10PlugInUnitCardType		OBJECT-TYPE
	SYNTAX		INTEGER
	MAX-ACCESS	read-create
	STATUS		current
	DESCRIPTION
		"the card type."
	::= { bgs10PlugInUnitEntry 5 }
		
bgs10PlugInUnitModule	OBJECT-TYPE
	SYNTAX		INTEGER
	MAX-ACCESS	read-create
	STATUS		current
	DESCRIPTION
		"the Module Number."
	::= { bgs10PlugInUnitEntry 6 }
	
bgs10PlugInUnitCardPosition	OBJECT-TYPE
	SYNTAX		INTEGER
	MAX-ACCESS	read-create
	STATUS		current
	DESCRIPTION
		" the card position."
	::= { bgs10PlugInUnitEntry 7}

bgs10PlugInUnitPhysicalClass	OBJECT-TYPE
	SYNTAX		INTEGER
	MAX-ACCESS	read-create
	STATUS		current
	DESCRIPTION
		" the card phyical class."
	::= { bgs10PlugInUnitEntry 8}
	
-- The global variables for network

bgs10NetConfig		OBJECT IDENTIFIER 	::= { zxbgs10mib 33 }
	
bgs10NetConfEthIpAddress	OBJECT-TYPE
	SYNTAX		IpAddress
	MAX-ACCESS	read-create
	STATUS		current
	DESCRIPTION
		" the IP Address of Ethnet."
	::= { bgs10NetConfig 1 }
	
bgs10NetConfEthIpMask	OBJECT-TYPE
	SYNTAX		IpAddress
	MAX-ACCESS	read-create
	STATUS		current
	DESCRIPTION
		" the sub-net mask code of Ethnet IP Address."
	::= { bgs10NetConfig 2 }
		
bgs10NetConfPvcIpAddress	OBJECT-TYPE
	SYNTAX		IpAddress
	MAX-ACCESS	read-create
	STATUS		current
	DESCRIPTION
		" the IP Address of PVC."
	::= { bgs10NetConfig 3 }
	
bgs10NetConfPvcIpMask	OBJECT-TYPE
	SYNTAX		IpAddress
	MAX-ACCESS	read-create
	STATUS		current
	DESCRIPTION
		" the sub-net maks  code of PVC IP Address."
	::= { bgs10NetConfig 4 }
	
bgs10NetConfNmsGatewayIp	OBJECT-TYPE
	SYNTAX		IpAddress
	MAX-ACCESS	read-create
	STATUS		current
	DESCRIPTION
		" the IP Address of the gateway of NMS(Network Management Server) ."
	::= { bgs10NetConfig 5 }
	
bgs10NetConfNmsDstNetid	OBJECT-TYPE
	SYNTAX		Unsigned32
	MAX-ACCESS	read-create
	STATUS		current
	DESCRIPTION
		" the Net ID of NMs's destation net element."
	::= { bgs10NetConfig 6 }
	
	
--The TC adapter supplyment
bgs10TcProtoCurTable	OBJECT-TYPE
	SYNTAX		SEQUENCE OF ZXB10TCProtocolEntry
	MAX-ACCESS	not-accessible
	STATUS		current
	DESCRIPTION
		"the plug-in unittable."
	::= { zxbgs10mib 34 }
	
bgs10TcProtoCurEntry	OBJECT-TYPE
	SYNTAX		ZXB10TCProtocolEntry
	MAX-ACCESS	not-accessible
	STATUS		current
	DESCRIPTION
		"the entry to the TC protocol table."
	AUGMENTS { atmfM4TcProtoCurrEntry }
	::= { bgs10TcProtoCurTable 1 }
	
ZXB10TCProtocolEntry	::=
	SEQUENCE {
		zxb10TcProCurPerfModule		UCHAR,
		zxb10TcProCurPerfPort		UCHAR,
		zxb10TcProCurSectionbip8	Gauge32,
		zxb10TcProCurLinebip8		Gauge32,
		zxb10TcProCurLinefebe		Gauge32, 
		zxb10TcProCurPathbip24		Gauge32,
		zxb10TcProCurPathfebe		Gauge32,
		zxb10TcProCurCorrecthcs		Gauge32,
		zxb10TcProCurRxCell			Gauge32,
		zxb10TcProCurTxCell			Gauge32
	}

zxb10TcProCurPerfModule		OBJECT-TYPE
	SYNTAX		UCHAR
	MAX-ACCESS	read-only
	STATUS		current
	DESCRIPTION
		"."
	::= { bgs10TcProtoCurEntry 1 }
	
zxb10TcProCurPerfPort		OBJECT-TYPE
	SYNTAX		UCHAR
	MAX-ACCESS	read-only
	STATUS		current
	DESCRIPTION
		"."
	::= { bgs10TcProtoCurEntry 2 }
		
zxb10TcProCurSectionbip8	OBJECT-TYPE
	SYNTAX		Gauge32
	MAX-ACCESS	read-only
	STATUS		current
	DESCRIPTION
		"."
	::= { bgs10TcProtoCurEntry 3 }
	
zxb10TcProCurLinebip8		OBJECT-TYPE
	SYNTAX		Gauge32
	MAX-ACCESS	read-only
	STATUS		current
	DESCRIPTION
		"."
	::= { bgs10TcProtoCurEntry 4 }
	
	
zxb10TcProCurLinefebe		OBJECT-TYPE
	SYNTAX		Gauge32
	MAX-ACCESS	read-only
	STATUS		current
	DESCRIPTION
		"."
	::= { bgs10TcProtoCurEntry 5 }
	
zxb10TcProCurPathbip24		OBJECT-TYPE
	SYNTAX		Gauge32
	MAX-ACCESS	read-only
	STATUS		current
	DESCRIPTION
		"."
	::= { bgs10TcProtoCurEntry 6 }
	
zxb10TcProCurPathfebe		OBJECT-TYPE
	SYNTAX		Gauge32
	MAX-ACCESS	read-only
	STATUS		current
	DESCRIPTION
		"."
	::= { bgs10TcProtoCurEntry 7 }
	
zxb10TcProCurCorrecthcs		OBJECT-TYPE
	SYNTAX		Gauge32
	MAX-ACCESS	read-only
	STATUS		current
	DESCRIPTION
		"."
	::= { bgs10TcProtoCurEntry 8 }
	
zxb10TcProCurRxCell			OBJECT-TYPE
	SYNTAX		Gauge32
	MAX-ACCESS	read-only
	STATUS		current
	DESCRIPTION
		"."
	::= { bgs10TcProtoCurEntry 9 }
	
zxb10TcProCurTxCell			OBJECT-TYPE
	SYNTAX		Gauge32
	MAX-ACCESS	read-only
	STATUS		current
	DESCRIPTION
		"."
	::= { bgs10TcProtoCurEntry 10 }
	
--The supplement to VP UPC/NPC		
bgs10VpUpcNpcCurrTable 	OBJECT-TYPE
	SYNTAX		SEQUENCE OF ZXB10VpUpcNpcEntry
	MAX-ACCESS	not-accessible
	STATUS		current
	DESCRIPTION
		"the plug-in unittable."
	::= { zxbgs10mib 35 }
	
bgs10VpUpcNpcCurEntry	OBJECT-TYPE
	SYNTAX		ZXB10VpUpcNpcEntry
	MAX-ACCESS	not-accessible
	STATUS		current
	DESCRIPTION
		"the entry to the TC protocol table."
	AUGMENTS { atmfM4VpUpcNpcCurrEntry }
	::= { bgs10VpUpcNpcCurrTable 1 }
	
ZXB10VpUpcNpcEntry	::=
	SEQUENCE {
		zxb10VpUpcNpcCurPassTagedCell		Gauge32,
		zxb10VpUpcNpcCurIfIndex				UShort,
		zxb10VpUpcNpcCurVpi					UShort
	}

zxb10VpUpcNpcCurPassTagedCell		OBJECT-TYPE
	SYNTAX		Gauge32
	MAX-ACCESS	read-only
	STATUS		current
	DESCRIPTION
		"."
	::= { bgs10VpUpcNpcCurEntry 1 }
	
zxb10VpUpcNpcCurIfIndex	OBJECT-TYPE
	SYNTAX		UShort
	MAX-ACCESS	read-only
	STATUS		current
	DESCRIPTION
		"Interface Interface."
	::= { bgs10VpUpcNpcCurEntry 2 }
	
zxb10VpUpcNpcCurVpi	OBJECT-TYPE
	SYNTAX		UShort
	MAX-ACCESS	read-only
	STATUS		current
	DESCRIPTION
		"Current VPI."
	::= { bgs10VpUpcNpcCurEntry 3 }


--The congest table.
bgs10CongestTable		OBJECT IDENTIFIER	::= { zxbgs10mib 36 }

bgs10CongRowStatus	OBJECT-TYPE
	SYNTAX		UCHAR
	MAX-ACCESS	read-only
	STATUS		current
	DESCRIPTION
		"."
	::= { bgs10CongestTable 1 }
	
bgs10Congperfmodule	OBJECT-TYPE
	SYNTAX		UCHAR
	MAX-ACCESS	read-only
	STATUS		current
	DESCRIPTION
		"."
	::= { bgs10CongestTable 2 }
	
bgs10Congperftype	OBJECT-TYPE
	SYNTAX		UCHAR
	MAX-ACCESS	read-only
	STATUS		current
	DESCRIPTION
		"."
	::= { bgs10CongestTable 3 }   
	
bgs10Congincellqueue	OBJECT-TYPE
	SYNTAX		Unsigned32
	MAX-ACCESS	read-only
	STATUS		current
	DESCRIPTION
		"."
	::= { bgs10CongestTable 4 }
	
bgs10Congoutcellqueue	OBJECT-TYPE
	SYNTAX		Unsigned32
	MAX-ACCESS	read-only
	STATUS		current
	DESCRIPTION
		"."
	::= { bgs10CongestTable 5 }
	
bgs10Congtime	OBJECT-TYPE
	SYNTAX		Unsigned32
	MAX-ACCESS	read-only
	STATUS		current
	DESCRIPTION
		"."
	::= { bgs10CongestTable 6 }
	
bgs10Congperfspace	OBJECT-TYPE
	SYNTAX		Unsigned32
	MAX-ACCESS	read-only
	STATUS		current
	DESCRIPTION
		"."
	::= { bgs10CongestTable 7 }
	
--The supplement to VC UPC/NPC		
bgs10VcUpcNpcCurrTable 	OBJECT-TYPE
	SYNTAX		SEQUENCE OF ZXB10VcUpcNpcEntry
	MAX-ACCESS	not-accessible
	STATUS		current
	DESCRIPTION
		"the plug-in unittable."
	::= { zxbgs10mib 37 }
	
bgs10VcUpcNpcCurEntry	OBJECT-TYPE
	SYNTAX		ZXB10VcUpcNpcEntry
	MAX-ACCESS	not-accessible
	STATUS		current
	DESCRIPTION
		"the entry to the TC protocol table."
	AUGMENTS { atmfM4VcUpcNpcCurrEntry }
	::= { bgs10VcUpcNpcCurrTable 1 }
	
ZXB10VcUpcNpcEntry	::=
	SEQUENCE {
		zxb10VcUpcNpcCurPassTagedCell		Gauge32,
		zxb10VcUpcNpcCurIfIndex				UShort,
		zxb10VcUpcNpcCurVpi					UShort,
		zxb10VcUpcNpcCurVci					UShort
	}

zxb10VcUpcNpcCurPassTagedCell		OBJECT-TYPE
	SYNTAX		Gauge32
	MAX-ACCESS	read-only
	STATUS		current
	DESCRIPTION
		"current passed taged cells."
	::= { bgs10VcUpcNpcCurEntry 1 }
	
zxb10VcUpcNpcCurIfIndex	OBJECT-TYPE
	SYNTAX		UShort
	MAX-ACCESS	read-only
	STATUS		current
	DESCRIPTION
		"Interface Interface."
	::= { bgs10VcUpcNpcCurEntry 2 }
	
zxb10VcUpcNpcCurVpi	OBJECT-TYPE
	SYNTAX		UShort
	MAX-ACCESS	read-only
	STATUS		current
	DESCRIPTION
		"Current VPI."
	::= { bgs10VcUpcNpcCurEntry 3 }

zxb10VcUpcNpcCurVci	OBJECT-TYPE
	SYNTAX		UShort
	MAX-ACCESS	read-only
	STATUS		current
	DESCRIPTION
		"Current VCI."
	::= { bgs10VcUpcNpcCurEntry 4 }


--The Software Special Alarm Table
bgs10SoftSpecialAlarmTable		OBJECT IDENTIFIER	::= { zxbgs10mib 38 }

zxb10SoftSpecialAlarmParam1	OBJECT-TYPE
	SYNTAX		UCHAR
	MAX-ACCESS	read-only
	STATUS		current
	DESCRIPTION
		"Software Alarm Parameter 1"
	::= { bgs10SoftSpecialAlarmTable 1 }
	
zxb10SoftSpecialAlarmParam2	OBJECT-TYPE
	SYNTAX		UShort
	MAX-ACCESS	read-only
	STATUS		current
	DESCRIPTION
		"Software Alarm Parameter 2"
	::= { bgs10SoftSpecialAlarmTable 2 }
	
zxb10SoftSpecialAlarmParam3	OBJECT-TYPE
	SYNTAX		UShort
	MAX-ACCESS	read-only
	STATUS		current
	DESCRIPTION
		"Software Alarm Parameter 3"
	::= { bgs10SoftSpecialAlarmTable 3 }
	
zxb10SoftSpecialAlarmParam4	OBJECT-TYPE
	SYNTAX		UShort
	MAX-ACCESS	read-only
	STATUS		current
	DESCRIPTION
		"Software Alarm Parameter 4"
	::= { bgs10SoftSpecialAlarmTable 4 }

zxb10SoftSpecialAlarmParam5	OBJECT-TYPE
	SYNTAX		UChar
	MAX-ACCESS	read-only
	STATUS		current
	DESCRIPTION
		"Software Alarm Parameter 5"
	::= { bgs10SoftSpecialAlarmTable 5 }

zxb10SoftSpecialAlarmParam6	OBJECT-TYPE
	SYNTAX		UChar
	MAX-ACCESS	read-only
	STATUS		current
	DESCRIPTION
		"Software Alarm Parameter 6"
	::= { bgs10SoftSpecialAlarmTable 6 }
	
zxb10SoftSpecialAlarmParam7	OBJECT-TYPE
	SYNTAX		UChar
	MAX-ACCESS	read-only
	STATUS		current
	DESCRIPTION
		"Software Alarm Parameter 7"
	::= { bgs10SoftSpecialAlarmTable 7 }

zxb10SoftSpecialAlarmParam8	OBJECT-TYPE
	SYNTAX		AtmAddr
	MAX-ACCESS	read-only
	STATUS		current
	DESCRIPTION
		"Software Alarm Parameter 8"
	::= { bgs10SoftSpecialAlarmTable 8 }

--the X25 table 
bgs10X25				OBJECT IDENTIFIER	::= { zxbgs10mib 39}
        
--struct_x25_map_table
bgs10X25MapTable	OBJECT-TYPE
	SYNTAX		SEQUENCE OF ZXB10X25MapEntry
	MAX-ACCESS	not-accessible
	STATUS		current
	DESCRIPTION
		"A list of Definition of Address Mapping-Table entries."
	::= { bgs10X25 1}
	
bgs10X25MapEntry	OBJECT-TYPE
	SYNTAX		ZXB10X25MapEntry
	MAX-ACCESS	not-accessible
	STATUS		current
	DESCRIPTION
		"An entry in the table."
	INDEX {	
		bgs10X25MapUserAddr		
		}
	::= { bgs10X25MapTable 1}
	
ZXB10X25MapEntry ::=
	SEQUENCE {	
		bgs10X25MapRowStatus				RowStatus,
		bgs10X25MapUserAddr				X25Address,
		bgs10X25MapMapAddr1				X25Address,
		bgs10X25MapMapAddr2				X25Address,
		bgs10X25MapMapAddr3				X25Address,
		bgs10X25MapMapAddr4				X25Address,
		bgs10X25MapMapAddr5				X25Address,
		bgs10X25MapMapAddr6				X25Address
	}

bgs10X25MapRowStatus	OBJECT-TYPE
	SYNTAX		RowStatus
	MAX-ACCESS	read-create
	STATUS		current
	DESCRIPTION
		"."
	::= { bgs10X25MapEntry 1}

bgs10X25MapUserAddr	OBJECT-TYPE
	SYNTAX		X25Address
	MAX-ACCESS	read-create
	STATUS		current
	DESCRIPTION
		"."
	::= { bgs10X25MapEntry 2}

bgs10X25MapMapAddr1	OBJECT-TYPE
	SYNTAX		X25Address
	MAX-ACCESS	read-create
	STATUS		current
	DESCRIPTION
		"."
	::= { bgs10X25MapEntry 3}

bgs10X25MapMapAddr2	OBJECT-TYPE
	SYNTAX		X25Address
	MAX-ACCESS	read-create
	STATUS		current
	DESCRIPTION
		"."
	::= { bgs10X25MapEntry 4}

bgs10X25MapMapAddr3	OBJECT-TYPE
	SYNTAX		X25Address
	MAX-ACCESS	read-create
	STATUS		current
	DESCRIPTION
		"."
	::= { bgs10X25MapEntry 5}

bgs10X25MapMapAddr4	OBJECT-TYPE
	SYNTAX		X25Address
	MAX-ACCESS	read-create
	STATUS		current
	DESCRIPTION
		"."
	::= { bgs10X25MapEntry 6}

bgs10X25MapMapAddr5	OBJECT-TYPE
	SYNTAX		X25Address
	MAX-ACCESS	read-create
	STATUS		current
	DESCRIPTION
		"."
	::= { bgs10X25MapEntry 7}

bgs10X25MapMapAddr6	OBJECT-TYPE
	SYNTAX		X25Address
	MAX-ACCESS	read-create
	STATUS		current
	DESCRIPTION
		"."
	::= { bgs10X25MapEntry 8}

-- struct_x25_subcriber_table
bgs10X25SubcriberTable	OBJECT-TYPE
	SYNTAX		SEQUENCE OF ZXB10X25SubcriberEntry
	MAX-ACCESS	not-accessible
	STATUS		current
	DESCRIPTION
		"A list of Definition of Subcriber-Table entries."
	::= { bgs10X25 2}
	
bgs10X25SubcriberEntry	OBJECT-TYPE
	SYNTAX		ZXB10X25SubcriberEntry
	MAX-ACCESS	not-accessible
	STATUS		current
	DESCRIPTION
		"An entry in the table."
	INDEX {	
		bgs10X25SubcriberUserAddr		
		}
	::= { bgs10X25SubcriberTable 1}
	
ZXB10X25SubcriberEntry ::=
	SEQUENCE {	
		bgs10X25SubcriberRowStatus				RowStatus,
		bgs10X25SubcriberUserAddr				X25Address,
		bgs10X25SubcriberModule					UCHAR,
		bgs10X25SubcriberPort					UShort,
		bgs10X25SubcriberPriority				UCHAR,
		bgs10X25SubcriberThrpt					UShort,
		bgs10X25SubnetCall						UShort,
		bgs10X25Sproute							UCHAR,
		bgs10X25RouteModule1					UCHAR,
		bgs10X25RoutePort1						UShort,
		bgs10X25RouteModule2					UCHAR,
		bgs10X25RoutePort2						UShort,
		bgs10X25RouteModule3					UCHAR,
		bgs10X25RoutePort3						UShort,
		bgs10X25Calledctrl						UCHAR,
		bgs10X25Calling1						X25Address,
		bgs10X25Calling2						X25Address,
		bgs10X25Calling3						X25Address,
		bgs10X25Calling4						X25Address,
		bgs10X25Calling5						X25Address,
		bgs10X25Calling6						X25Address,
		bgs10X25Calling7						X25Address,
		bgs10X25Calling8						X25Address,
		bgs10X25Calling9						X25Address,
		bgs10X25Calling10						X25Address,
		bgs10X25Calling11						X25Address,
		bgs10X25Calling12						X25Address,
		bgs10X25Calling13						X25Address,
		bgs10X25Calling14						X25Address,
		bgs10X25Calling15						X25Address,
		bgs10X25Calling16						X25Address,
		bgs10X25Calling17						X25Address,
		bgs10X25Calling18						X25Address,
		bgs10X25Calling19						X25Address,
		bgs10X25Calling20						X25Address,
		bgs10X25Calling21						X25Address,
		bgs10X25Calling22						X25Address,
		bgs10X25Calling23						X25Address,
		bgs10X25Calling24						X25Address,
		bgs10X25Calling25						X25Address,
		bgs10X25Calling26						X25Address,
		bgs10X25Calling27						X25Address,
		bgs10X25Calling28						X25Address,
		bgs10X25Calling29						X25Address,
		bgs10X25Calling30						X25Address
	}

bgs10X25SubcriberRowStatus	OBJECT-TYPE
	SYNTAX		RowStatus
	MAX-ACCESS	read-create
	STATUS		current
	DESCRIPTION
		"."
	::= { bgs10X25SubcriberEntry 1}

bgs10X25SubcriberUserAddr	OBJECT-TYPE
	SYNTAX		X25Address
	MAX-ACCESS	read-create
	STATUS		current
	DESCRIPTION
		"."
	::= { bgs10X25SubcriberEntry 2}

bgs10X25SubcriberModule	OBJECT-TYPE
	SYNTAX		UCHAR
	MAX-ACCESS	read-create
	STATUS		current
	DESCRIPTION
		"."
	::= { bgs10X25SubcriberEntry 3}

bgs10X25SubcriberPort	OBJECT-TYPE
	SYNTAX		UShort
	MAX-ACCESS	read-create
	STATUS		current
	DESCRIPTION
		"."
	::= { bgs10X25SubcriberEntry 4}

bgs10X25SubcriberPriority	OBJECT-TYPE
	SYNTAX		UCHAR
	MAX-ACCESS	read-create
	STATUS		current
	DESCRIPTION
		"."
	::= { bgs10X25SubcriberEntry 5}

bgs10X25SubcriberThrpt	OBJECT-TYPE
	SYNTAX		UShort
	MAX-ACCESS	read-create
	STATUS		current
	DESCRIPTION
		"."
	::= { bgs10X25SubcriberEntry 6}

bgs10X25SubnetCall	OBJECT-TYPE
	SYNTAX		UShort
	MAX-ACCESS	read-create
	STATUS		current
	DESCRIPTION
		"."
	::= { bgs10X25SubcriberEntry 7}

bgs10X25Sproute	OBJECT-TYPE
	SYNTAX		UCHAR
	MAX-ACCESS	read-create
	STATUS		current
	DESCRIPTION
		"."
	::= { bgs10X25SubcriberEntry 8}

bgs10X25RouteModule1	OBJECT-TYPE
	SYNTAX		UCHAR
	MAX-ACCESS	read-create
	STATUS		current
	DESCRIPTION
		"."
	::= { bgs10X25SubcriberEntry 9}

bgs10X25RoutePort1	OBJECT-TYPE
	SYNTAX		UShort
	MAX-ACCESS	read-create
	STATUS		current
	DESCRIPTION
		"."
	::= { bgs10X25SubcriberEntry 10}

bgs10X25RouteModule2	OBJECT-TYPE
	SYNTAX		UCHAR
	MAX-ACCESS	read-create
	STATUS		current
	DESCRIPTION
		"."
	::= { bgs10X25SubcriberEntry 11}

bgs10X25RoutePort2	OBJECT-TYPE
	SYNTAX		UShort
	MAX-ACCESS	read-create
	STATUS		current
	DESCRIPTION
		"."
	::= { bgs10X25SubcriberEntry 12}

bgs10X25RouteModule3	OBJECT-TYPE
	SYNTAX		UCHAR
	MAX-ACCESS	read-create
	STATUS		current
	DESCRIPTION
		"."
	::= { bgs10X25SubcriberEntry 13}

bgs10X25RoutePort3	OBJECT-TYPE
	SYNTAX		UShort
	MAX-ACCESS	read-create
	STATUS		current
	DESCRIPTION
		"."
	::= { bgs10X25SubcriberEntry 14}

bgs10X25Calledctrl	OBJECT-TYPE
	SYNTAX		UCHAR
	MAX-ACCESS	read-create
	STATUS		current
	DESCRIPTION
		"."
	::= { bgs10X25SubcriberEntry 15}

bgs10X25Calling1	OBJECT-TYPE
	SYNTAX		X25Address
	MAX-ACCESS	read-create
	STATUS		current
	DESCRIPTION
		"."
	::= { bgs10X25SubcriberEntry 16}

bgs10X25Calling2	OBJECT-TYPE
	SYNTAX		X25Address
	MAX-ACCESS	read-create
	STATUS		current
	DESCRIPTION
		"."
	::= { bgs10X25SubcriberEntry 17}

bgs10X25Calling3	OBJECT-TYPE
	SYNTAX		X25Address
	MAX-ACCESS	read-create
	STATUS		current
	DESCRIPTION
		"."
	::= { bgs10X25SubcriberEntry 18}

bgs10X25Calling4	OBJECT-TYPE
	SYNTAX		X25Address
	MAX-ACCESS	read-create
	STATUS		current
	DESCRIPTION
		"."
	::= { bgs10X25SubcriberEntry 19}

bgs10X25Calling5	OBJECT-TYPE
	SYNTAX		X25Address
	MAX-ACCESS	read-create
	STATUS		current
	DESCRIPTION
		"."
	::= { bgs10X25SubcriberEntry 20}

bgs10X25Calling6	OBJECT-TYPE
	SYNTAX		X25Address
	MAX-ACCESS	read-create
	STATUS		current
	DESCRIPTION
		"."
	::= { bgs10X25SubcriberEntry 21}

bgs10X25Calling7	OBJECT-TYPE
	SYNTAX		X25Address
	MAX-ACCESS	read-create
	STATUS		current
	DESCRIPTION
		"."
	::= { bgs10X25SubcriberEntry 22}

bgs10X25Calling8	OBJECT-TYPE
	SYNTAX		X25Address
	MAX-ACCESS	read-create
	STATUS		current
	DESCRIPTION
		"."
	::= { bgs10X25SubcriberEntry 23}

bgs10X25Calling9	OBJECT-TYPE
	SYNTAX		X25Address
	MAX-ACCESS	read-create
	STATUS		current
	DESCRIPTION
		"."
	::= { bgs10X25SubcriberEntry 24}

bgs10X25Calling10	OBJECT-TYPE
	SYNTAX		X25Address
	MAX-ACCESS	read-create
	STATUS		current
	DESCRIPTION
		"."
	::= { bgs10X25SubcriberEntry 25}

bgs10X25Calling11	OBJECT-TYPE
	SYNTAX		X25Address
	MAX-ACCESS	read-create
	STATUS		current
	DESCRIPTION
		"."
	::= { bgs10X25SubcriberEntry 26}

bgs10X25Calling12	OBJECT-TYPE
	SYNTAX		X25Address
	MAX-ACCESS	read-create
	STATUS		current
	DESCRIPTION
		"."
	::= { bgs10X25SubcriberEntry 27}

bgs10X25Calling13	OBJECT-TYPE
	SYNTAX		X25Address
	MAX-ACCESS	read-create
	STATUS		current
	DESCRIPTION
		"."
	::= { bgs10X25SubcriberEntry 28}

bgs10X25Calling14	OBJECT-TYPE
	SYNTAX		X25Address
	MAX-ACCESS	read-create
	STATUS		current
	DESCRIPTION
		"."
	::= { bgs10X25SubcriberEntry 29}

bgs10X25Calling15	OBJECT-TYPE
	SYNTAX		X25Address
	MAX-ACCESS	read-create
	STATUS		current
	DESCRIPTION
		"."
	::= { bgs10X25SubcriberEntry 30}

bgs10X25Calling16	OBJECT-TYPE
	SYNTAX		X25Address
	MAX-ACCESS	read-create
	STATUS		current
	DESCRIPTION
		"."
	::= { bgs10X25SubcriberEntry 31}

bgs10X25Calling17	OBJECT-TYPE
	SYNTAX		X25Address
	MAX-ACCESS	read-create
	STATUS		current
	DESCRIPTION
		"."
	::= { bgs10X25SubcriberEntry 32}

bgs10X25Calling18	OBJECT-TYPE
	SYNTAX		X25Address
	MAX-ACCESS	read-create
	STATUS		current
	DESCRIPTION
		"."
	::= { bgs10X25SubcriberEntry 33}

bgs10X25Calling19	OBJECT-TYPE
	SYNTAX		X25Address
	MAX-ACCESS	read-create
	STATUS		current
	DESCRIPTION
		"."
	::= { bgs10X25SubcriberEntry 34}

bgs10X25Calling20	OBJECT-TYPE
	SYNTAX		X25Address
	MAX-ACCESS	read-create
	STATUS		current
	DESCRIPTION
		"."
	::= { bgs10X25SubcriberEntry 35}

bgs10X25Calling21	OBJECT-TYPE
	SYNTAX		X25Address
	MAX-ACCESS	read-create
	STATUS		current
	DESCRIPTION
		"."
	::= { bgs10X25SubcriberEntry 36}

bgs10X25Calling22	OBJECT-TYPE
	SYNTAX		X25Address
	MAX-ACCESS	read-create
	STATUS		current
	DESCRIPTION
		"."
	::= { bgs10X25SubcriberEntry 37}

bgs10X25Calling23	OBJECT-TYPE
	SYNTAX		X25Address
	MAX-ACCESS	read-create
	STATUS		current
	DESCRIPTION
		"."
	::= { bgs10X25SubcriberEntry 38}

bgs10X25Calling24	OBJECT-TYPE
	SYNTAX		X25Address
	MAX-ACCESS	read-create
	STATUS		current
	DESCRIPTION
		"."
	::= { bgs10X25SubcriberEntry 39}

bgs10X25Calling25	OBJECT-TYPE
	SYNTAX		X25Address
	MAX-ACCESS	read-create
	STATUS		current
	DESCRIPTION
		"."
	::= { bgs10X25SubcriberEntry 40}

bgs10X25Calling26	OBJECT-TYPE
	SYNTAX		X25Address
	MAX-ACCESS	read-create
	STATUS		current
	DESCRIPTION
		"."
	::= { bgs10X25SubcriberEntry 41}

bgs10X25Calling27	OBJECT-TYPE
	SYNTAX		X25Address
	MAX-ACCESS	read-create
	STATUS		current
	DESCRIPTION
		"."
	::= { bgs10X25SubcriberEntry 42}

bgs10X25Calling28	OBJECT-TYPE
	SYNTAX		X25Address
	MAX-ACCESS	read-create
	STATUS		current
	DESCRIPTION
		"."
	::= { bgs10X25SubcriberEntry 43}

bgs10X25Calling29	OBJECT-TYPE
	SYNTAX		X25Address
	MAX-ACCESS	read-create
	STATUS		current
	DESCRIPTION
		"."
	::= { bgs10X25SubcriberEntry 44}

bgs10X25Calling30	OBJECT-TYPE
	SYNTAX		X25Address
	MAX-ACCESS	read-create
	STATUS		current
	DESCRIPTION
		"."
	::= { bgs10X25SubcriberEntry 45}

-- struct_x25_trunk_table
bgs10X25TrunkTable	OBJECT-TYPE
	SYNTAX		SEQUENCE OF ZXB10X25TrunkEntry
	MAX-ACCESS	not-accessible
	STATUS		current
	DESCRIPTION
		"A list of Definition of Trunk-Table entries."
	::= { bgs10X25 3}
	
bgs10X25TrunkEntry	OBJECT-TYPE
	SYNTAX		ZXB10X25TrunkEntry
	MAX-ACCESS	not-accessible
	STATUS		current
	DESCRIPTION
		"An entry in the table."
	INDEX {	
		bgs10X25TrunkId		
		}
	::= { bgs10X25TrunkTable 1}
	
ZXB10X25TrunkEntry ::=
	SEQUENCE {	
		bgs10X25TrunkRowStatus					RowStatus,
		bgs10X25TrunkId							UShort,
		bgs10X25TrunkModule						UCHAR,
		bgs10X25TrunkPort						UShort,
		bgs10X25TrunkClass						UCHAR,
		bgs10X25TrunkCnfrate					Unsigned32,
		bgs10X25TrunkUsedrate					Unsigned32,		
		bgs10X25TrunkNetmatch					X25Address,
		bgs10X25TrunkProperty					UCHAR,
		bgs10X25TrunkPortstate					UCHAR,
		bgs10X25Trunkcnflinknum					UShort,
		bgs10X25Trunkuesdlinknum				UShort		
	}

bgs10X25TrunkRowStatus	OBJECT-TYPE
	SYNTAX		RowStatus
	MAX-ACCESS	read-create
	STATUS		current
	DESCRIPTION
		"."
	::= { bgs10X25TrunkEntry 1}

bgs10X25TrunkId	OBJECT-TYPE
	SYNTAX		UShort
	MAX-ACCESS	read-create
	STATUS		current
	DESCRIPTION
		"."
	::= { bgs10X25TrunkEntry 2}

bgs10X25TrunkModule	OBJECT-TYPE
	SYNTAX		UCHAR
	MAX-ACCESS	read-create
	STATUS		current
	DESCRIPTION
		"."
	::= { bgs10X25TrunkEntry 3}

bgs10X25TrunkPort	OBJECT-TYPE
	SYNTAX		UShort
	MAX-ACCESS	read-create
	STATUS		current
	DESCRIPTION
		"."
	::= { bgs10X25TrunkEntry 4}

bgs10X25TrunkClass	OBJECT-TYPE
	SYNTAX		UCHAR
	MAX-ACCESS	read-create
	STATUS		current
	DESCRIPTION
		"."
	::= { bgs10X25TrunkEntry 5}

bgs10X25TrunkCnfrate	OBJECT-TYPE
	SYNTAX		Unsigned32
	MAX-ACCESS	read-create
	STATUS		current
	DESCRIPTION
		"."
	::= { bgs10X25TrunkEntry 6}

bgs10X25TrunkUsedrate	OBJECT-TYPE
	SYNTAX		Unsigned32
	MAX-ACCESS	read-create
	STATUS		current
	DESCRIPTION
		"."
	::= { bgs10X25TrunkEntry 7}

bgs10X25TrunkNetmatch	OBJECT-TYPE
	SYNTAX		X25Address
	MAX-ACCESS	read-create
	STATUS		current
	DESCRIPTION
		"."
	::= { bgs10X25TrunkEntry 8}

bgs10X25TrunkProperty	OBJECT-TYPE
	SYNTAX		UCHAR
	MAX-ACCESS	read-create
	STATUS		current
	DESCRIPTION
		"."
	::= { bgs10X25TrunkEntry 9}

bgs10X25TrunkPortstate	OBJECT-TYPE
	SYNTAX		UCHAR
	MAX-ACCESS	read-create
	STATUS		current
	DESCRIPTION
		"."
	::= { bgs10X25TrunkEntry 10}

bgs10X25Trunkcnflinknum	OBJECT-TYPE
	SYNTAX		UShort
	MAX-ACCESS	read-create
	STATUS		current
	DESCRIPTION
		"."
	::= { bgs10X25TrunkEntry 11}

bgs10X25Trunkuesdlinknum	OBJECT-TYPE
	SYNTAX		UShort
	MAX-ACCESS	read-create
	STATUS		current
	DESCRIPTION
		"."
	::= { bgs10X25TrunkEntry 12}

-- struct_x25_pvc_config_table
bgs10X25PVCTable	OBJECT-TYPE
	SYNTAX		SEQUENCE OF ZXB10X25PVCEntry
	MAX-ACCESS	not-accessible
	STATUS		current
	DESCRIPTION
		"A list of Definition of PVC-Table entries."
	::= { bgs10X25 4}
	
bgs10X25PVCEntry	OBJECT-TYPE
	SYNTAX		ZXB10X25PVCEntry
	MAX-ACCESS	not-accessible
	STATUS		current
	DESCRIPTION
		"An entry in the table."
	INDEX {	
		bgs10X25PVCNo,
		bgs10X25PVCModule,
		bgs10X25PVCPort		
		}
	::= { bgs10X25PVCTable 1}
	
ZXB10X25PVCEntry ::=
	SEQUENCE {
		bgs10X25PVCRowStatus				RowStatus,
		bgs10X25PVCNo						UShort,
		bgs10X25PVCThrpt					UShort,
		bgs10X25PVCModule					UCHAR,
		bgs10X25PVCPort						UShort,
		bgs10X25PVCLci						UShort,
		bgs10X25PVCOutModule				UCHAR,
		bgs10X25PVCOutPort					UShort,		
		bgs10X25PVCOutLci					UShort
	}

bgs10X25PVCRowStatus	OBJECT-TYPE
	SYNTAX		RowStatus
	MAX-ACCESS	read-create
	STATUS		current
	DESCRIPTION
		"."
	::= { bgs10X25PVCEntry 1}

bgs10X25PVCNo	OBJECT-TYPE
	SYNTAX		UShort
	MAX-ACCESS	read-create
	STATUS		current
	DESCRIPTION
		"."
	::= { bgs10X25PVCEntry 2}

bgs10X25PVCThrpt	OBJECT-TYPE
	SYNTAX		UShort
	MAX-ACCESS	read-create
	STATUS		current
	DESCRIPTION
		"."
	::= { bgs10X25PVCEntry 3}

bgs10X25PVCModule	OBJECT-TYPE
	SYNTAX		UCHAR
	MAX-ACCESS	read-create
	STATUS		current
	DESCRIPTION
		"."
	::= { bgs10X25PVCEntry 4}

bgs10X25PVCPort	OBJECT-TYPE
	SYNTAX		UShort
	MAX-ACCESS	read-create
	STATUS		current
	DESCRIPTION
		"."
	::= { bgs10X25PVCEntry 5}

bgs10X25PVCLci	OBJECT-TYPE
	SYNTAX		UShort
	MAX-ACCESS	read-create
	STATUS		current
	DESCRIPTION
		"."
	::= { bgs10X25PVCEntry 6}

bgs10X25PVCOutModule	OBJECT-TYPE
	SYNTAX		UCHAR
	MAX-ACCESS	read-create
	STATUS		current
	DESCRIPTION
		"."
	::= { bgs10X25PVCEntry 7}

bgs10X25PVCOutPort	OBJECT-TYPE
	SYNTAX		UShort
	MAX-ACCESS	read-create
	STATUS		current
	DESCRIPTION
		"."
	::= { bgs10X25PVCEntry 8}

bgs10X25PVCOutLci	OBJECT-TYPE
	SYNTAX		UShort
	MAX-ACCESS	read-create
	STATUS		current
	DESCRIPTION
		"."
	::= { bgs10X25PVCEntry 9}
	
-- struct_x25_brdcstcfg_table
bgs10X25BrdcstTable	OBJECT-TYPE
	SYNTAX		SEQUENCE OF ZXB10X25BrdcstEntry
	MAX-ACCESS	not-accessible
	STATUS		current
	DESCRIPTION
		"A list of Definition of Brdcst-Table entries."
	::= { bgs10X25 5}
	
bgs10X25BrdcstEntry	OBJECT-TYPE
	SYNTAX		ZXB10X25BrdcstEntry
	MAX-ACCESS	not-accessible
	STATUS		current
	DESCRIPTION
		"An entry in the table."
	INDEX {	
		bgs10X25BrdcstSrcModule,
		bgs10X25BrdcstSrcPort,
		bgs10X25BrdcstOutModule,
		bgs10X25BrdcstOutLci		
		}
	::= { bgs10X25BrdcstTable 1}
	
ZXB10X25BrdcstEntry ::=
	SEQUENCE {
		bgs10X25BrdcstRowStatus				RowStatus,
		bgs10X25BrdcstSrcModule				UCHAR,
		bgs10X25BrdcstSrcPort				UShort,
		bgs10X25BrdcstThrpt					UShort,
		bgs10X25BrdcstOutModule				UCHAR,
		bgs10X25BrdcstOutPort				UShort,		
		bgs10X25BrdcstOutLci				UShort
	}

bgs10X25BrdcstRowStatus	OBJECT-TYPE
	SYNTAX		RowStatus
	MAX-ACCESS	read-create
	STATUS		current
	DESCRIPTION
		"."
	::= { bgs10X25BrdcstEntry 1}

bgs10X25BrdcstSrcModule	OBJECT-TYPE
	SYNTAX		UCHAR
	MAX-ACCESS	read-create
	STATUS		current
	DESCRIPTION
		"."
	::= { bgs10X25BrdcstEntry 2}

bgs10X25BrdcstSrcPort	OBJECT-TYPE
	SYNTAX		UShort
	MAX-ACCESS	read-create
	STATUS		current
	DESCRIPTION
		"."
	::= { bgs10X25BrdcstEntry 3}

bgs10X25BrdcstThrpt	OBJECT-TYPE
	SYNTAX		UShort
	MAX-ACCESS	read-create
	STATUS		current
	DESCRIPTION
		"."
	::= { bgs10X25BrdcstEntry 4}

bgs10X25BrdcstOutModule	OBJECT-TYPE
	SYNTAX		UCHAR
	MAX-ACCESS	read-create
	STATUS		current
	DESCRIPTION
		"."
	::= { bgs10X25BrdcstEntry 5}

bgs10X25BrdcstOutPort	OBJECT-TYPE
	SYNTAX		UShort
	MAX-ACCESS	read-create
	STATUS		current
	DESCRIPTION
		"."
	::= { bgs10X25BrdcstEntry 6}

bgs10X25BrdcstOutLci	OBJECT-TYPE
	SYNTAX		UShort
	MAX-ACCESS	read-create
	STATUS		current
	DESCRIPTION
		"."
	::= { bgs10X25BrdcstEntry 7}


-- struct_LapbOperTable(add)
bgs10X25LapbOperTable	OBJECT-TYPE
	SYNTAX		SEQUENCE OF ZXB10X25LapbOperEntry
	MAX-ACCESS	not-accessible
	STATUS		current
	DESCRIPTION
		"A list of Definition of LapbOper-Table entries."
	::= { bgs10X25 6}
	
bgs10X25LapbOperEntry	OBJECT-TYPE
	SYNTAX		ZXB10X25LapbOperEntry
	MAX-ACCESS	not-accessible
	STATUS		current
	DESCRIPTION
		"An entry in the table."
	INDEX { bgs10X25LapbOperLinkNo }		
	::= { bgs10X25LapbOperTable 1}
	
ZXB10X25LapbOperEntry ::=
	SEQUENCE {
		bgs10X25LapbOperRowStatus				RowStatus,
		bgs10X25LapbOperType					UCHAR,
		bgs10X25LapbOperState					UCHAR,
		bgs10X25LapbOperRealmodule				UCHAR,
		bgs10X25LapbOperRealport				UCHAR,
		bgs10X25LapbOperDlci					Unsigned32,		
		bgs10X25LapbOperVpi						UShort,
		bgs10X25LapbOperVci						UShort,
		bgs10X25LapbOperStationType 			UCHAR,
		bgs10X25LapbOperControlField  			UCHAR,	
		bgs10X25LapbOperLinkMode    			UCHAR,	
		bgs10X25LapbOperTransmitN1FrameSize 	UShort,		
		bgs10X25LapbOperReceiveN1FrameSize 		UShort,
		bgs10X25LapbOperTransmitKWindowSize 	UShort,
		bgs10X25LapbOperReceiveKWindowSize 		UShort,
		bgs10X25LapbOperN2RxmitCount 			UShort,
		bgs10X25LapbOperT1AckTimer 				UShort,
		bgs10X25LapbOperT2AckDelayTimer 		UShort,
		bgs10X25LapbOperT3DisconnectTimer 		UShort,
		bgs10X25LapbOperT4IdleTimer 			UShort,
		bgs10X25LapbOperPortId 					UShort,
		bgs10X25LapbOperProtocolVersionId 		UCHAR,
		bgs10X25LapbOperLapbState				UCHAR,
		bgs10X25LapbOperLinkNo					UShort,
		bgs10X25LapbOperWNego					UCHAR,
		bgs10X25LapbOperStatus					UCHAR
	}

bgs10X25LapbOperRowStatus	OBJECT-TYPE
	SYNTAX		RowStatus
	MAX-ACCESS	read-create
	STATUS		current
	DESCRIPTION
		"."
	::= { bgs10X25LapbOperEntry 1}

bgs10X25LapbOperType	OBJECT-TYPE
	SYNTAX		UCHAR
	MAX-ACCESS	read-create
	STATUS		current
	DESCRIPTION
		"."
	::= { bgs10X25LapbOperEntry 2}
	
bgs10X25LapbOperState	OBJECT-TYPE
	SYNTAX		UCHAR
	MAX-ACCESS	read-create
	STATUS		current
	DESCRIPTION
		"."
	::= { bgs10X25LapbOperEntry 3}
	
bgs10X25LapbOperRealmodule	OBJECT-TYPE
	SYNTAX		UCHAR
	MAX-ACCESS	read-create
	STATUS		current
	DESCRIPTION
		"."
	::= { bgs10X25LapbOperEntry 4}
	
bgs10X25LapbOperRealport	OBJECT-TYPE
	SYNTAX		UCHAR
	MAX-ACCESS	read-create
	STATUS		current
	DESCRIPTION
		"."
	::= { bgs10X25LapbOperEntry 5}
	
bgs10X25LapbOperDlci	OBJECT-TYPE
	SYNTAX		Unsigned32
	MAX-ACCESS	read-create
	STATUS		current
	DESCRIPTION
		"."
	::= { bgs10X25LapbOperEntry 6}
	
bgs10X25LapbOperVpi	OBJECT-TYPE
	SYNTAX		UShort
	MAX-ACCESS	read-create
	STATUS		current
	DESCRIPTION
		"."
	::= { bgs10X25LapbOperEntry 7}
	
bgs10X25LapbOperVci	OBJECT-TYPE
	SYNTAX		UShort
	MAX-ACCESS	read-create
	STATUS		current
	DESCRIPTION
		"."
	::= { bgs10X25LapbOperEntry 8}

bgs10X25LapbOperStationType	OBJECT-TYPE
	SYNTAX		UCHAR
	MAX-ACCESS	read-create
	STATUS		current
	DESCRIPTION
		"."
	::= { bgs10X25LapbOperEntry 9}

bgs10X25LapbOperControlField	OBJECT-TYPE
	SYNTAX		UCHAR
	MAX-ACCESS	read-create
	STATUS		current
	DESCRIPTION
		"."
	::= { bgs10X25LapbOperEntry 10}

bgs10X25LapbOperLinkMode	OBJECT-TYPE
	SYNTAX		UCHAR
	MAX-ACCESS	read-create
	STATUS		current
	DESCRIPTION
		"."
	::= { bgs10X25LapbOperEntry 11}

bgs10X25LapbOperTransmitN1FrameSize	OBJECT-TYPE
	SYNTAX		UShort
	MAX-ACCESS	read-create
	STATUS		current
	DESCRIPTION
		"."
	::= { bgs10X25LapbOperEntry 12}

bgs10X25LapbOperReceiveN1FrameSize	OBJECT-TYPE
	SYNTAX		UShort
	MAX-ACCESS	read-create
	STATUS		current
	DESCRIPTION
		"."
	::= { bgs10X25LapbOperEntry 13}

bgs10X25LapbOperTransmitKWindowSize	OBJECT-TYPE
	SYNTAX		UShort
	MAX-ACCESS	read-create
	STATUS		current
	DESCRIPTION
		"."
	::= { bgs10X25LapbOperEntry 14}

bgs10X25LapbOperReceiveKWindowSize	OBJECT-TYPE
	SYNTAX		UShort
	MAX-ACCESS	read-create
	STATUS		current
	DESCRIPTION
		"."
	::= { bgs10X25LapbOperEntry 15}

bgs10X25LapbOperN2RxmitCount	OBJECT-TYPE
	SYNTAX		UShort
	MAX-ACCESS	read-create
	STATUS		current
	DESCRIPTION
		"."
	::= { bgs10X25LapbOperEntry 16}

bgs10X25LapbOperT1AckTimer	OBJECT-TYPE
	SYNTAX		UShort
	MAX-ACCESS	read-create
	STATUS		current
	DESCRIPTION
		"."
	::= { bgs10X25LapbOperEntry 17}

bgs10X25LapbOperT2AckDelayTimer	OBJECT-TYPE
	SYNTAX		UShort
	MAX-ACCESS	read-create
	STATUS		current
	DESCRIPTION
		"."
	::= { bgs10X25LapbOperEntry 18}

bgs10X25LapbOperT3DisconnectTimer	OBJECT-TYPE
	SYNTAX		UShort
	MAX-ACCESS	read-create
	STATUS		current
	DESCRIPTION
		"."
	::= { bgs10X25LapbOperEntry 19}

bgs10X25LapbOperT4IdleTimer	OBJECT-TYPE
	SYNTAX		UShort
	MAX-ACCESS	read-create
	STATUS		current
	DESCRIPTION
		"."
	::= { bgs10X25LapbOperEntry 20}

bgs10X25LapbOperPortId	OBJECT-TYPE
	SYNTAX		UShort
	MAX-ACCESS	read-create
	STATUS		current
	DESCRIPTION
		"."
	::= { bgs10X25LapbOperEntry 21}

bgs10X25LapbOperProtocolVersionId	OBJECT-TYPE
	SYNTAX		UCHAR
	MAX-ACCESS	read-create
	STATUS		current
	DESCRIPTION
		"."
	::= { bgs10X25LapbOperEntry 22}

bgs10X25LapbOperLapbState	OBJECT-TYPE
	SYNTAX		UCHAR
	MAX-ACCESS	read-create
	STATUS		current
	DESCRIPTION
		"."
	::= { bgs10X25LapbOperEntry 23}

bgs10X25LapbOperLinkNo	OBJECT-TYPE
	SYNTAX		UShort
	MAX-ACCESS	read-create
	STATUS		current
	DESCRIPTION
		"."
	::= { bgs10X25LapbOperEntry 24}

bgs10X25LapbOperWNego	OBJECT-TYPE
	SYNTAX		UCHAR
	MAX-ACCESS	read-create
	STATUS		current
	DESCRIPTION
		"."
	::= { bgs10X25LapbOperEntry 25}
	
bgs10X25LapbOperStatus	OBJECT-TYPE
	SYNTAX		UCHAR
	MAX-ACCESS	read-create
	STATUS		current
	DESCRIPTION
		"."
	::= { bgs10X25LapbOperEntry 26}
		
-- struct_x25OperTable
bgs10X25OperTable	OBJECT-TYPE
	SYNTAX		SEQUENCE OF ZXB10X25OperEntry
	MAX-ACCESS	not-accessible
	STATUS		current
	DESCRIPTION
		"A list of Definition of Operation Table entries."
	::= { bgs10X25 7}
	
bgs10X25OperEntry	OBJECT-TYPE
	SYNTAX		ZXB10X25OperEntry
	MAX-ACCESS	not-accessible
	STATUS		current
	DESCRIPTION
		"An entry in the table."
	INDEX{
	  bgs10X25OperLinkno	
		}
	::= { bgs10X25OperTable 1}
	
ZXB10X25OperEntry ::=
	SEQUENCE {
		bgs10X25OperRowStatus						RowStatus,
		bgs10X25OperInterfaceMode            		UCHAR,		
		bgs10X25OperMaxActiveCircuits  				UShort,
		bgs10X25OperPacketSequencing				UCHAR,
		bgs10X25OperRestartTimer 					UShort,		
		bgs10X25OperCallTimer 						UShort,
		bgs10X25OperResetTimer 						UShort,	
		bgs10X25OperClearTimer 						UShort,	
		bgs10X25OperWindowTimer    					Unsigned32,
		bgs10X25OperDataRxmtTimer 					Unsigned32,	
		bgs10X25OperInterruptTimer 					Unsigned32,	
		bgs10X25OperRejectTimer 					Unsigned32,	
		bgs10X25OperRegistrationRequestTimer 		Unsigned32,	
		bgs10X25OperMinimumRecallTimer 				UShort,
		bgs10X25OperRestartCount            		UShort,	
		bgs10X25OperResetCount						UShort,	
		bgs10X25OperClearCount						UShort,	
		bgs10X25OperDataRxmtCount					UShort,	
		bgs10X25OperRejectCount						UShort,	
		bgs10X25OperRegistrationRequestCount		UShort,	
		bgs10X25OperNumberPVCs						UShort,	
		bgs10X25OperDefCallParamId					UShort,	
		bgs10X25OperLocalAddress					X25Address,
		bgs10X25OperDataLinkId						UShort,
		bgs10X25OperProtocolVersionSupported		UShort,	
		bgs10X25OperWNego							UCHAR,	
		bgs10X25OperLinkno							UShort,
		bgs10X25OperMaxCircuit						UShort,
		bgs10X25OperRestart							UCHAR,
		bgs10X25OperPortFlag						UCHAR,	
		bgs10X25OperFlag							UCHAR
	}

bgs10X25OperRowStatus	OBJECT-TYPE
	SYNTAX		RowStatus
	MAX-ACCESS	read-create
	STATUS		current
	DESCRIPTION
		"."
	::= { bgs10X25OperEntry 1}

bgs10X25OperInterfaceMode	OBJECT-TYPE
	SYNTAX		UCHAR
	MAX-ACCESS	read-create
	STATUS		current
	DESCRIPTION
		"."
	::= { bgs10X25OperEntry 2}
	
bgs10X25OperMaxActiveCircuits	OBJECT-TYPE
	SYNTAX		UShort
	MAX-ACCESS	read-create
	STATUS		current
	DESCRIPTION
		"."
	::= { bgs10X25OperEntry 3}
	
bgs10X25OperPacketSequencing	OBJECT-TYPE
	SYNTAX		UCHAR
	MAX-ACCESS	read-create
	STATUS		current
	DESCRIPTION
		"."
	::= { bgs10X25OperEntry 4}
	
bgs10X25OperRestartTimer	OBJECT-TYPE
	SYNTAX		UShort
	MAX-ACCESS	read-create
	STATUS		current
	DESCRIPTION
		"."
	::= { bgs10X25OperEntry 5}
	
bgs10X25OperCallTimer	OBJECT-TYPE
	SYNTAX		UShort
	MAX-ACCESS	read-create
	STATUS		current
	DESCRIPTION
		"."
	::= { bgs10X25OperEntry 6}
	
bgs10X25OperResetTimer	OBJECT-TYPE
	SYNTAX		UShort
	MAX-ACCESS	read-create
	STATUS		current
	DESCRIPTION
		"."
	::= { bgs10X25OperEntry 7}
	
bgs10X25OperClearTimer	OBJECT-TYPE
	SYNTAX		UShort
	MAX-ACCESS	read-create
	STATUS		current
	DESCRIPTION
		"."
	::= { bgs10X25OperEntry 8}
		
bgs10X25OperWindowTimer	OBJECT-TYPE
	SYNTAX		Unsigned32
	MAX-ACCESS	read-create
	STATUS		current
	DESCRIPTION
		"."
	::= { bgs10X25OperEntry 9}

bgs10X25OperDataRxmtTimer	OBJECT-TYPE
	SYNTAX		Unsigned32
	MAX-ACCESS	read-create
	STATUS		current
	DESCRIPTION
		"."
	::= { bgs10X25OperEntry 10}

bgs10X25OperInterruptTimer	OBJECT-TYPE
	SYNTAX		Unsigned32
	MAX-ACCESS	read-create
	STATUS		current
	DESCRIPTION
		"."
	::= { bgs10X25OperEntry 11}

bgs10X25OperRejectTimer	OBJECT-TYPE
	SYNTAX		Unsigned32
	MAX-ACCESS	read-create
	STATUS		current
	DESCRIPTION
		"."
	::= { bgs10X25OperEntry 12}

bgs10X25OperRegistrationRequestTimer	OBJECT-TYPE
	SYNTAX		Unsigned32
	MAX-ACCESS	read-create
	STATUS		current
	DESCRIPTION
		"."
	::= { bgs10X25OperEntry 13}

bgs10X25OperMinimumRecallTimer	OBJECT-TYPE
	SYNTAX		UShort
	MAX-ACCESS	read-create
	STATUS		current
	DESCRIPTION
		"."
	::= { bgs10X25OperEntry 14}

bgs10X25OperRestartCount	OBJECT-TYPE
	SYNTAX		UShort
	MAX-ACCESS	read-create
	STATUS		current
	DESCRIPTION
		"."
	::= { bgs10X25OperEntry 15}

bgs10X25OperResetCount	OBJECT-TYPE
	SYNTAX		UShort
	MAX-ACCESS	read-create
	STATUS		current
	DESCRIPTION
		"."
	::= { bgs10X25OperEntry 16}

bgs10X25OperClearCount	OBJECT-TYPE
	SYNTAX		UShort
	MAX-ACCESS	read-create
	STATUS		current
	DESCRIPTION
		"."
	::= { bgs10X25OperEntry 17}

bgs10X25OperDataRxmtCount	OBJECT-TYPE
	SYNTAX		UShort
	MAX-ACCESS	read-create
	STATUS		current
	DESCRIPTION
		"."
	::= { bgs10X25OperEntry 18}

bgs10X25OperRejectCount	OBJECT-TYPE
	SYNTAX		UShort
	MAX-ACCESS	read-create
	STATUS		current
	DESCRIPTION
		"."
	::= { bgs10X25OperEntry 19}

bgs10X25OperRegistrationRequestCount	OBJECT-TYPE
	SYNTAX		UShort
	MAX-ACCESS	read-create
	STATUS		current
	DESCRIPTION
		"."
	::= { bgs10X25OperEntry 20}

bgs10X25OperNumberPVCs	OBJECT-TYPE
	SYNTAX		UShort
	MAX-ACCESS	read-create
	STATUS		current
	DESCRIPTION
		"."
	::= { bgs10X25OperEntry 21}

bgs10X25OperDefCallParamId	OBJECT-TYPE
	SYNTAX		UShort
	MAX-ACCESS	read-create
	STATUS		current
	DESCRIPTION
		"."
	::= { bgs10X25OperEntry 22}

bgs10X25OperLocalAddress	OBJECT-TYPE
	SYNTAX		X25Address
	MAX-ACCESS	read-create
	STATUS		current
	DESCRIPTION
		"."
	::= { bgs10X25OperEntry 23}

bgs10X25OperDataLinkId	OBJECT-TYPE
	SYNTAX		UShort
	MAX-ACCESS	read-create
	STATUS		current
	DESCRIPTION
		"."
	::= { bgs10X25OperEntry 24}

bgs10X25OperProtocolVersionSupported	OBJECT-TYPE
	SYNTAX		UShort
	MAX-ACCESS	read-create
	STATUS		current
	DESCRIPTION
		"."
	::= { bgs10X25OperEntry 25}

bgs10X25OperWNego	OBJECT-TYPE
	SYNTAX		UCHAR
	MAX-ACCESS	read-create
	STATUS		current
	DESCRIPTION
		"."
	::= { bgs10X25OperEntry 26}

bgs10X25OperLinkno	OBJECT-TYPE
	SYNTAX		UShort
	MAX-ACCESS	read-create
	STATUS		current
	DESCRIPTION
		"."
	::= { bgs10X25OperEntry 27}
	
bgs10X25OperMaxCircuit	OBJECT-TYPE
	SYNTAX		UShort
	MAX-ACCESS	read-create
	STATUS		current
	DESCRIPTION
		"."
	::= { bgs10X25OperEntry 28}
	
bgs10X25OperRestart	OBJECT-TYPE
	SYNTAX		UCHAR
	MAX-ACCESS	read-create
	STATUS		current
	DESCRIPTION
		"."
	::= { bgs10X25OperEntry 29}

bgs10X25OperPortFlag	OBJECT-TYPE
	SYNTAX		UCHAR
	MAX-ACCESS	read-create
	STATUS		current
	DESCRIPTION
		"."
	::= { bgs10X25OperEntry 30}

bgs10X25OperFlag	OBJECT-TYPE
	SYNTAX		UCHAR
	MAX-ACCESS	read-create
	STATUS		current
	DESCRIPTION
		"."
	::= { bgs10X25OperEntry 31}

-- struct_Rs232PortTable
bgs10X25Rs232PortTable	OBJECT-TYPE
	SYNTAX		SEQUENCE OF ZXB10X25Rs232PortEntry
	MAX-ACCESS	not-accessible
	STATUS		current
	DESCRIPTION
		"A list of Definition of Rs232 Port Table entries."
	::= { bgs10X25 8}
	
bgs10X25Rs232PortEntry	OBJECT-TYPE
	SYNTAX		ZXB10X25Rs232PortEntry
	MAX-ACCESS	not-accessible
	STATUS		current
	DESCRIPTION
		"An entry in the table."
	AUGMENTS
      {	
    	rs232PortEntry
	  }
	::= { bgs10X25Rs232PortTable 1}
	
ZXB10X25Rs232PortEntry ::=
	SEQUENCE {
		bgs10X25Rs232PortRowStatus				RowStatus,
		bgs10X25Rs232PortDSRAlarm				UCHAR,
		bgs10X25Rs232PortDTRAlarm				UCHAR,
		bgs10X25Rs232PortFlag					UCHAR
	}

bgs10X25Rs232PortRowStatus	OBJECT-TYPE
	SYNTAX		RowStatus
	MAX-ACCESS	read-create
	STATUS		current
	DESCRIPTION
		"."
	::= { bgs10X25Rs232PortEntry 1}

bgs10X25Rs232PortDSRAlarm	OBJECT-TYPE
	SYNTAX		UCHAR
	MAX-ACCESS	read-create
	STATUS		current
	DESCRIPTION
		"."
	::= { bgs10X25Rs232PortEntry 2}

bgs10X25Rs232PortDTRAlarm	OBJECT-TYPE
	SYNTAX		UCHAR
	MAX-ACCESS	read-create
	STATUS		current
	DESCRIPTION
		"."
	::= { bgs10X25Rs232PortEntry 3}

bgs10X25Rs232PortFlag	OBJECT-TYPE
	SYNTAX		UCHAR
	MAX-ACCESS	read-create
	STATUS		current
	DESCRIPTION
		"."
	::= { bgs10X25Rs232PortEntry 4}

-- struct_Rs232SyncPortTable
bgs10X25Rs232SyncPortTable	OBJECT-TYPE
	SYNTAX		SEQUENCE OF ZXB10X25Rs232SyncPortEntry
	MAX-ACCESS	not-accessible
	STATUS		current
	DESCRIPTION
		"A list of Definition of Rs232 Syncronize Port Table entries."
	::= { bgs10X25 9}
	
bgs10X25Rs232SyncPortEntry	OBJECT-TYPE
	SYNTAX		ZXB10X25Rs232SyncPortEntry
	MAX-ACCESS	not-accessible
	STATUS		current
	DESCRIPTION
		"An entry in the table."
	AUGMENTS
      {	
    	rs232SyncPortEntry
	  }
	::= { bgs10X25Rs232SyncPortTable 1}
	
ZXB10X25Rs232SyncPortEntry ::=
	SEQUENCE {
		bgs10X25Rs232SyncPortRowStatus				RowStatus,
		bgs10X25Rs232SyncPortSpaceTime				Unsigned32,
		bgs10X25Rs232SyncPortSendCounts				Unsigned32,
		bgs10X25Rs232SyncPortRecvCounts				Unsigned32
	}

bgs10X25Rs232SyncPortRowStatus	OBJECT-TYPE
	SYNTAX		RowStatus
	MAX-ACCESS	read-create
	STATUS		current
	DESCRIPTION
		"."
	::= { bgs10X25Rs232SyncPortEntry 1}

bgs10X25Rs232SyncPortSpaceTime	OBJECT-TYPE
	SYNTAX		Unsigned32
	MAX-ACCESS	read-create
	STATUS		current
	DESCRIPTION
		"."
	::= { bgs10X25Rs232SyncPortEntry 2}

bgs10X25Rs232SyncPortSendCounts	OBJECT-TYPE
	SYNTAX		Unsigned32
	MAX-ACCESS	read-create
	STATUS		current
	DESCRIPTION
		"."
	::= { bgs10X25Rs232SyncPortEntry 3}

bgs10X25Rs232SyncPortRecvCounts	OBJECT-TYPE
	SYNTAX		Unsigned32
	MAX-ACCESS	read-create
	STATUS		current
	DESCRIPTION
		"."
	::= { bgs10X25Rs232SyncPortEntry 4}

-- struct_Rs232InSigTable
bgs10X25Rs232InSigTable	OBJECT-TYPE
	SYNTAX		SEQUENCE OF ZXB10X25Rs232InSigEntry
	MAX-ACCESS	not-accessible
	STATUS		current
	DESCRIPTION
		"A list of Definition of Rs232 Input Signal Table entries."
	::= { bgs10X25 10}
	
bgs10X25Rs232InSigEntry	OBJECT-TYPE
	SYNTAX		ZXB10X25Rs232InSigEntry
	MAX-ACCESS	not-accessible
	STATUS		current
	DESCRIPTION
		"An entry in the table."
	INDEX
      {	
    	bgs10X25Rs232InSigphyModule,
    	bgs10X25Rs232InSigphyPort,
    	bgs10X25Rs232InSigName
	  }
	::= { bgs10X25Rs232InSigTable 1}
	
ZXB10X25Rs232InSigEntry ::=
	SEQUENCE {
		bgs10X25Rs232InSigRowStatus		RowStatus,
		bgs10X25Rs232InSigphyModule 	UCHAR,
		bgs10X25Rs232InSigphyPort 		UShort,	
		bgs10X25Rs232InSigName 		 	UCHAR,
		bgs10X25Rs232InSigState 	 	UCHAR,	
		bgs10X25Rs232InSigChanges 	 	Unsigned32
	}

bgs10X25Rs232InSigRowStatus	OBJECT-TYPE
	SYNTAX		RowStatus
	MAX-ACCESS	read-create
	STATUS		current
	DESCRIPTION
		"."
	::= { bgs10X25Rs232InSigEntry 1}
	
bgs10X25Rs232InSigphyModule	OBJECT-TYPE
	SYNTAX		UCHAR
	MAX-ACCESS	read-create
	STATUS		current
	DESCRIPTION
		"."
	::= { bgs10X25Rs232InSigEntry 2}

bgs10X25Rs232InSigphyPort	OBJECT-TYPE
	SYNTAX		UShort
	MAX-ACCESS	read-create
	STATUS		current
	DESCRIPTION
		"."
	::= { bgs10X25Rs232InSigEntry 3}

bgs10X25Rs232InSigName	OBJECT-TYPE
	SYNTAX		UCHAR
	MAX-ACCESS	read-create
	STATUS		current
	DESCRIPTION
		"."
	::= { bgs10X25Rs232InSigEntry 4}

bgs10X25Rs232InSigState	OBJECT-TYPE
	SYNTAX		UCHAR
	MAX-ACCESS	read-create
	STATUS		current
	DESCRIPTION
		"."
	::= { bgs10X25Rs232InSigEntry 5}

bgs10X25Rs232InSigChanges	OBJECT-TYPE
	SYNTAX		Unsigned32
	MAX-ACCESS	read-create
	STATUS		current
	DESCRIPTION
		"."
	::= { bgs10X25Rs232InSigEntry 6}

-- struct_Rs232OutSigTable
bgs10X25Rs232OutSigTable	OBJECT-TYPE
	SYNTAX		SEQUENCE OF ZXB10X25Rs232OutSigEntry
	MAX-ACCESS	not-accessible
	STATUS		current
	DESCRIPTION
		"A list of Definition of Rs232 Output Signal Table entries."
	::= { bgs10X25 11}
	
bgs10X25Rs232OutSigEntry	OBJECT-TYPE
	SYNTAX		ZXB10X25Rs232OutSigEntry
	MAX-ACCESS	not-accessible
	STATUS		current
	DESCRIPTION
		"An entry in the table."
	INDEX
      {	
    	bgs10X25Rs232OutSigphyModule,
    	bgs10X25Rs232OutSigphyPort,
    	bgs10X25Rs232OutSigName
	  }
	::= { bgs10X25Rs232OutSigTable 1}
	
ZXB10X25Rs232OutSigEntry ::=
	SEQUENCE {
		bgs10X25Rs232OutSigRowStatus			RowStatus,
		bgs10X25Rs232OutSigphyModule 			UCHAR,
		bgs10X25Rs232OutSigphyPort 			    UShort,	
		bgs10X25Rs232OutSigName 	     		UCHAR,
		bgs10X25Rs232OutSigState 	     		UCHAR,	
		bgs10X25Rs232OutSigChanges 	     		Unsigned32			
	}

bgs10X25Rs232OutSigRowStatus	OBJECT-TYPE
	SYNTAX		RowStatus
	MAX-ACCESS	read-create
	STATUS		current
	DESCRIPTION
		"."
	::= { bgs10X25Rs232OutSigEntry 1}

bgs10X25Rs232OutSigphyModule	OBJECT-TYPE
	SYNTAX		UCHAR
	MAX-ACCESS	read-create
	STATUS		current
	DESCRIPTION
		"."
	::= { bgs10X25Rs232OutSigEntry 2}

bgs10X25Rs232OutSigphyPort	OBJECT-TYPE
	SYNTAX		UShort
	MAX-ACCESS	read-create
	STATUS		current
	DESCRIPTION
		"."
	::= { bgs10X25Rs232OutSigEntry 3}

bgs10X25Rs232OutSigName	OBJECT-TYPE
	SYNTAX		UCHAR
	MAX-ACCESS	read-create
	STATUS		current
	DESCRIPTION
		"."
	::= { bgs10X25Rs232OutSigEntry 4}

bgs10X25Rs232OutSigState	OBJECT-TYPE
	SYNTAX		UCHAR
	MAX-ACCESS	read-create
	STATUS		current
	DESCRIPTION
		"."
	::= { bgs10X25Rs232OutSigEntry 5}

bgs10X25Rs232OutSigChanges	OBJECT-TYPE
	SYNTAX		Unsigned32
	MAX-ACCESS	read-create
	STATUS		current
	DESCRIPTION
		"."
	::= { bgs10X25Rs232OutSigEntry 6}
	

-- struct_x25StatTable
bgs10X25StatTable	OBJECT-TYPE
	SYNTAX		SEQUENCE OF ZXB10X25StatEntry
	MAX-ACCESS	not-accessible
	STATUS		current
	DESCRIPTION
		"A list of Definition of Statistics Table entries."
	::= { bgs10X25 12}
	
bgs10X25StatEntry	OBJECT-TYPE
	SYNTAX		ZXB10X25StatEntry
	MAX-ACCESS	not-accessible
	STATUS		current
	DESCRIPTION
		"An entry in the table."
	AUGMENTS
      {	
    	x25StatEntry
	  }
	::= { bgs10X25StatTable 1}
	
ZXB10X25StatEntry ::=
	SEQUENCE {
		bgs10X25StatRowStatus				RowStatus,
		bgs10X25StatSpaceTime				Unsigned32,
		bgs10X25StatCircuitSpaceTime		Unsigned32
	}

bgs10X25StatRowStatus	OBJECT-TYPE
	SYNTAX		RowStatus
	MAX-ACCESS	read-create
	STATUS		current
	DESCRIPTION
		"."
	::= { bgs10X25StatEntry 1}

bgs10X25StatSpaceTime	OBJECT-TYPE
	SYNTAX		Unsigned32
	MAX-ACCESS	read-create
	STATUS		current
	DESCRIPTION
		"."
	::= { bgs10X25StatEntry 2}

bgs10X25StatCircuitSpaceTime	OBJECT-TYPE
	SYNTAX		Unsigned32
	MAX-ACCESS	read-create
	STATUS		current
	DESCRIPTION
		"."
	::= { bgs10X25StatEntry 3}

-- struct_LapbFlowTable
bgs10X25LapbFlowTable	OBJECT-TYPE
	SYNTAX		SEQUENCE OF ZXB10X25LapbFlowEntry
	MAX-ACCESS	not-accessible
	STATUS		current
	DESCRIPTION
		"A list of Definition of Lapb Flow Table entries."
	::= { bgs10X25 13}
	
bgs10X25LapbFlowEntry	OBJECT-TYPE
	SYNTAX		ZXB10X25LapbFlowEntry
	MAX-ACCESS	not-accessible
	STATUS		current
	DESCRIPTION
		"An entry in the table."
	AUGMENTS
      {	
    	lapbFlowEntry
	  }
	::= { bgs10X25LapbFlowTable 1}
	
ZXB10X25LapbFlowEntry ::=
	SEQUENCE {
		bgs10X25LapbFlowRowStatus				RowStatus,
		bgs10X25LapbFlowSpaceTime				Unsigned32,
		bgs10X25LapbFlowRROutPkts				Unsigned32,
		bgs10X25LapbFlowRRInPkts				Unsigned32,
		bgs10X25LapbFlowRNROutPkts				Unsigned32,
		bgs10X25LapbFlowRNRInPkts				Unsigned32,
		bgs10X25LapbFlowIOutPkts				Unsigned32,
		bgs10X25LapbFlowIInPkts					Unsigned32,
		bgs10X25LapbFlowDMOutPkts				Unsigned32,
		bgs10X25LapbFlowDMInPkts				Unsigned32,
		bgs10X25LapbFlowSABOutPkts				Unsigned32,
		bgs10X25LapbFlowSABInPkts				Unsigned32,
		bgs10X25LapbFlowUAOutPkts				Unsigned32,
		bgs10X25LapbFlowUAInPkts				Unsigned32,
		bgs10X25LapbFlowDISCOutPkts				Unsigned32,
		bgs10X25LapbFlowDISCInPkts				Unsigned32,
		bgs10X25LapbFlowFRMROutPkts				Unsigned32,
		bgs10X25LapbFlowFRMRInPkts				Unsigned32,
		bgs10X25LapbFlowOutPkts					Unsigned32,
		bgs10X25LapbFlowInPkts					Unsigned32		
	}

bgs10X25LapbFlowRowStatus	OBJECT-TYPE
	SYNTAX		RowStatus
	MAX-ACCESS	read-create
	STATUS		current
	DESCRIPTION
		"."
	::= { bgs10X25LapbFlowEntry 1}

bgs10X25LapbFlowSpaceTime	OBJECT-TYPE
	SYNTAX		Unsigned32
	MAX-ACCESS	read-create
	STATUS		current
	DESCRIPTION
		"."
	::= { bgs10X25LapbFlowEntry 2}

bgs10X25LapbFlowRROutPkts	OBJECT-TYPE
	SYNTAX		Unsigned32
	MAX-ACCESS	read-create
	STATUS		current
	DESCRIPTION
		"."
	::= { bgs10X25LapbFlowEntry 3}

bgs10X25LapbFlowRRInPkts	OBJECT-TYPE
	SYNTAX		Unsigned32
	MAX-ACCESS	read-create
	STATUS		current
	DESCRIPTION
		"."
	::= { bgs10X25LapbFlowEntry 4}

bgs10X25LapbFlowRNROutPkts	OBJECT-TYPE
	SYNTAX		Unsigned32
	MAX-ACCESS	read-create
	STATUS		current
	DESCRIPTION
		"."
	::= { bgs10X25LapbFlowEntry 5}

bgs10X25LapbFlowRNRInPkts	OBJECT-TYPE
	SYNTAX		Unsigned32
	MAX-ACCESS	read-create
	STATUS		current
	DESCRIPTION
		"."
	::= { bgs10X25LapbFlowEntry 6}

bgs10X25LapbFlowIOutPkts	OBJECT-TYPE
	SYNTAX		Unsigned32
	MAX-ACCESS	read-create
	STATUS		current
	DESCRIPTION
		"."
	::= { bgs10X25LapbFlowEntry 7}

bgs10X25LapbFlowIInPkts	OBJECT-TYPE
	SYNTAX		Unsigned32
	MAX-ACCESS	read-create
	STATUS		current
	DESCRIPTION
		"."
	::= { bgs10X25LapbFlowEntry 8}

bgs10X25LapbFlowDMOutPkts	OBJECT-TYPE
	SYNTAX		Unsigned32
	MAX-ACCESS	read-create
	STATUS		current
	DESCRIPTION
		"."
	::= { bgs10X25LapbFlowEntry 9}

bgs10X25LapbFlowDMInPkts	OBJECT-TYPE
	SYNTAX		Unsigned32
	MAX-ACCESS	read-create
	STATUS		current
	DESCRIPTION
		"."
	::= { bgs10X25LapbFlowEntry 10}

bgs10X25LapbFlowSABOutPkts	OBJECT-TYPE
	SYNTAX		Unsigned32
	MAX-ACCESS	read-create
	STATUS		current
	DESCRIPTION
		"."
	::= { bgs10X25LapbFlowEntry 11}

bgs10X25LapbFlowSABInPkts	OBJECT-TYPE
	SYNTAX		Unsigned32
	MAX-ACCESS	read-create
	STATUS		current
	DESCRIPTION
		"."
	::= { bgs10X25LapbFlowEntry 12}

bgs10X25LapbFlowUAOutPkts	OBJECT-TYPE
	SYNTAX		Unsigned32
	MAX-ACCESS	read-create
	STATUS		current
	DESCRIPTION
		"."
	::= { bgs10X25LapbFlowEntry 13}

bgs10X25LapbFlowUAInPkts	OBJECT-TYPE
	SYNTAX		Unsigned32
	MAX-ACCESS	read-create
	STATUS		current
	DESCRIPTION
		"."
	::= { bgs10X25LapbFlowEntry 14}

bgs10X25LapbFlowDISCOutPkts	OBJECT-TYPE
	SYNTAX		Unsigned32
	MAX-ACCESS	read-create
	STATUS		current
	DESCRIPTION
		"."
	::= { bgs10X25LapbFlowEntry 15}

bgs10X25LapbFlowDISCInPkts	OBJECT-TYPE
	SYNTAX		Unsigned32
	MAX-ACCESS	read-create
	STATUS		current
	DESCRIPTION
		"."
	::= { bgs10X25LapbFlowEntry 16}

bgs10X25LapbFlowFRMROutPkts	OBJECT-TYPE
	SYNTAX		Unsigned32
	MAX-ACCESS	read-create
	STATUS		current
	DESCRIPTION
		"."
	::= { bgs10X25LapbFlowEntry 17}

bgs10X25LapbFlowFRMRInPkts	OBJECT-TYPE
	SYNTAX		Unsigned32
	MAX-ACCESS	read-create
	STATUS		current
	DESCRIPTION
		"."
	::= { bgs10X25LapbFlowEntry 18}

bgs10X25LapbFlowOutPkts	OBJECT-TYPE
	SYNTAX		Unsigned32
	MAX-ACCESS	read-create
	STATUS		current
	DESCRIPTION
		"."
	::= { bgs10X25LapbFlowEntry 19}

bgs10X25LapbFlowInPkts	OBJECT-TYPE
	SYNTAX		Unsigned32
	MAX-ACCESS	read-create
	STATUS		current
	DESCRIPTION
		"."
	::= { bgs10X25LapbFlowEntry 20}

-- struct_x25CircuitTable
bgs10X25CircuitTable	OBJECT-TYPE
	SYNTAX		SEQUENCE OF ZXB10X25CircuitEntry
	MAX-ACCESS	not-accessible
	STATUS		current
	DESCRIPTION
		"A list of Definition of Circuit Table entries."
	::= { bgs10X25 14}
	
bgs10X25CircuitEntry	OBJECT-TYPE
	SYNTAX		ZXB10X25CircuitEntry
	MAX-ACCESS	not-accessible
	STATUS		current
	DESCRIPTION
		"An entry in the table."
	INDEX
      {	
    	bgs10X25CircuitModule,
    	bgs10X25CircuitPort,
		bgs10X25CircuitChannel    	
	  }
	::= { bgs10X25CircuitTable 1}
	
ZXB10X25CircuitEntry ::=
	SEQUENCE {
		bgs10X25CircuitRowStatus					RowStatus,
		bgs10X25CircuitModule 						UCHAR,
		bgs10X25CircuitPort 						UShort,		
		bgs10X25CircuitChannel 						UShort,	
		bgs10X25CircuitStatus                     	UCHAR,	
		bgs10X25CircuitEstablishTime                TimeTicks,
		bgs10X25CircuitDirection                 	UCHAR,
		bgs10X25CircuitInOctets                     Unsigned32,		
		bgs10X25CircuitInPdus                     	Unsigned32,		
		bgs10X25CircuitInRemotelyInitiatedResets    Unsigned32,		
		bgs10X25CircuitInProviderInitiatedResets    Unsigned32,		
		bgs10X25CircuitInInterrupts                 Unsigned32,		
		bgs10X25CircuitOutOctets                    Unsigned32,		
		bgs10X25CircuitOutPdus                    	Unsigned32,		
		bgs10X25CircuitOutInterrupts                Unsigned32,		
		bgs10X25CircuitDataRetransmissionTimeouts   Unsigned32,		
		bgs10X25CircuitResetTimeouts                Unsigned32,		
		bgs10X25CircuitInterruptTimeouts            Unsigned32,		
		bgs10X25CircuitCallParamId	                UShort,		
		bgs10X25CircuitCalledDteAddress    			X25Address,
		bgs10X25CircuitCallingDteAddress    		X25Address,
		bgs10X25CircuitOriginallyCalledAddress		X25Address	
	}

bgs10X25CircuitRowStatus	OBJECT-TYPE
	SYNTAX		RowStatus
	MAX-ACCESS	read-create
	STATUS		current
	DESCRIPTION
		"."
	::= { bgs10X25CircuitEntry 1}
	
bgs10X25CircuitModule	OBJECT-TYPE
	SYNTAX		UCHAR
	MAX-ACCESS	read-create
	STATUS		current
	DESCRIPTION
		"."
	::= { bgs10X25CircuitEntry 2}
	
bgs10X25CircuitPort	OBJECT-TYPE
	SYNTAX		UShort
	MAX-ACCESS	read-create
	STATUS		current
	DESCRIPTION
		"."
	::= { bgs10X25CircuitEntry 3}
	
bgs10X25CircuitChannel	OBJECT-TYPE
	SYNTAX		UShort
	MAX-ACCESS	read-create
	STATUS		current
	DESCRIPTION
		"."
	::= { bgs10X25CircuitEntry 4}
	
bgs10X25CircuitStatus	OBJECT-TYPE
	SYNTAX		UCHAR
	MAX-ACCESS	read-create
	STATUS		current
	DESCRIPTION
		"."
	::= { bgs10X25CircuitEntry 5}
	
bgs10X25CircuitEstablishTime	OBJECT-TYPE
	SYNTAX		TimeTicks
	MAX-ACCESS	read-create
	STATUS		current
	DESCRIPTION
		"."
	::= { bgs10X25CircuitEntry 6}
	
bgs10X25CircuitDirection	OBJECT-TYPE
	SYNTAX		UCHAR
	MAX-ACCESS	read-create
	STATUS		current
	DESCRIPTION
		"."
	::= { bgs10X25CircuitEntry 7}
	
bgs10X25CircuitInOctets	OBJECT-TYPE
	SYNTAX		Unsigned32
	MAX-ACCESS	read-create
	STATUS		current
	DESCRIPTION
		"."
	::= { bgs10X25CircuitEntry 8}
	
bgs10X25CircuitInPdus	OBJECT-TYPE
	SYNTAX		Unsigned32
	MAX-ACCESS	read-create
	STATUS		current
	DESCRIPTION
		"."
	::= { bgs10X25CircuitEntry 9}
	
bgs10X25CircuitInRemotelyInitiatedResets	OBJECT-TYPE
	SYNTAX		Unsigned32
	MAX-ACCESS	read-create
	STATUS		current
	DESCRIPTION
		"."
	::= { bgs10X25CircuitEntry 10}

bgs10X25CircuitInProviderInitiatedResets	OBJECT-TYPE
	SYNTAX		Unsigned32
	MAX-ACCESS	read-create
	STATUS		current
	DESCRIPTION
		"."
	::= { bgs10X25CircuitEntry 11}

bgs10X25CircuitInInterrupts	OBJECT-TYPE
	SYNTAX		Unsigned32
	MAX-ACCESS	read-create
	STATUS		current
	DESCRIPTION
		"."
	::= { bgs10X25CircuitEntry 12}

bgs10X25CircuitOutOctets	OBJECT-TYPE
	SYNTAX		Unsigned32
	MAX-ACCESS	read-create
	STATUS		current
	DESCRIPTION
		"."
	::= { bgs10X25CircuitEntry 13}

bgs10X25CircuitOutPdus	OBJECT-TYPE
	SYNTAX		Unsigned32
	MAX-ACCESS	read-create
	STATUS		current
	DESCRIPTION
		"."
	::= { bgs10X25CircuitEntry 14}

bgs10X25CircuitOutInterrupts	OBJECT-TYPE
	SYNTAX		Unsigned32
	MAX-ACCESS	read-create
	STATUS		current
	DESCRIPTION
		"."
	::= { bgs10X25CircuitEntry 15}

bgs10X25CircuitDataRetransmissionTimeouts	OBJECT-TYPE
	SYNTAX		Unsigned32
	MAX-ACCESS	read-create
	STATUS		current
	DESCRIPTION
		"."
	::= { bgs10X25CircuitEntry 16}

bgs10X25CircuitResetTimeouts	OBJECT-TYPE
	SYNTAX		Unsigned32
	MAX-ACCESS	read-create
	STATUS		current
	DESCRIPTION
		"."
	::= { bgs10X25CircuitEntry 17}

bgs10X25CircuitInterruptTimeouts	OBJECT-TYPE
	SYNTAX		Unsigned32
	MAX-ACCESS	read-create
	STATUS		current
	DESCRIPTION
		"."
	::= { bgs10X25CircuitEntry 18}

bgs10X25CircuitCallParamId	OBJECT-TYPE
	SYNTAX		UShort
	MAX-ACCESS	read-create
	STATUS		current
	DESCRIPTION
		"."
	::= { bgs10X25CircuitEntry 19}

bgs10X25CircuitCalledDteAddress	OBJECT-TYPE
	SYNTAX		X25Address
	MAX-ACCESS	read-create
	STATUS		current
	DESCRIPTION
		"."
	::= { bgs10X25CircuitEntry 20}

bgs10X25CircuitCallingDteAddress	OBJECT-TYPE
	SYNTAX		X25Address
	MAX-ACCESS	read-create
	STATUS		current
	DESCRIPTION
		"."
	::= { bgs10X25CircuitEntry 21}

bgs10X25CircuitOriginallyCalledAddress	OBJECT-TYPE
	SYNTAX		X25Address
	MAX-ACCESS	read-create
	STATUS		current
	DESCRIPTION
		"."
	::= { bgs10X25CircuitEntry 22}

-- struct_x25ClearedCircuitTable
bgs10X25ClearedCircuitTable	OBJECT-TYPE
	SYNTAX		SEQUENCE OF ZXB10X25ClearedCircuitEntry
	MAX-ACCESS	not-accessible
	STATUS		current
	DESCRIPTION
		"A list of Definition of Cleared Circuit Table entries."
	::= { bgs10X25 15}
	
bgs10X25ClearedCircuitEntry	OBJECT-TYPE
	SYNTAX		ZXB10X25ClearedCircuitEntry
	MAX-ACCESS	not-accessible
	STATUS		current
	DESCRIPTION
		"An entry in the table."
	AUGMENTS
      {	
    	x25ClearedCircuitEntry
	  }
	::= { bgs10X25ClearedCircuitTable 1}
	
ZXB10X25ClearedCircuitEntry ::=
	SEQUENCE {
		bgs10X25ClearedCircuitRowStatus				RowStatus
	}

bgs10X25ClearedCircuitRowStatus	OBJECT-TYPE
	SYNTAX		RowStatus
	MAX-ACCESS	read-create
	STATUS		current
	DESCRIPTION
		"."
	::= { bgs10X25ClearedCircuitEntry 1}

-- struct_x25CallParameterTable
bgs10X25CallParameterTable	OBJECT-TYPE
	SYNTAX		SEQUENCE OF ZXB10X25CallParameterEntry
	MAX-ACCESS	not-accessible
	STATUS		current
	DESCRIPTION
		"A list of Definition of Call Parameter Table entries."
	::= { bgs10X25 16}
	
bgs10X25CallParameterEntry	OBJECT-TYPE
	SYNTAX		ZXB10X25CallParameterEntry
	MAX-ACCESS	not-accessible
	STATUS		current
	DESCRIPTION
		"An entry in the table."
	INDEX
      {	
    	bgs10X25CallParameterLinkno
	  }
	::= { bgs10X25CallParameterTable 1}
	
ZXB10X25CallParameterEntry ::=
	SEQUENCE {
		bgs10X25CallParameterRowStatus				RowStatus,
        bgs10X25CallParmIndex						UShort,
        bgs10X25CallParmRefCount					UShort,
        bgs10X25CallParmInPacketSize				UShort,
        bgs10X25CallParmOutPacketSize				UShort,
        bgs10X25CallParmInWindowSize				UShort,
        bgs10X25CallParmOutWindowSize				UShort,
        bgs10X25CallParmAcceptReverseCharging		UCHAR,
        bgs10X25CallParmProposeReverseCharging		UCHAR,
        bgs10X25CallParmFastSelect					UCHAR,
        bgs10X25CallParmInThruPutClasSize			UShort,
        bgs10X25CallParmOutThruPutClasSize			UShort,
        bgs10X25CallParmCug							OCTET STRING,
        bgs10X25CallParmCugoa						OCTET STRING,
        bgs10X25CallParmBcug						OCTET STRING,
        bgs10X25CallParmNui							OCTET STRING,
        bgs10X25CallParmChargingInfo				UCHAR,
        bgs10X25CallParmTrnstDly					Unsigned32,
        bgs10X25CallParmCallingExt					OCTET STRING,
        bgs10X25CallParmCalledExt					OCTET STRING,
        bgs10X25CallParmInMinThuPutCls				UShort,
        bgs10X25CallParmOutMinThuPutCls				UShort,
        bgs10X25CallParmEndTrnsDly					OCTET STRING,
        bgs10X25CallParmPriority					OCTET STRING,
        bgs10X25CallParmProtection					OCTET STRING,
        bgs10X25CallParmExptData					UCHAR,
        bgs10X25CallParmCallingNetworkFacilities	OCTET STRING,
        bgs10X25CallParmCalledNetworkFacilities		OCTET STRING,		
		bgs10X25CallParameterPktszNego				UCHAR,
		bgs10X25CallParameterPktsegAllow			UCHAR,
		bgs10X25CallParameterLinkno					UCHAR
	}

bgs10X25CallParameterRowStatus	OBJECT-TYPE
	SYNTAX		RowStatus
	MAX-ACCESS	read-create
	STATUS		current
	DESCRIPTION
		"."
	::= { bgs10X25CallParameterEntry 1}

bgs10X25CallParmIndex	OBJECT-TYPE
	SYNTAX		UShort
	MAX-ACCESS	read-create
	STATUS		current
	DESCRIPTION
		"."
	::= { bgs10X25CallParameterEntry 2}

bgs10X25CallParmRefCount	OBJECT-TYPE
	SYNTAX		UShort
	MAX-ACCESS	read-create
	STATUS		current
	DESCRIPTION
		"."
	::= { bgs10X25CallParameterEntry 3}

bgs10X25CallParmInPacketSize	OBJECT-TYPE
	SYNTAX		UShort
	MAX-ACCESS	read-create
	STATUS		current
	DESCRIPTION
		"."
	::= { bgs10X25CallParameterEntry 4}

bgs10X25CallParmOutPacketSize	OBJECT-TYPE
	SYNTAX		UShort
	MAX-ACCESS	read-create
	STATUS		current
	DESCRIPTION
		"."
	::= { bgs10X25CallParameterEntry 5}

bgs10X25CallParmInWindowSize	OBJECT-TYPE
	SYNTAX		UShort
	MAX-ACCESS	read-create
	STATUS		current
	DESCRIPTION
		"."
	::= { bgs10X25CallParameterEntry 6}

bgs10X25CallParmOutWindowSize	OBJECT-TYPE
	SYNTAX		UShort
	MAX-ACCESS	read-create
	STATUS		current
	DESCRIPTION
		"."
	::= { bgs10X25CallParameterEntry 7}

bgs10X25CallParmAcceptReverseCharging	OBJECT-TYPE
	SYNTAX		UCHAR
	MAX-ACCESS	read-create
	STATUS		current
	DESCRIPTION
		"."
	::= { bgs10X25CallParameterEntry 8}

bgs10X25CallParmProposeReverseCharging	OBJECT-TYPE
	SYNTAX		UCHAR
	MAX-ACCESS	read-create
	STATUS		current
	DESCRIPTION
		"."
	::= { bgs10X25CallParameterEntry 9}

bgs10X25CallParmFastSelect	OBJECT-TYPE
	SYNTAX		UCHAR
	MAX-ACCESS	read-create
	STATUS		current
	DESCRIPTION
		"."
	::= { bgs10X25CallParameterEntry 10}

bgs10X25CallParmInThruPutClasSize	OBJECT-TYPE
	SYNTAX		UShort
	MAX-ACCESS	read-create
	STATUS		current
	DESCRIPTION
		"."
	::= { bgs10X25CallParameterEntry 11}

bgs10X25CallParmOutThruPutClasSize	OBJECT-TYPE
	SYNTAX		UShort
	MAX-ACCESS	read-create
	STATUS		current
	DESCRIPTION
		"."
	::= { bgs10X25CallParameterEntry 12}

bgs10X25CallParmCug	OBJECT-TYPE
	SYNTAX		OCTET STRING(SIZE(0..3))
	MAX-ACCESS	read-create
	STATUS		current
	DESCRIPTION
		"."
	::= { bgs10X25CallParameterEntry 13}

bgs10X25CallParmCugoa	OBJECT-TYPE
	SYNTAX		OCTET STRING(SIZE(0..3))
	MAX-ACCESS	read-create
	STATUS		current
	DESCRIPTION
		"."
	::= { bgs10X25CallParameterEntry 14}

bgs10X25CallParmBcug	OBJECT-TYPE
	SYNTAX		OCTET STRING(SIZE(0..2))
	MAX-ACCESS	read-create
	STATUS		current
	DESCRIPTION
		"."
	::= { bgs10X25CallParameterEntry 15}

bgs10X25CallParmNui	OBJECT-TYPE
	SYNTAX		OCTET STRING(SIZE(0..107))
	MAX-ACCESS	read-create
	STATUS		current
	DESCRIPTION
		"."
	::= { bgs10X25CallParameterEntry 16}

bgs10X25CallParmChargingInfo	OBJECT-TYPE
	SYNTAX		UCHAR
	MAX-ACCESS	read-create
	STATUS		current
	DESCRIPTION
		"."
	::= { bgs10X25CallParameterEntry 17}

bgs10X25CallParmTrnstDly	OBJECT-TYPE
	SYNTAX		Unsigned32
	MAX-ACCESS	read-create
	STATUS		current
	DESCRIPTION
		"."
	::= { bgs10X25CallParameterEntry 18}

bgs10X25CallParmCallingExt	OBJECT-TYPE
	SYNTAX		OCTET STRING(SIZE(0..39))
	MAX-ACCESS	read-create
	STATUS		current
	DESCRIPTION
		"."
	::= { bgs10X25CallParameterEntry 19}

bgs10X25CallParmCalledExt	OBJECT-TYPE
	SYNTAX		OCTET STRING(SIZE(0..39))
	MAX-ACCESS	read-create
	STATUS		current
	DESCRIPTION
		"."
	::= { bgs10X25CallParameterEntry 20}

bgs10X25CallParmInMinThuPutCls	OBJECT-TYPE
	SYNTAX		UShort
	MAX-ACCESS	read-create
	STATUS		current
	DESCRIPTION
		"."
	::= { bgs10X25CallParameterEntry 21}

bgs10X25CallParmOutMinThuPutCls	OBJECT-TYPE
	SYNTAX		UShort
	MAX-ACCESS	read-create
	STATUS		current
	DESCRIPTION
		"."
	::= { bgs10X25CallParameterEntry 22}

bgs10X25CallParmEndTrnsDly	OBJECT-TYPE
	SYNTAX		OCTET STRING(SIZE(0..5))
	MAX-ACCESS	read-create
	STATUS		current
	DESCRIPTION
		"."
	::= { bgs10X25CallParameterEntry 23}

bgs10X25CallParmPriority	OBJECT-TYPE
	SYNTAX		OCTET STRING(SIZE(0..5))
	MAX-ACCESS	read-create
	STATUS		current
	DESCRIPTION
		"."
	::= { bgs10X25CallParameterEntry 24}

bgs10X25CallParmProtection	OBJECT-TYPE
	SYNTAX		OCTET STRING(SIZE(0..107))
	MAX-ACCESS	read-create
	STATUS		current
	DESCRIPTION
		"."
	::= { bgs10X25CallParameterEntry 25}

bgs10X25CallParmExptData	OBJECT-TYPE
	SYNTAX		UCHAR
	MAX-ACCESS	read-create
	STATUS		current
	DESCRIPTION
		"."
	::= { bgs10X25CallParameterEntry 26}

bgs10X25CallParmCallingNetworkFacilities	OBJECT-TYPE
	SYNTAX		OCTET STRING(SIZE(0..107))
	MAX-ACCESS	read-create
	STATUS		current
	DESCRIPTION
		"."
	::= { bgs10X25CallParameterEntry 27}

bgs10X25CallParmCalledNetworkFacilities	OBJECT-TYPE
	SYNTAX		OCTET STRING(SIZE(0..107))
	MAX-ACCESS	read-create
	STATUS		current
	DESCRIPTION
		"."
	::= { bgs10X25CallParameterEntry 28}

bgs10X25CallParameterPktszNego	OBJECT-TYPE
	SYNTAX		UCHAR
	MAX-ACCESS	read-create
	STATUS		current
	DESCRIPTION
		"."
	::= { bgs10X25CallParameterEntry 29}

bgs10X25CallParameterPktsegAllow	OBJECT-TYPE
	SYNTAX		UCHAR
	MAX-ACCESS	read-create
	STATUS		current
	DESCRIPTION
		"."
	::= { bgs10X25CallParameterEntry 30}

bgs10X25CallParameterLinkno	OBJECT-TYPE
	SYNTAX		UCHAR
	MAX-ACCESS	read-create
	STATUS		current
	DESCRIPTION
		"."
	::= { bgs10X25CallParameterEntry 31}

-- struct_x25_terminal_netnumber
bgs10X25TerminalNetnumberConfigure	OBJECT IDENTIFIER ::= { bgs10X25 17}
	
bgs10X25TerminalNetnumberRowStatus	OBJECT-TYPE
	SYNTAX		UCHAR
	MAX-ACCESS	read-create
	STATUS		current
	DESCRIPTION
		"."
	::= { bgs10X25TerminalNetnumberConfigure 1 }

bgs10X25TerminalNetnumberAirBei	OBJECT-TYPE
	SYNTAX		X25Address
	MAX-ACCESS	read-create
	STATUS		current
	DESCRIPTION
		"."
	::= { bgs10X25TerminalNetnumberConfigure 2 }

bgs10X25TerminalNetnumberAirNan	OBJECT-TYPE
	SYNTAX		X25Address
	MAX-ACCESS	read-create
	STATUS		current
	DESCRIPTION
		"."
	::= { bgs10X25TerminalNetnumberConfigure 3 }

bgs10X25TerminalNetnumberAirJi	OBJECT-TYPE
	SYNTAX		X25Address
	MAX-ACCESS	read-create
	STATUS		current
	DESCRIPTION
		"."
	::= { bgs10X25TerminalNetnumberConfigure 4 }

bgs10X25TerminalNetnumberAirCheng	OBJECT-TYPE
	SYNTAX		X25Address
	MAX-ACCESS	read-create
	STATUS		current
	DESCRIPTION
		"."
	::= { bgs10X25TerminalNetnumberConfigure 5 }

bgs10X25TerminalNetnumberAirFu	OBJECT-TYPE
	SYNTAX		X25Address
	MAX-ACCESS	read-create
	STATUS		current
	DESCRIPTION
		"."
	::= { bgs10X25TerminalNetnumberConfigure 6 }

bgs10X25TerminalNetnumberAirShen	OBJECT-TYPE
	SYNTAX		X25Address
	MAX-ACCESS	read-create
	STATUS		current
	DESCRIPTION
		"."
	::= { bgs10X25TerminalNetnumberConfigure 7 }

bgs10X25TerminalNetnumberAirLan	OBJECT-TYPE
	SYNTAX		X25Address
	MAX-ACCESS	read-create
	STATUS		current
	DESCRIPTION
		"."
	::= { bgs10X25TerminalNetnumberConfigure 8 }

-- struct_x25_netmask
bgs10X25NetmaskConfigure	OBJECT IDENTIFIER ::= { bgs10X25 18}
	
bgs10X25NetmaskRowStatus	OBJECT-TYPE
	SYNTAX		UCHAR
	MAX-ACCESS	read-create
	STATUS		current
	DESCRIPTION
		"."
	::= { bgs10X25NetmaskConfigure 1 }

bgs10X25NetmaskNet1		OBJECT-TYPE
	SYNTAX		X25Address
	MAX-ACCESS	read-create
	STATUS		current
	DESCRIPTION
		"."
	::= { bgs10X25NetmaskConfigure 2 }

bgs10X25NetmaskNet2		OBJECT-TYPE
	SYNTAX		X25Address
	MAX-ACCESS	read-create
	STATUS		current
	DESCRIPTION
		"."
	::= { bgs10X25NetmaskConfigure 3 }

bgs10X25NetmaskNet3		OBJECT-TYPE
	SYNTAX		X25Address
	MAX-ACCESS	read-create
	STATUS		current
	DESCRIPTION
		"."
	::= { bgs10X25NetmaskConfigure 4 }

bgs10X25NetmaskNet4		OBJECT-TYPE
	SYNTAX		X25Address
	MAX-ACCESS	read-create
	STATUS		current
	DESCRIPTION
		"."
	::= { bgs10X25NetmaskConfigure 5 }

bgs10X25NetmaskNet5		OBJECT-TYPE
	SYNTAX		X25Address
	MAX-ACCESS	read-create
	STATUS		current
	DESCRIPTION
		"."
	::= { bgs10X25NetmaskConfigure 6 }

bgs10X25NetmaskNet6		OBJECT-TYPE
	SYNTAX		X25Address
	MAX-ACCESS	read-create
	STATUS		current
	DESCRIPTION
		"."
	::= { bgs10X25NetmaskConfigure 7 }
	
-- struct_X25BroadSourConfigTable
bgs10X25BroadSourConfigTable OBJECT-TYPE
	SYNTAX		SEQUENCE OF ZXB10X25BroadSourConfigEntry
	MAX-ACCESS	not-accessible
	STATUS		current
	DESCRIPTION
		"A list of Definition of BroadSource Table entries."
	::= { bgs10X25 19}
	
bgs10X25BroadSourConfigEntry	OBJECT-TYPE
	SYNTAX		ZXB10X25BroadSourConfigEntry
	MAX-ACCESS	not-accessible
	STATUS		current
	DESCRIPTION
		"An entry in the table."
	INDEX
      {	
    	bgs10X25BroadSourConfigModule,
    	bgs10X25BroadSourConfigPort
	  }
	::= { bgs10X25BroadSourConfigTable 1}
	
ZXB10X25BroadSourConfigEntry ::=
	SEQUENCE {
		bgs10X25BroadSourConfigRowStatus				RowStatus,
		bgs10X25BroadSourConfigModule					UCHAR,
		bgs10X25BroadSourConfigPort						UCHAR,
		bgs10X25BroadSourConfigVps1Vpi					UShort,
		bgs10X25BroadSourConfigVps1Vci					UShort,
		bgs10X25BroadSourConfigVps2Vpi					UShort,
		bgs10X25BroadSourConfigVps2Vci					UShort,
		bgs10X25BroadSourConfigVps3Vpi					UShort,
		bgs10X25BroadSourConfigVps3Vci					UShort,
		bgs10X25BroadSourConfigVps4Vpi					UShort,
		bgs10X25BroadSourConfigVps4Vci					UShort,
		bgs10X25BroadSourConfigVps5Vpi					UShort,
		bgs10X25BroadSourConfigVps5Vci					UShort,
		bgs10X25BroadSourConfigVps6Vpi					UShort,
		bgs10X25BroadSourConfigVps6Vci					UShort,
		bgs10X25BroadSourConfigVps7Vpi					UShort,
		bgs10X25BroadSourConfigVps7Vci					UShort,
		bgs10X25BroadSourConfigVps8Vpi					UShort,
		bgs10X25BroadSourConfigVps8Vci					UShort,
		bgs10X25BroadSourConfigLocal					OCTET STRING(SIZE(8))
	}

bgs10X25BroadSourConfigRowStatus	OBJECT-TYPE
	SYNTAX		RowStatus
	MAX-ACCESS	read-create
	STATUS		current
	DESCRIPTION
		"."
	::= { bgs10X25BroadSourConfigEntry 1}

bgs10X25BroadSourConfigModule	OBJECT-TYPE
	SYNTAX		UCHAR
	MAX-ACCESS	read-create
	STATUS		current
	DESCRIPTION
		"."
	::= { bgs10X25BroadSourConfigEntry 2}

bgs10X25BroadSourConfigPort	OBJECT-TYPE
	SYNTAX		UCHAR
	MAX-ACCESS	read-create
	STATUS		current
	DESCRIPTION
		"."
	::= { bgs10X25BroadSourConfigEntry 3}

bgs10X25BroadSourConfigVps1Vpi	OBJECT-TYPE
	SYNTAX		UShort
	MAX-ACCESS	read-create
	STATUS		current
	DESCRIPTION
		"."
	::= { bgs10X25BroadSourConfigEntry 4}
	
bgs10X25BroadSourConfigVps1Vci	OBJECT-TYPE
	SYNTAX		UShort
	MAX-ACCESS	read-create
	STATUS		current
	DESCRIPTION
		"."
	::= { bgs10X25BroadSourConfigEntry 5}

bgs10X25BroadSourConfigVps2Vpi	OBJECT-TYPE
	SYNTAX		UShort
	MAX-ACCESS	read-create
	STATUS		current
	DESCRIPTION
		"."
	::= { bgs10X25BroadSourConfigEntry 6}
	
bgs10X25BroadSourConfigVps2Vci	OBJECT-TYPE
	SYNTAX		UShort
	MAX-ACCESS	read-create
	STATUS		current
	DESCRIPTION
		"."
	::= { bgs10X25BroadSourConfigEntry 7}
	
bgs10X25BroadSourConfigVps3Vpi	OBJECT-TYPE
	SYNTAX		UShort
	MAX-ACCESS	read-create
	STATUS		current
	DESCRIPTION
		"."
	::= { bgs10X25BroadSourConfigEntry 8}
	
bgs10X25BroadSourConfigVps3Vci	OBJECT-TYPE
	SYNTAX		UShort
	MAX-ACCESS	read-create
	STATUS		current
	DESCRIPTION
		"."
	::= { bgs10X25BroadSourConfigEntry 9}

bgs10X25BroadSourConfigVps4Vpi	OBJECT-TYPE
	SYNTAX		UShort
	MAX-ACCESS	read-create
	STATUS		current
	DESCRIPTION
		"."
	::= { bgs10X25BroadSourConfigEntry 10}
	
bgs10X25BroadSourConfigVps4Vci	OBJECT-TYPE
	SYNTAX		UShort
	MAX-ACCESS	read-create
	STATUS		current
	DESCRIPTION
		"."
	::= { bgs10X25BroadSourConfigEntry 11}

bgs10X25BroadSourConfigVps5Vpi	OBJECT-TYPE
	SYNTAX		UShort
	MAX-ACCESS	read-create
	STATUS		current
	DESCRIPTION
		"."
	::= { bgs10X25BroadSourConfigEntry 12}
	
bgs10X25BroadSourConfigVps5Vci	OBJECT-TYPE
	SYNTAX		UShort
	MAX-ACCESS	read-create
	STATUS		current
	DESCRIPTION
		"."
	::= { bgs10X25BroadSourConfigEntry 13}

bgs10X25BroadSourConfigVps6Vpi	OBJECT-TYPE
	SYNTAX		UShort
	MAX-ACCESS	read-create
	STATUS		current
	DESCRIPTION
		"."
	::= { bgs10X25BroadSourConfigEntry 14}
	
bgs10X25BroadSourConfigVps6Vci	OBJECT-TYPE
	SYNTAX		UShort
	MAX-ACCESS	read-create
	STATUS		current
	DESCRIPTION
		"."
	::= { bgs10X25BroadSourConfigEntry 15}

bgs10X25BroadSourConfigVps7Vpi	OBJECT-TYPE
	SYNTAX		UShort
	MAX-ACCESS	read-create
	STATUS		current
	DESCRIPTION
		"."
	::= { bgs10X25BroadSourConfigEntry 16}
	
bgs10X25BroadSourConfigVps7Vci	OBJECT-TYPE
	SYNTAX		UShort
	MAX-ACCESS	read-create
	STATUS		current
	DESCRIPTION
		"."
	::= { bgs10X25BroadSourConfigEntry 17}

bgs10X25BroadSourConfigVps8Vpi	OBJECT-TYPE
	SYNTAX		UShort
	MAX-ACCESS	read-create
	STATUS		current
	DESCRIPTION
		"."
	::= { bgs10X25BroadSourConfigEntry 18}
	
bgs10X25BroadSourConfigVps8Vci	OBJECT-TYPE
	SYNTAX		UShort
	MAX-ACCESS	read-create
	STATUS		current
	DESCRIPTION
		"."
	::= { bgs10X25BroadSourConfigEntry 19}
	
bgs10X25BroadSourConfigLocal	OBJECT-TYPE
	SYNTAX		OCTET STRING(SIZE(8))
	MAX-ACCESS	read-create
	STATUS		current
	DESCRIPTION
		"."
	::= { bgs10X25BroadSourConfigEntry 20}

-- struct_X25BroadDestConfigTable
bgs10X25BroadDestConfigTable OBJECT-TYPE
	SYNTAX		SEQUENCE OF ZXB10X25BroadDestConfigEntry
	MAX-ACCESS	not-accessible
	STATUS		current
	DESCRIPTION
		"A list of Definition of BroadDestce Table entries."
	::= { bgs10X25 20}
	
bgs10X25BroadDestConfigEntry	OBJECT-TYPE
	SYNTAX		ZXB10X25BroadDestConfigEntry
	MAX-ACCESS	not-accessible
	STATUS		current
	DESCRIPTION
		"An entry in the table."
	INDEX
      {	
    	bgs10X25BroadDestConfigModule,
    	bgs10X25BroadDestConfigVpi,
    	bgs10X25BroadDestConfigVci
	  }
	::= { bgs10X25BroadDestConfigTable 1}
	
ZXB10X25BroadDestConfigEntry ::=
	SEQUENCE {
		bgs10X25BroadDestConfigRowStatus				RowStatus,
		bgs10X25BroadDestConfigModule					UCHAR,
		bgs10X25BroadDestConfigVpi						UShort,
		bgs10X25BroadDestConfigVci						UShort,
		bgs10X25BroadDestConfigVps1Vpi					UShort,
		bgs10X25BroadDestConfigVps1Vci					UShort,
		bgs10X25BroadDestConfigVps2Vpi					UShort,
		bgs10X25BroadDestConfigVps2Vci					UShort,
		bgs10X25BroadDestConfigVps3Vpi					UShort,
		bgs10X25BroadDestConfigVps3Vci					UShort,
		bgs10X25BroadDestConfigVps4Vpi					UShort,
		bgs10X25BroadDestConfigVps4Vci					UShort,
		bgs10X25BroadDestConfigVps5Vpi					UShort,
		bgs10X25BroadDestConfigVps5Vci					UShort,
		bgs10X25BroadDestConfigVps6Vpi					UShort,
		bgs10X25BroadDestConfigVps6Vci					UShort,
		bgs10X25BroadDestConfigVps7Vpi					UShort,
		bgs10X25BroadDestConfigVps7Vci					UShort,
		bgs10X25BroadDestConfigVps8Vpi					UShort,
		bgs10X25BroadDestConfigVps8Vci					UShort,
		bgs10X25BroadDestConfigLocal					OCTET STRING(SIZE(8))
	}

bgs10X25BroadDestConfigRowStatus	OBJECT-TYPE
	SYNTAX		RowStatus
	MAX-ACCESS	read-create
	STATUS		current
	DESCRIPTION
		"."
	::= { bgs10X25BroadDestConfigEntry 1}

bgs10X25BroadDestConfigModule	OBJECT-TYPE
	SYNTAX		UCHAR
	MAX-ACCESS	read-create
	STATUS		current
	DESCRIPTION
		"."
	::= { bgs10X25BroadDestConfigEntry 2}

bgs10X25BroadDestConfigVpi	OBJECT-TYPE
	SYNTAX		UShort
	MAX-ACCESS	read-create
	STATUS		current
	DESCRIPTION
		"."
	::= { bgs10X25BroadDestConfigEntry 3}

bgs10X25BroadDestConfigVci	OBJECT-TYPE
	SYNTAX		UShort
	MAX-ACCESS	read-create
	STATUS		current
	DESCRIPTION
		"."
	::= { bgs10X25BroadDestConfigEntry 4}

bgs10X25BroadDestConfigVps1Vpi	OBJECT-TYPE
	SYNTAX		UShort
	MAX-ACCESS	read-create
	STATUS		current
	DESCRIPTION
		"."
	::= { bgs10X25BroadDestConfigEntry 5}
	
bgs10X25BroadDestConfigVps1Vci	OBJECT-TYPE
	SYNTAX		UShort
	MAX-ACCESS	read-create
	STATUS		current
	DESCRIPTION
		"."
	::= { bgs10X25BroadDestConfigEntry 6}

bgs10X25BroadDestConfigVps2Vpi	OBJECT-TYPE
	SYNTAX		UShort
	MAX-ACCESS	read-create
	STATUS		current
	DESCRIPTION
		"."
	::= { bgs10X25BroadDestConfigEntry 7}
	
bgs10X25BroadDestConfigVps2Vci	OBJECT-TYPE
	SYNTAX		UShort
	MAX-ACCESS	read-create
	STATUS		current
	DESCRIPTION
		"."
	::= { bgs10X25BroadDestConfigEntry 8}
	
bgs10X25BroadDestConfigVps3Vpi	OBJECT-TYPE
	SYNTAX		UShort
	MAX-ACCESS	read-create
	STATUS		current
	DESCRIPTION
		"."
	::= { bgs10X25BroadDestConfigEntry 9}
	
bgs10X25BroadDestConfigVps3Vci	OBJECT-TYPE
	SYNTAX		UShort
	MAX-ACCESS	read-create
	STATUS		current
	DESCRIPTION
		"."
	::= { bgs10X25BroadDestConfigEntry 10}

bgs10X25BroadDestConfigVps4Vpi	OBJECT-TYPE
	SYNTAX		UShort
	MAX-ACCESS	read-create
	STATUS		current
	DESCRIPTION
		"."
	::= { bgs10X25BroadDestConfigEntry 11}
	
bgs10X25BroadDestConfigVps4Vci	OBJECT-TYPE
	SYNTAX		UShort
	MAX-ACCESS	read-create
	STATUS		current
	DESCRIPTION
		"."
	::= { bgs10X25BroadDestConfigEntry 12}

bgs10X25BroadDestConfigVps5Vpi	OBJECT-TYPE
	SYNTAX		UShort
	MAX-ACCESS	read-create
	STATUS		current
	DESCRIPTION
		"."
	::= { bgs10X25BroadDestConfigEntry 13}
	
bgs10X25BroadDestConfigVps5Vci	OBJECT-TYPE
	SYNTAX		UShort
	MAX-ACCESS	read-create
	STATUS		current
	DESCRIPTION
		"."
	::= { bgs10X25BroadDestConfigEntry 14}

bgs10X25BroadDestConfigVps6Vpi	OBJECT-TYPE
	SYNTAX		UShort
	MAX-ACCESS	read-create
	STATUS		current
	DESCRIPTION
		"."
	::= { bgs10X25BroadDestConfigEntry 15}
	
bgs10X25BroadDestConfigVps6Vci	OBJECT-TYPE
	SYNTAX		UShort
	MAX-ACCESS	read-create
	STATUS		current
	DESCRIPTION
		"."
	::= { bgs10X25BroadDestConfigEntry 16}

bgs10X25BroadDestConfigVps7Vpi	OBJECT-TYPE
	SYNTAX		UShort
	MAX-ACCESS	read-create
	STATUS		current
	DESCRIPTION
		"."
	::= { bgs10X25BroadDestConfigEntry 17}
	
bgs10X25BroadDestConfigVps7Vci	OBJECT-TYPE
	SYNTAX		UShort
	MAX-ACCESS	read-create
	STATUS		current
	DESCRIPTION
		"."
	::= { bgs10X25BroadDestConfigEntry 18}

bgs10X25BroadDestConfigVps8Vpi	OBJECT-TYPE
	SYNTAX		UShort
	MAX-ACCESS	read-create
	STATUS		current
	DESCRIPTION
		"."
	::= { bgs10X25BroadDestConfigEntry 19}
	
bgs10X25BroadDestConfigVps8Vci	OBJECT-TYPE
	SYNTAX		UShort
	MAX-ACCESS	read-create
	STATUS		current
	DESCRIPTION
		"."
	::= { bgs10X25BroadDestConfigEntry 20}
	
bgs10X25BroadDestConfigLocal	OBJECT-TYPE
	SYNTAX		OCTET STRING(SIZE(8))
	MAX-ACCESS	read-create
	STATUS		current
	DESCRIPTION
		"."
	::= { bgs10X25BroadDestConfigEntry 21}

--The Signal Table
bgs10Signal		OBJECT IDENTIFIER	::= { zxbgs10mib 40 }

--The Signal Active Table
bgs10SignalActive		OBJECT IDENTIFIER ::= { bgs10Signal 1}

zxb10SigActiveRowStatus	OBJECT-TYPE
	SYNTAX		RowStatus
	MAX-ACCESS	read-write
	STATUS		current
	DESCRIPTION
		"."
	::= { bgs10SignalActive 1 }

zxb10SigActivebtModule	OBJECT-TYPE
	SYNTAX		UCHAR
	MAX-ACCESS	read-write
	STATUS		current
	DESCRIPTION
		"."
	::= { bgs10SignalActive 2 }
	
zxb10SigActivewLinkId	OBJECT-TYPE
	SYNTAX		UShort
	MAX-ACCESS	read-write
	STATUS		current
	DESCRIPTION
		"."
	::= { bgs10SignalActive 3 }
	
zxb10SigActivebtAddrId	OBJECT-TYPE
	SYNTAX		UCHAR
	MAX-ACCESS	read-write
	STATUS		current
	DESCRIPTION
		"."
	::= { bgs10SignalActive 4 }
	
zxb10SigActivebtMainAddrLen	OBJECT-TYPE
	SYNTAX		UCHAR
	MAX-ACCESS	read-write
	STATUS		current
	DESCRIPTION
		"."
	::= { bgs10SignalActive 5 }

zxb10SigActiveMainAddr	OBJECT-TYPE
	SYNTAX		OCTET STRING(SIZE(0..19))
	MAX-ACCESS	read-write
	STATUS		current
	DESCRIPTION
		"."
	::= { bgs10SignalActive 6 }
		
zxb10SigActivebtSubAddrLen	OBJECT-TYPE
	SYNTAX		UCHAR
	MAX-ACCESS	read-write
	STATUS		current
	DESCRIPTION
		"."
	::= { bgs10SignalActive 7 }

zxb10SigActiveSubAddr	OBJECT-TYPE
	SYNTAX		OCTET STRING(SIZE(0..19))
	MAX-ACCESS	read-write
	STATUS		current
	DESCRIPTION
		"."
	::= { bgs10SignalActive 8 }
		
zxb10SigActiveCallingActive	OBJECT-TYPE
	SYNTAX		UCHAR
	MAX-ACCESS	read-write
	STATUS		current
	DESCRIPTION
		"."
	::= { bgs10SignalActive 9 }

zxb10SigActiveCalledActive	OBJECT-TYPE
	SYNTAX		UCHAR
	MAX-ACCESS	read-write
	STATUS		current
	DESCRIPTION
		"."
	::= { bgs10SignalActive 10 }

zxb10SigActiveLinkActive	OBJECT-TYPE
	SYNTAX		UCHAR
	MAX-ACCESS	read-write
	STATUS		current
	DESCRIPTION
		"."
	::= { bgs10SignalActive 11 }

zxb10SigActiveContrlActive	OBJECT-TYPE
	SYNTAX		UCHAR
	MAX-ACCESS	read-write
	STATUS		current
	DESCRIPTION
		"."
	::= { bgs10SignalActive 12 }

zxb10SigActiveSigConfigActive	OBJECT-TYPE
	SYNTAX		UCHAR
	MAX-ACCESS	read-write
	STATUS		current
	DESCRIPTION
		"."
	::= { bgs10SignalActive 13 }

zxb10SigSigMaaActive	OBJECT-TYPE
	SYNTAX		UCHAR
	MAX-ACCESS	read-write
	STATUS		current
	DESCRIPTION
		"."
	::= { bgs10SignalActive 14 }

zxb10SigActiveSigAlarmActive	OBJECT-TYPE
	SYNTAX		UCHAR
	MAX-ACCESS	read-write
	STATUS		current
	DESCRIPTION
		"."
	::= { bgs10SignalActive 15 }

--The Trans Package Head Table
bgs10SignalTransPackageHead		OBJECT IDENTIFIER ::= { bgs10Signal 2}

zxb10SigTransPackageHeadbtModule	OBJECT-TYPE
	SYNTAX		UCHAR
	MAX-ACCESS	read-write
	STATUS		current
	DESCRIPTION
		"."
	::= { bgs10SignalTransPackageHead 1 }

zxb10SigTransPackageHeadbtTransId	OBJECT-TYPE
	SYNTAX		UCHAR
	MAX-ACCESS	read-write
	STATUS		current
	DESCRIPTION
		"."
	::= { bgs10SignalTransPackageHead 2 }

zxb10SigTransPackageHeadwPackageLen	OBJECT-TYPE
	SYNTAX		UShort
	MAX-ACCESS	read-write
	STATUS		current
	DESCRIPTION
		"."
	::= { bgs10SignalTransPackageHead 3 }

--The SigConfig Table
bgs10SignalConfig		OBJECT IDENTIFIER ::= { bgs10Signal 3}

zxb10SigConfigbtModule	OBJECT-TYPE
	SYNTAX		UCHAR
	MAX-ACCESS	read-write
	STATUS		current
	DESCRIPTION
		"."
	::= { bgs10SignalConfig 1 }

zxb10SigConfigwLnkId	OBJECT-TYPE
	SYNTAX		UShort
	MAX-ACCESS	read-write
	STATUS		current
	DESCRIPTION
		"."
	::= { bgs10SignalConfig 2 }

zxb10SigConfigwSarVpi	OBJECT-TYPE
	SYNTAX		UShort
	MAX-ACCESS	read-write
	STATUS		current
	DESCRIPTION
		"."
	::= { bgs10SignalConfig 3 }

zxb10SigConfigwSarVci	OBJECT-TYPE
	SYNTAX		UShort
	MAX-ACCESS	read-write
	STATUS		current
	DESCRIPTION
		"."
	::= { bgs10SignalConfig 4 }

zxb10SigConfigbtInitialized	OBJECT-TYPE
	SYNTAX		UCHAR
	MAX-ACCESS	read-write
	STATUS		current
	DESCRIPTION
		"."
	::= { bgs10SignalConfig 5 }

zxb10SigConfigwTransRate	OBJECT-TYPE
	SYNTAX		UShort
	MAX-ACCESS	read-write
	STATUS		current
	DESCRIPTION
		"."
	::= { bgs10SignalConfig 6 }

zxb10SigConfigbtMaxCredit	OBJECT-TYPE
	SYNTAX		UCHAR
	MAX-ACCESS	read-write
	STATUS		current
	DESCRIPTION
		"."
	::= { bgs10SignalConfig 7 }

zxb10SigConfigbtPollAfterRetrans	OBJECT-TYPE
	SYNTAX		UCHAR
	MAX-ACCESS	read-write
	STATUS		current
	DESCRIPTION
		"."
	::= { bgs10SignalConfig 8 }

zxb10SigConfigbtMaxCC	OBJECT-TYPE
	SYNTAX		UCHAR
	MAX-ACCESS	read-write
	STATUS		current
	DESCRIPTION
		"."
	::= { bgs10SignalConfig 9 }

zxb10SigConfigbtMaxSTAT	OBJECT-TYPE
	SYNTAX		UCHAR
	MAX-ACCESS	read-write
	STATUS		current
	DESCRIPTION
		"."
	::= { bgs10SignalConfig 10 }

zxb10SigConfigbtMaxPD	OBJECT-TYPE
	SYNTAX		UCHAR
	MAX-ACCESS	read-write
	STATUS		current
	DESCRIPTION
		"."
	::= { bgs10SignalConfig 11 }

zxb10SigConfigwMaxMu	OBJECT-TYPE
	SYNTAX		UShort
	MAX-ACCESS	read-write
	STATUS		current
	DESCRIPTION
		"."
	::= { bgs10SignalConfig 12 }

zxb10SigConfigwMaxUu	OBJECT-TYPE
	SYNTAX		UShort
	MAX-ACCESS	read-write
	STATUS		current
	DESCRIPTION
		"."
	::= { bgs10SignalConfig 13 }

zxb10SigConfigwTmrValue1	OBJECT-TYPE
	SYNTAX		UShort
	MAX-ACCESS	read-write
	STATUS		current
	DESCRIPTION
		"."
	::= { bgs10SignalConfig 14 }

zxb10SigConfigwTmrValue2	OBJECT-TYPE
	SYNTAX		UShort
	MAX-ACCESS	read-write
	STATUS		current
	DESCRIPTION
		"."
	::= { bgs10SignalConfig 15 }

zxb10SigConfigwTmrValue3	OBJECT-TYPE
	SYNTAX		UShort
	MAX-ACCESS	read-write
	STATUS		current
	DESCRIPTION
		"."
	::= { bgs10SignalConfig 16 }

zxb10SigConfigwTmrValue4	OBJECT-TYPE
	SYNTAX		UShort
	MAX-ACCESS	read-write
	STATUS		current
	DESCRIPTION
		"."
	::= { bgs10SignalConfig 17 }

zxb10SigConfigwTmrValue5	OBJECT-TYPE
	SYNTAX		UShort
	MAX-ACCESS	read-write
	STATUS		current
	DESCRIPTION
		"."
	::= { bgs10SignalConfig 18 }

--The SigMaa Table
bgs10SignalMaa		OBJECT IDENTIFIER ::= { bgs10Signal 4}

zxb10SigMaabtModule	OBJECT-TYPE
	SYNTAX		UCHAR
	MAX-ACCESS	read-write
	STATUS		current
	DESCRIPTION
		"."
	::= { bgs10SignalMaa 1 }

zxb10SigMaawLinkId	OBJECT-TYPE
	SYNTAX		UShort
	MAX-ACCESS	read-write
	STATUS		current
	DESCRIPTION
		"."
	::= { bgs10SignalMaa 2 }

zxb10SigMaabtErrorCode	OBJECT-TYPE
	SYNTAX		UCHAR
	MAX-ACCESS	read-write
	STATUS		current
	DESCRIPTION
		"."
	::= { bgs10SignalMaa 3 }

zxb10SigMaawCount	OBJECT-TYPE
	SYNTAX		UShort
	MAX-ACCESS	read-write
	STATUS		current
	DESCRIPTION
		"."
	::= { bgs10SignalMaa 4 }

--The SigMaa Table
bgs10SignalAlarm		OBJECT IDENTIFIER ::= { bgs10Signal 5}

zxb10SigAlarmbtModule	OBJECT-TYPE
	SYNTAX		UCHAR
	MAX-ACCESS	read-write
	STATUS		current
	DESCRIPTION
		"."
	::= { bgs10SignalAlarm 1 }

zxb10SigAlarmwLinkId	OBJECT-TYPE
	SYNTAX		UShort
	MAX-ACCESS	read-write
	STATUS		current
	DESCRIPTION
		"."
	::= { bgs10SignalAlarm 2 }

zxb10SigAlarmbtAlarmType	OBJECT-TYPE
	SYNTAX		UCHAR
	MAX-ACCESS	read-write
	STATUS		current
	DESCRIPTION
		"."
	::= { bgs10SignalAlarm 3 }

-- struct_ipoaifTable
bgs10IPOATable	OBJECT-TYPE
	SYNTAX		SEQUENCE OF ZXB10IPOAEntry
	MAX-ACCESS	not-accessible
	STATUS		current
	DESCRIPTION
		"."
	::= { zxbgs10mib 41}
	
bgs10IPOAEntry	OBJECT-TYPE
	SYNTAX		ZXB10IPOAEntry
	MAX-ACCESS	not-accessible
	STATUS		current
	DESCRIPTION
		"An entry in the table."
	INDEX
      {	
    	bgs10IPOAModule,
    	bgs10IPOAIfindex
	  }
	::= { bgs10IPOATable 1}
	
ZXB10IPOAEntry ::=
	SEQUENCE {
		bgs10IPOARowStatus				RowStatus,
        bgs10IPOAModule					UCHAR,
        bgs10IPOAIfindex				UCHAR,
        bgs10IPOAState					UCHAR,
        bgs10IPOAIpAddr					Unsigned32,
        bgs10IPOAMask					Unsigned32,
        bgs10IPOAHwtype					UCHAR,
        bgs10IPOANiHa					OCTET STRING,
        bgs10IPOANiHb					OCTET STRING,
        bgs10IPOAVpi					UShort,
        bgs10IPOAVci					UShort
	}

bgs10IPOARowStatus	OBJECT-TYPE
	SYNTAX		RowStatus
	MAX-ACCESS	read-create
	STATUS		current
	DESCRIPTION
		"."
	::= { bgs10IPOAEntry 1}

bgs10IPOAModule	OBJECT-TYPE
	SYNTAX		UCHAR
	MAX-ACCESS	read-create
	STATUS		current
	DESCRIPTION
		"."
	::= { bgs10IPOAEntry 2}

bgs10IPOAIfindex	OBJECT-TYPE
	SYNTAX		UCHAR
	MAX-ACCESS	read-create
	STATUS		current
	DESCRIPTION
		"."
	::= { bgs10IPOAEntry 3}

bgs10IPOAState	OBJECT-TYPE
	SYNTAX		UCHAR
	MAX-ACCESS	read-create
	STATUS		current
	DESCRIPTION
		"."
	::= { bgs10IPOAEntry 4}

bgs10IPOAIpAddr	OBJECT-TYPE
	SYNTAX		Unsigned32
	MAX-ACCESS	read-create
	STATUS		current
	DESCRIPTION
		"."
	::= { bgs10IPOAEntry 5}

bgs10IPOAMask	OBJECT-TYPE
	SYNTAX		Unsigned32
	MAX-ACCESS	read-create
	STATUS		current
	DESCRIPTION
		"."
	::= { bgs10IPOAEntry 6}

bgs10IPOAHwtype	OBJECT-TYPE
	SYNTAX		UCHAR
	MAX-ACCESS	read-create
	STATUS		current
	DESCRIPTION
		"."
	::= { bgs10IPOAEntry 7}

bgs10IPOANiHa	OBJECT-TYPE
	SYNTAX		OCTET STRING
	MAX-ACCESS	read-create
	STATUS		current
	DESCRIPTION
		"."
	::= { bgs10IPOAEntry 8}

bgs10IPOANiHb	OBJECT-TYPE
	SYNTAX		OCTET STRING
	MAX-ACCESS	read-create
	STATUS		current
	DESCRIPTION
		"."
	::= { bgs10IPOAEntry 9}

bgs10IPOAVpi	OBJECT-TYPE
	SYNTAX		UShort
	MAX-ACCESS	read-create
	STATUS		current
	DESCRIPTION
		"."
	::= { bgs10IPOAEntry 10}

bgs10IPOAVci	OBJECT-TYPE
	SYNTAX		UShort
	MAX-ACCESS	read-create
	STATUS		current
	DESCRIPTION
		"."
	::= { bgs10IPOAEntry 11}

--the Mpls table 
bgs10Mpls				OBJECT IDENTIFIER	::= { zxbgs10mib 42}
        
-- Ldp_Lsr
bgs10MplsLdpLsrTable	OBJECT-TYPE
	SYNTAX		SEQUENCE OF ZXB10MplsLdpLsrEntry
	MAX-ACCESS	not-accessible
	STATUS		current
	DESCRIPTION
		"A list of Definition of MPLS LDP LSR Table entries."
	::= { bgs10Mpls 1}
	
bgs10MplsLdpLsrEntry	OBJECT-TYPE
	SYNTAX		ZXB10MplsLdpLsrEntry
	MAX-ACCESS	not-accessible
	STATUS		current
	DESCRIPTION
		"An entry in the table."
	INDEX {	
		bgs10MplsLdpLsrID
		}
	::= { bgs10MplsLdpLsrTable 1}
	
ZXB10MplsLdpLsrEntry ::=
	SEQUENCE {
		bgs10MplsLdpLsrRowStatus		RowStatus,	
		bgs10MplsLdpLsrID			Unsigned32,
		bgs10MplsLdpLsrLabelRetentionMode	UCHAR,
		bgs10MplsLdpLsrLoopDetectionForPV	UCHAR,
		bgs10MplsLdpLsrPathVectorLimit		UCHAR,
		bgs10MplsLdpLsrEdgeId			UCHAR
	}

bgs10MplsLdpLsrRowStatus	OBJECT-TYPE
	SYNTAX		RowStatus
	MAX-ACCESS	read-create
	STATUS		current
	DESCRIPTION
		"."
	::= { bgs10MplsLdpLsrEntry 1}

bgs10MplsLdpLsrID	OBJECT-TYPE
	SYNTAX		Unsigned32
	MAX-ACCESS	read-create
	STATUS		current
	DESCRIPTION
		"."
	::= { bgs10MplsLdpLsrEntry 2}

bgs10MplsLdpLsrLabelRetentionMode	OBJECT-TYPE
	SYNTAX		UCHAR
	MAX-ACCESS	read-create
	STATUS		current
	DESCRIPTION
		"."
	::= { bgs10MplsLdpLsrEntry 3}

bgs10MplsLdpLsrLoopDetectionForPV	OBJECT-TYPE
	SYNTAX		UCHAR
	MAX-ACCESS	read-create
	STATUS		current
	DESCRIPTION
		"."
	::= { bgs10MplsLdpLsrEntry 4}

bgs10MplsLdpLsrPathVectorLimit	OBJECT-TYPE
	SYNTAX		UCHAR
	MAX-ACCESS	read-create
	STATUS		current
	DESCRIPTION
		"."
	::= { bgs10MplsLdpLsrEntry 5}

bgs10MplsLdpLsrEdgeId	OBJECT-TYPE
	SYNTAX		UCHAR
	MAX-ACCESS	read-create
	STATUS		current
	DESCRIPTION
		"."
	::= { bgs10MplsLdpLsrEntry 6}

-- Ldp_Interface
bgs10MplsLdpInterfaceTable	OBJECT-TYPE
	SYNTAX		SEQUENCE OF ZXB10MplsLdpInterfaceEntry
	MAX-ACCESS	not-accessible
	STATUS		current
	DESCRIPTION
		"A list of Definition of MPLS LDP Interface Table entries."
	::= { bgs10Mpls 2}
	
bgs10MplsLdpInterfaceEntry	OBJECT-TYPE
	SYNTAX		ZXB10MplsLdpInterfaceEntry
	MAX-ACCESS	not-accessible
	STATUS		current
	DESCRIPTION
		"An entry in the table."
	INDEX {	
		bgs10MplsLdpInterfaceIfindex
		}
	::= { bgs10MplsLdpInterfaceTable 1}
	
ZXB10MplsLdpInterfaceEntry ::=
	SEQUENCE {
		bgs10MplsLdpInterfaceRowStatus			RowStatus,	
		bgs10MplsLdpInterfaceIfindex			UShort,
		bgs10MplsLdpInterfaceIfIpAddress		Unsigned32,
		bgs10MplsLdpInterfaceLsrAddress			Unsigned32,
		bgs10MplsLdpInterfaceLabelSpace			UShort,
		bgs10MplsLdpInterfaceMinVpi				UShort,
		bgs10MplsLdpInterfaceMinVci				UShort,
		bgs10MplsLdpInterfaceMaxVpi				UShort,
		bgs10MplsLdpInterfaceMaxVci				UShort,
		bgs10MplsLdpInterfaceAdminStatus		UCHAR,
		bgs10MplsLdpInterfaceOperStatus			UCHAR		
	}

bgs10MplsLdpInterfaceRowStatus	OBJECT-TYPE
	SYNTAX		RowStatus
	MAX-ACCESS	read-create
	STATUS		current
	DESCRIPTION
		"."
	::= { bgs10MplsLdpInterfaceEntry 1}

bgs10MplsLdpInterfaceIfindex	OBJECT-TYPE
	SYNTAX		UShort
	MAX-ACCESS	read-create
	STATUS		current
	DESCRIPTION
		"."
	::= { bgs10MplsLdpInterfaceEntry 2}
	
bgs10MplsLdpInterfaceIfIpAddress	OBJECT-TYPE
	SYNTAX		Unsigned32
	MAX-ACCESS	read-create
	STATUS		current
	DESCRIPTION
		"."
	::= { bgs10MplsLdpInterfaceEntry 3}

bgs10MplsLdpInterfaceLsrAddress	OBJECT-TYPE
	SYNTAX		Unsigned32
	MAX-ACCESS	read-create
	STATUS		current
	DESCRIPTION
		"."
	::= { bgs10MplsLdpInterfaceEntry 4}

bgs10MplsLdpInterfaceLabelSpace	OBJECT-TYPE
	SYNTAX		UShort
	MAX-ACCESS	read-create
	STATUS		current
	DESCRIPTION
		"."
	::= { bgs10MplsLdpInterfaceEntry 5}

bgs10MplsLdpInterfaceMinVpi	OBJECT-TYPE
	SYNTAX		UShort
	MAX-ACCESS	read-create
	STATUS		current
	DESCRIPTION
		"."
	::= { bgs10MplsLdpInterfaceEntry 6}

bgs10MplsLdpInterfaceMinVci	OBJECT-TYPE
	SYNTAX		UShort
	MAX-ACCESS	read-create
	STATUS		current
	DESCRIPTION
		"."
	::= { bgs10MplsLdpInterfaceEntry 7}

bgs10MplsLdpInterfaceMaxVpi	OBJECT-TYPE
	SYNTAX		UShort
	MAX-ACCESS	read-create
	STATUS		current
	DESCRIPTION
		"."
	::= { bgs10MplsLdpInterfaceEntry 8}

bgs10MplsLdpInterfaceMaxVci	OBJECT-TYPE
	SYNTAX		UShort
	MAX-ACCESS	read-create
	STATUS		current
	DESCRIPTION
		"."
	::= { bgs10MplsLdpInterfaceEntry 9}

bgs10MplsLdpInterfaceAdminStatus	OBJECT-TYPE
	SYNTAX		UCHAR
	MAX-ACCESS	read-create
	STATUS		current
	DESCRIPTION
		"."
	::= { bgs10MplsLdpInterfaceEntry 10}

bgs10MplsLdpInterfaceOperStatus	OBJECT-TYPE
	SYNTAX		UCHAR
	MAX-ACCESS	read-create
	STATUS		current
	DESCRIPTION
		"."
	::= { bgs10MplsLdpInterfaceEntry 11}

-- Ldp_Entity
bgs10MplsLdpEntityTable	OBJECT-TYPE
	SYNTAX		SEQUENCE OF ZXB10MplsLdpEntityEntry
	MAX-ACCESS	not-accessible
	STATUS		current
	DESCRIPTION
		"A list of Definition of MPLS LDP Entity Table entries."
	::= { bgs10Mpls 3}
	
bgs10MplsLdpEntityEntry	OBJECT-TYPE
	SYNTAX		ZXB10MplsLdpEntityEntry
	MAX-ACCESS	not-accessible
	STATUS		current
	DESCRIPTION
		"An entry in the table."
	INDEX {	
		bgs10MplsLdpEntityLsrAddress,
		bgs10MplsLdpEntityLabelSpace
		}
	::= { bgs10MplsLdpEntityTable 1}
	
ZXB10MplsLdpEntityEntry ::=
	SEQUENCE {
		bgs10MplsLdpEntityRowStatus				RowStatus,	
		bgs10MplsLdpEntityIndex					Unsigned32,
		bgs10MplsLdpEntityLsrAddress				Unsigned32,
		bgs10MplsLdpEntityLabelSpace				UShort,
		bgs10MplsLdpEntityProtocolVersion			UCHAR,
		bgs10MplsLdpEntityAdminStatus				UCHAR,
		bgs10MplsLdpEntityOperStatus				UCHAR,
		bgs10MplsLdpEntityWellKnownDiscoveryPort		UShort,
		bgs10MplsLdpEntityMaxPduLength				UShort,
		bgs10MplsLdpEntitykeepAliveHoldTimer			Unsigned32,
		bgs10MplsLdpEntityHelloHoldTimer			Unsigned32,
		bgs10MplsLdpEntityFailedInitSessionThreshold		Unsigned32,
		bgs10MplsLdpEntityLabelDistributionMethod		UCHAR,
		bgs10MplsLdpEntityTargetedPeer				UCHAR,
		bgs10MplsLdpEntityTargetedPeerAddrType			UShort,
		bgs10MplsLdpEntityTargetedPeerAddr			Unsigned32,
		bgs10MplsLdpEntityOptionalParameters			UCHAR,
		bgs10MplsLdpEntityAtmMergeCap				UCHAR,
		bgs10MplsLdpEntityAtmVcDirectionality			UCHAR,
		bgs10MplsLdpEntityAtmLsrConnectivity			UCHAR,
		bgs10MplsLdpEntityDefaultControlVpi			UShort,
		bgs10MplsLdpEntityDefaultControlVci			UShort,
		bgs10MplsLdpEntityUnlabTrafVpi				UShort,
		bgs10MplsLdpEntityUnlabTrafVci				UShort,
		bgs10MplsLdpEntityIfArray					UShort,
		bgs10MplsLdpEntityIfNumber					UCHAR
	}

bgs10MplsLdpEntityRowStatus	OBJECT-TYPE
	SYNTAX		RowStatus
	MAX-ACCESS	read-create
	STATUS		current
	DESCRIPTION
		"."
	::= { bgs10MplsLdpEntityEntry 1}

bgs10MplsLdpEntityIndex	OBJECT-TYPE
	SYNTAX		Unsigned32
	MAX-ACCESS	read-create
	STATUS		current
	DESCRIPTION
		"."
	::= { bgs10MplsLdpEntityEntry 2}

bgs10MplsLdpEntityLsrAddress	OBJECT-TYPE
	SYNTAX		Unsigned32
	MAX-ACCESS	read-create
	STATUS		current
	DESCRIPTION
		"."
	::= { bgs10MplsLdpEntityEntry 3}

bgs10MplsLdpEntityLabelSpace	OBJECT-TYPE
	SYNTAX		UShort
	MAX-ACCESS	read-create
	STATUS		current
	DESCRIPTION
		"."
	::= { bgs10MplsLdpEntityEntry 4}

bgs10MplsLdpEntityProtocolVersion	OBJECT-TYPE
	SYNTAX		UCHAR
	MAX-ACCESS	read-create
	STATUS		current
	DESCRIPTION
		"."
	::= { bgs10MplsLdpEntityEntry 5}

bgs10MplsLdpEntityAdminStatus	OBJECT-TYPE
	SYNTAX		UCHAR
	MAX-ACCESS	read-create
	STATUS		current
	DESCRIPTION
		"."
	::= { bgs10MplsLdpEntityEntry 6}

bgs10MplsLdpEntityOperStatus	OBJECT-TYPE
	SYNTAX		UCHAR
	MAX-ACCESS	read-create
	STATUS		current
	DESCRIPTION
		"."
	::= { bgs10MplsLdpEntityEntry 7}

bgs10MplsLdpEntityWellKnownDiscoveryPort	OBJECT-TYPE
	SYNTAX		UShort
	MAX-ACCESS	read-create
	STATUS		current
	DESCRIPTION
		"."
	::= { bgs10MplsLdpEntityEntry 8}

bgs10MplsLdpEntityMaxPduLength	OBJECT-TYPE
	SYNTAX		UShort
	MAX-ACCESS	read-create
	STATUS		current
	DESCRIPTION
		"."
	::= { bgs10MplsLdpEntityEntry 9}

bgs10MplsLdpEntitykeepAliveHoldTimer	OBJECT-TYPE
	SYNTAX		Unsigned32
	MAX-ACCESS	read-create
	STATUS		current
	DESCRIPTION
		"."
	::= { bgs10MplsLdpEntityEntry 10}

bgs10MplsLdpEntityHelloHoldTimer	OBJECT-TYPE
	SYNTAX		Unsigned32
	MAX-ACCESS	read-create
	STATUS		current
	DESCRIPTION
		"."
	::= { bgs10MplsLdpEntityEntry 11}

bgs10MplsLdpEntityFailedInitSessionThreshold	OBJECT-TYPE
	SYNTAX		Unsigned32
	MAX-ACCESS	read-create
	STATUS		current
	DESCRIPTION
		"."
	::= { bgs10MplsLdpEntityEntry 12}

bgs10MplsLdpEntityLabelDistributionMethod	OBJECT-TYPE
	SYNTAX		UCHAR
	MAX-ACCESS	read-create
	STATUS		current
	DESCRIPTION
		"."
	::= { bgs10MplsLdpEntityEntry 13}

bgs10MplsLdpEntityTargetedPeer	OBJECT-TYPE
	SYNTAX		UCHAR
	MAX-ACCESS	read-create
	STATUS		current
	DESCRIPTION
		"."
	::= { bgs10MplsLdpEntityEntry 14}

bgs10MplsLdpEntityTargetedPeerAddrType	OBJECT-TYPE
	SYNTAX		UShort
	MAX-ACCESS	read-create
	STATUS		current
	DESCRIPTION
		"."
	::= { bgs10MplsLdpEntityEntry 15}

bgs10MplsLdpEntityTargetedPeerAddr	OBJECT-TYPE
	SYNTAX		Unsigned32
	MAX-ACCESS	read-create
	STATUS		current
	DESCRIPTION
		"."
	::= { bgs10MplsLdpEntityEntry 16}

bgs10MplsLdpEntityOptionalParameters	OBJECT-TYPE
	SYNTAX		UCHAR
	MAX-ACCESS	read-create
	STATUS		current
	DESCRIPTION
		"."
	::= { bgs10MplsLdpEntityEntry 17}

bgs10MplsLdpEntityAtmMergeCap	OBJECT-TYPE
	SYNTAX		UCHAR
	MAX-ACCESS	read-create
	STATUS		current
	DESCRIPTION
		"."
	::= { bgs10MplsLdpEntityEntry 18}

bgs10MplsLdpEntityAtmVcDirectionality	OBJECT-TYPE
	SYNTAX		UCHAR
	MAX-ACCESS	read-create
	STATUS		current
	DESCRIPTION
		"."
	::= { bgs10MplsLdpEntityEntry 19}

bgs10MplsLdpEntityAtmLsrConnectivity	OBJECT-TYPE
	SYNTAX		UCHAR
	MAX-ACCESS	read-create
	STATUS		current
	DESCRIPTION
		"."
	::= { bgs10MplsLdpEntityEntry 20}

bgs10MplsLdpEntityDefaultControlVpi	OBJECT-TYPE
	SYNTAX		UShort
	MAX-ACCESS	read-create
	STATUS		current
	DESCRIPTION
		"."
	::= { bgs10MplsLdpEntityEntry 21}

bgs10MplsLdpEntityDefaultControlVci	OBJECT-TYPE
	SYNTAX		UShort
	MAX-ACCESS	read-create
	STATUS		current
	DESCRIPTION
		"."
	::= { bgs10MplsLdpEntityEntry 22}

bgs10MplsLdpEntityUnlabTrafVpi	OBJECT-TYPE
	SYNTAX		UShort
	MAX-ACCESS	read-create
	STATUS		current
	DESCRIPTION
		"."
	::= { bgs10MplsLdpEntityEntry 23}

bgs10MplsLdpEntityUnlabTrafVci	OBJECT-TYPE
	SYNTAX		UShort
	MAX-ACCESS	read-create
	STATUS		current
	DESCRIPTION
		"."
	::= { bgs10MplsLdpEntityEntry 24}
	
bgs10MplsLdpEntityIfArray	OBJECT-TYPE
	SYNTAX		UShort
	MAX-ACCESS	read-create
	STATUS		current
	DESCRIPTION
		"."
	::= { bgs10MplsLdpEntityEntry 25}
	
bgs10MplsLdpEntityIfNumber	OBJECT-TYPE
	SYNTAX		UCHAR
	MAX-ACCESS	read-create
	STATUS		current
	DESCRIPTION
		"."
	::= { bgs10MplsLdpEntityEntry 26}
	
-- Ldp_Erlsp
bgs10MplsErlspTable	OBJECT-TYPE
	SYNTAX		SEQUENCE OF ZXB10MplsErlspEntry
	MAX-ACCESS	not-accessible
	STATUS		current
	DESCRIPTION
		"A list of Definition of MPLS ER LSP Table entries."
	::= { bgs10Mpls 4}
	
bgs10MplsErlspEntry	OBJECT-TYPE
	SYNTAX		ZXB10MplsErlspEntry
	MAX-ACCESS	not-accessible
	STATUS		current
	DESCRIPTION
		"An entry in the table."
	INDEX {	
		bgs10MplsErlspIndex
		}
	::= { bgs10MplsErlspTable 1}
	
ZXB10MplsErlspEntry ::=
	SEQUENCE {
		bgs10MplsErlspRowStatus				RowStatus,	
		bgs10MplsErlspIndex					Unsigned32,
		bgs10MplsErlspNumberFecElements		UShort,
		bgs10MplsErlspWcElemExists			UCHAR,
		bgs10MplsErlspFecElemType			OCTET STRING(SIZE(40)),
		bgs10MplaErlspAddressFam			OCTET STRING(SIZE(40)),
		bgs10MplsErlspPreLen				OCTET STRING(SIZE(40)),
		bgs10MplsErlspFecAddress1			OCTET STRING(SIZE(40)),	
		bgs10MplsErlspFecAddress2			OCTET STRING(SIZE(40)),	
		bgs10MplsErlspFecAddress3			OCTET STRING(SIZE(40)),	
		bgs10MplsErlspFecAddress4			OCTET STRING(SIZE(40)),	
		bgs10MplsErlspFecAddress5			OCTET STRING(SIZE(40)),	
		bgs10MplsErlspNumberErHops			UShort,
		bgs10MplsErlspErHopType1			OCTET STRING(SIZE(40)),
		bgs10MplsErlspErHopType2			OCTET STRING(SIZE(40)),
		bgs10MplsErlspErFlag1				OCTET STRING(SIZE(40)),
		bgs10MplsErlspErFlag2				OCTET STRING(SIZE(40)),
		bgs10MplsErlspErFlag3				OCTET STRING(SIZE(40)),
		bgs10MplsErlspErFlag4				OCTET STRING(SIZE(40)),
		bgs10MplsErlspErFlag5				OCTET STRING(SIZE(40)),
		bgs10MplsErlspErAddress1			OCTET STRING(SIZE(40)),
		bgs10MplsErlspErAddress2			OCTET STRING(SIZE(40)),
		bgs10MplsErlspErAddress3			OCTET STRING(SIZE(40)),
		bgs10MplsErlspErAddress4			OCTET STRING(SIZE(40)),
		bgs10MplsErlspErAddress5			OCTET STRING(SIZE(40)),
    	bgs10MplsErlspFlag					UCHAR,
    	bgs10MplsErlspFreq					UCHAR,
    	bgs10MplsErlspWeight				UCHAR,
    	bgs10MplsErlspPdr					Unsigned32,
    	bgs10MplsErlspPbs					Unsigned32,
    	bgs10MplsErLspCdr					Unsigned32,
    	bgs10MplsErlspCbs					Unsigned32,
    	bgs10MplsErlspEbs					Unsigned32,
    	bgs10MplsErlspPinFlag				UCHAR,
    	bgs10MplsErlspRsCls					Unsigned32,
    	bgs10MplsErlspQosMark				UCHAR,
    	bgs10MplsErlspSetPrio				UCHAR,
    	bgs10MplsErlspHoldPrio				UCHAR,
    	bgs10MplsErlspTos					OCTET STRING(SIZE(10)),
    	bgs10MplsErlspPort					OCTET STRING(SIZE(10)),
    	bgs10MplsErlspQosNum				UCHAR
	}

bgs10MplsErlspRowStatus	OBJECT-TYPE
	SYNTAX		RowStatus
	MAX-ACCESS	read-create
	STATUS		current
	DESCRIPTION
		"."
	::= { bgs10MplsErlspEntry 1}

bgs10MplsErlspIndex	OBJECT-TYPE
	SYNTAX		Unsigned32
	MAX-ACCESS	read-create
	STATUS		current
	DESCRIPTION
		"."
	::= { bgs10MplsErlspEntry 2}

bgs10MplsErlspNumberFecElements	OBJECT-TYPE
	SYNTAX		UShort
	MAX-ACCESS	read-create
	STATUS		current
	DESCRIPTION
		"."
	::= { bgs10MplsErlspEntry 3}

bgs10MplsErlspWcElemExists	OBJECT-TYPE
	SYNTAX		UCHAR
	MAX-ACCESS	read-create
	STATUS		current
	DESCRIPTION
		"."
	::= { bgs10MplsErlspEntry 4}

bgs10MplsErlspFecElemType	OBJECT-TYPE
	SYNTAX		OCTET STRING(SIZE(40))
	MAX-ACCESS	read-create
	STATUS		current
	DESCRIPTION
		"."
	::= { bgs10MplsErlspEntry 5}

bgs10MplaErlspAddressFam	OBJECT-TYPE
	SYNTAX		OCTET STRING(SIZE(40))
	MAX-ACCESS	read-create
	STATUS		current
	DESCRIPTION
		"."
	::= { bgs10MplsErlspEntry 6}

bgs10MplsErlspPreLen	OBJECT-TYPE
	SYNTAX		OCTET STRING(SIZE(40))
	MAX-ACCESS	read-create
	STATUS		current
	DESCRIPTION
		"."
	::= { bgs10MplsErlspEntry 7}

bgs10MplsErlspFecAddress1	OBJECT-TYPE
	SYNTAX		OCTET STRING(SIZE(40))
	MAX-ACCESS	read-create
	STATUS		current
	DESCRIPTION
		"."
	::= { bgs10MplsErlspEntry 8}

bgs10MplsErlspFecAddress2	OBJECT-TYPE
	SYNTAX		OCTET STRING(SIZE(40))
	MAX-ACCESS	read-create
	STATUS		current
	DESCRIPTION
		"."
	::= { bgs10MplsErlspEntry 9}

bgs10MplsErlspFecAddress3	OBJECT-TYPE
	SYNTAX		OCTET STRING(SIZE(40))
	MAX-ACCESS	read-create
	STATUS		current
	DESCRIPTION
		"."
	::= { bgs10MplsErlspEntry 10}

bgs10MplsErlspFecAddress4	OBJECT-TYPE
	SYNTAX		OCTET STRING(SIZE(40))
	MAX-ACCESS	read-create
	STATUS		current
	DESCRIPTION
		"."
	::= { bgs10MplsErlspEntry 11}

bgs10MplsErlspFecAddress5	OBJECT-TYPE
	SYNTAX		OCTET STRING(SIZE(40))
	MAX-ACCESS	read-create
	STATUS		current
	DESCRIPTION
		"."
	::= { bgs10MplsErlspEntry 12}

bgs10MplsErlspNumberErHops	OBJECT-TYPE
	SYNTAX		UShort
	MAX-ACCESS	read-create
	STATUS		current
	DESCRIPTION
		"."
	::= { bgs10MplsErlspEntry 13}

bgs10MplsErlspErHopType1	OBJECT-TYPE
	SYNTAX		OCTET STRING(SIZE(40))
	MAX-ACCESS	read-create
	STATUS		current
	DESCRIPTION
		"."
	::= { bgs10MplsErlspEntry 14}

bgs10MplsErlspErHopType2	OBJECT-TYPE
	SYNTAX		OCTET STRING(SIZE(40))
	MAX-ACCESS	read-create
	STATUS		current
	DESCRIPTION
		"."
	::= { bgs10MplsErlspEntry 15}

bgs10MplsErlspErFlag1	OBJECT-TYPE
	SYNTAX		OCTET STRING(SIZE(40))
	MAX-ACCESS	read-create
	STATUS		current
	DESCRIPTION
		"."
	::= { bgs10MplsErlspEntry 16}

bgs10MplsErlspErFlag2	OBJECT-TYPE
	SYNTAX		OCTET STRING(SIZE(40))
	MAX-ACCESS	read-create
	STATUS		current
	DESCRIPTION
		"."
	::= { bgs10MplsErlspEntry 17}

bgs10MplsErlspErFlag3	OBJECT-TYPE
	SYNTAX		OCTET STRING(SIZE(40))
	MAX-ACCESS	read-create
	STATUS		current
	DESCRIPTION
		"."
	::= { bgs10MplsErlspEntry 18}

bgs10MplsErlspErFlag4	OBJECT-TYPE
	SYNTAX		OCTET STRING(SIZE(40))
	MAX-ACCESS	read-create
	STATUS		current
	DESCRIPTION
		"."
	::= { bgs10MplsErlspEntry 19}

bgs10MplsErlspErFlag5	OBJECT-TYPE
	SYNTAX		OCTET STRING(SIZE(40))
	MAX-ACCESS	read-create
	STATUS		current
	DESCRIPTION
		"."
	::= { bgs10MplsErlspEntry 20}

bgs10MplsErlspErAddress1	OBJECT-TYPE
	SYNTAX		OCTET STRING(SIZE(40))
	MAX-ACCESS	read-create
	STATUS		current
	DESCRIPTION
		"."
	::= { bgs10MplsErlspEntry 21}

bgs10MplsErlspErAddress2	OBJECT-TYPE
	SYNTAX		OCTET STRING(SIZE(40))
	MAX-ACCESS	read-create
	STATUS		current
	DESCRIPTION
		"."
	::= { bgs10MplsErlspEntry 22}

bgs10MplsErlspErAddress3	OBJECT-TYPE
	SYNTAX		OCTET STRING(SIZE(40))
	MAX-ACCESS	read-create
	STATUS		current
	DESCRIPTION
		"."
	::= { bgs10MplsErlspEntry 23}

bgs10MplsErlspErAddress4	OBJECT-TYPE
	SYNTAX		OCTET STRING(SIZE(40))
	MAX-ACCESS	read-create
	STATUS		current
	DESCRIPTION
		"."
	::= { bgs10MplsErlspEntry 24}

bgs10MplsErlspErAddress5	OBJECT-TYPE
	SYNTAX		OCTET STRING(SIZE(40))
	MAX-ACCESS	read-create
	STATUS		current
	DESCRIPTION
		"."
	::= { bgs10MplsErlspEntry 25}

bgs10MplsErlspFlag	OBJECT-TYPE
	SYNTAX		UCHAR
	MAX-ACCESS	read-create
	STATUS		current
	DESCRIPTION
		"."
	::= { bgs10MplsErlspEntry 26}

bgs10MplsErlspFreq	OBJECT-TYPE
	SYNTAX		UCHAR
	MAX-ACCESS	read-create
	STATUS		current
	DESCRIPTION
		"."
	::= { bgs10MplsErlspEntry 27}

bgs10MplsErlspWeight	OBJECT-TYPE
	SYNTAX		UCHAR
	MAX-ACCESS	read-create
	STATUS		current
	DESCRIPTION
		"."
	::= { bgs10MplsErlspEntry 28}

bgs10MplsErlspPdr	OBJECT-TYPE
	SYNTAX		Unsigned32
	MAX-ACCESS	read-create
	STATUS		current
	DESCRIPTION
		"."
	::= { bgs10MplsErlspEntry 29}

bgs10MplsErlspPbs	OBJECT-TYPE
	SYNTAX		Unsigned32
	MAX-ACCESS	read-create
	STATUS		current
	DESCRIPTION
		"."
	::= { bgs10MplsErlspEntry 30}

bgs10MplsErLspCdr	OBJECT-TYPE
	SYNTAX		Unsigned32
	MAX-ACCESS	read-create
	STATUS		current
	DESCRIPTION
		"."
	::= { bgs10MplsErlspEntry 31}

bgs10MplsErlspCbs	OBJECT-TYPE
	SYNTAX		Unsigned32
	MAX-ACCESS	read-create
	STATUS		current
	DESCRIPTION
		"."
	::= { bgs10MplsErlspEntry 32}

bgs10MplsErlspEbs	OBJECT-TYPE
	SYNTAX		Unsigned32
	MAX-ACCESS	read-create
	STATUS		current
	DESCRIPTION
		"."
	::= { bgs10MplsErlspEntry 33}

bgs10MplsErlspPinFlag	OBJECT-TYPE
	SYNTAX		UCHAR
	MAX-ACCESS	read-create
	STATUS		current
	DESCRIPTION
		"."
	::= { bgs10MplsErlspEntry 34}

bgs10MplsErlspRsCls	OBJECT-TYPE
	SYNTAX		Unsigned32
	MAX-ACCESS	read-create
	STATUS		current
	DESCRIPTION
		"."
	::= { bgs10MplsErlspEntry 35}

bgs10MplsErlspQosMark	OBJECT-TYPE
	SYNTAX		UCHAR
	MAX-ACCESS	read-create
	STATUS		current
	DESCRIPTION
		"."
	::= { bgs10MplsErlspEntry 36}

bgs10MplsErlspSetPrio	OBJECT-TYPE
	SYNTAX		UCHAR
	MAX-ACCESS	read-create
	STATUS		current
	DESCRIPTION
		"."
	::= { bgs10MplsErlspEntry 37}

bgs10MplsErlspHoldPrio	OBJECT-TYPE
	SYNTAX		UCHAR
	MAX-ACCESS	read-create
	STATUS		current
	DESCRIPTION
		"."
	::= { bgs10MplsErlspEntry 38}

bgs10MplsErlspTos	OBJECT-TYPE
	SYNTAX		OCTET STRING(SIZE(10))
	MAX-ACCESS	read-create
	STATUS		current
	DESCRIPTION
		"."
	::= { bgs10MplsErlspEntry 39}

bgs10MplsErlspPort	OBJECT-TYPE
	SYNTAX		OCTET STRING(SIZE(10))
	MAX-ACCESS	read-create
	STATUS		current
	DESCRIPTION
		"."
	::= { bgs10MplsErlspEntry 40}

bgs10MplsErlspQosNum	OBJECT-TYPE
	SYNTAX		UCHAR
	MAX-ACCESS	read-create
	STATUS		current
	DESCRIPTION
		"."
	::= { bgs10MplsErlspEntry 41}

-- atmMplsCardTrafficTable
bgs10MplsCardTrafficTable	OBJECT-TYPE
	SYNTAX		SEQUENCE OF ZXB10MplsCardTrafficEntry
	MAX-ACCESS	not-accessible
	STATUS		current
	DESCRIPTION
		"A list of Definition of MPLS Card Traffic Table entries."
	::= { bgs10Mpls 5}
	
bgs10MplsCardTrafficEntry	OBJECT-TYPE
	SYNTAX		ZXB10MplsCardTrafficEntry
	MAX-ACCESS	not-accessible
	STATUS		current
	DESCRIPTION
		"An entry in the table."
	INDEX {	
		bgs10MplsErlspIndex
		}
	::= { bgs10MplsCardTrafficTable 1}
	
ZXB10MplsCardTrafficEntry ::=
	SEQUENCE {
		bgs10MplsCardTrafficRowStatus			RowStatus,	
		bgs10MplsCardTrafficModule				UCHAR,	
		bgs10MplsCardTrafficCardType			Unsigned32,			
		bgs10MplsCardTrafficFlag				UCHAR,
		bgs10MplsCardTrafficFreq				UCHAR,
		bgs10MplsCardTrafficWeight				UCHAR,
		bgs10MplsCardTrafficPdr					Unsigned32,
		bgs10MplsCardTrafficPbs					Unsigned32,
		bgs10MplsCardTrafficCdr					Unsigned32,
		bgs10MplsCardTrafficCbs					Unsigned32,
		bgs10MplsCardTrafficEbs					Unsigned32		
	}

bgs10MplsCardTrafficRowStatus	OBJECT-TYPE
	SYNTAX		RowStatus
	MAX-ACCESS	read-create
	STATUS		current
	DESCRIPTION
		"."
	::= { bgs10MplsCardTrafficEntry 1}

bgs10MplsCardTrafficModule	OBJECT-TYPE
	SYNTAX		UCHAR
	MAX-ACCESS	read-create
	STATUS		current
	DESCRIPTION
		"."
	::= { bgs10MplsCardTrafficEntry 2}

bgs10MplsCardTrafficCardType	OBJECT-TYPE
	SYNTAX		Unsigned32
	MAX-ACCESS	read-create
	STATUS		current
	DESCRIPTION
		"."
	::= { bgs10MplsCardTrafficEntry 3}

bgs10MplsCardTrafficFlag	OBJECT-TYPE
	SYNTAX		UCHAR
	MAX-ACCESS	read-create
	STATUS		current
	DESCRIPTION
		"."
	::= { bgs10MplsCardTrafficEntry 4}

bgs10MplsCardTrafficFreq	OBJECT-TYPE
	SYNTAX		UCHAR
	MAX-ACCESS	read-create
	STATUS		current
	DESCRIPTION
		"."
	::= { bgs10MplsCardTrafficEntry 5}

bgs10MplsCardTrafficWeight	OBJECT-TYPE
	SYNTAX		UCHAR
	MAX-ACCESS	read-create
	STATUS		current
	DESCRIPTION
		"."
	::= { bgs10MplsCardTrafficEntry 6}

bgs10MplsCardTrafficPdr	OBJECT-TYPE
	SYNTAX		Unsigned32
	MAX-ACCESS	read-create
	STATUS		current
	DESCRIPTION
		"."
	::= { bgs10MplsCardTrafficEntry 7}

bgs10MplsCardTrafficPbs	OBJECT-TYPE
	SYNTAX		Unsigned32
	MAX-ACCESS	read-create
	STATUS		current
	DESCRIPTION
		"."
	::= { bgs10MplsCardTrafficEntry 8}

bgs10MplsCardTrafficCdr	OBJECT-TYPE
	SYNTAX		Unsigned32
	MAX-ACCESS	read-create
	STATUS		current
	DESCRIPTION
		"."
	::= { bgs10MplsCardTrafficEntry 9}

bgs10MplsCardTrafficCbs	OBJECT-TYPE
	SYNTAX		Unsigned32
	MAX-ACCESS	read-create
	STATUS		current
	DESCRIPTION
		"."
	::= { bgs10MplsCardTrafficEntry 10}

bgs10MplsCardTrafficEbs	OBJECT-TYPE
	SYNTAX		Unsigned32
	MAX-ACCESS	read-create
	STATUS		current
	DESCRIPTION
		"."
	::= { bgs10MplsCardTrafficEntry 11}

-- MplsFecfilterTable
bgs10MplsFecfilterTable	OBJECT-TYPE
	SYNTAX		SEQUENCE OF ZXB10MplsFecfilterEntry
	MAX-ACCESS	not-accessible
	STATUS		current
	DESCRIPTION
		"A list of Definition of MPLS Fec Filter Table entries."
	::= { bgs10Mpls 6}
	
bgs10MplsFecfilterEntry	OBJECT-TYPE
	SYNTAX		ZXB10MplsFecfilterEntry
	MAX-ACCESS	not-accessible
	STATUS		current
	DESCRIPTION
		"An entry in the table."
	INDEX {	
		bgs10MplsErlspIndex
		}
	::= { bgs10MplsFecfilterTable 1}
	
ZXB10MplsFecfilterEntry ::=
	SEQUENCE {
		bgs10MplsFecfilterRowStatus			RowStatus,	
		bgs10MplsFecfilterNet				Unsigned32,
		bgs10MplsFecfilterMask				Unsigned32,
		bgs10MplsFecfilterNextHop			Unsigned32,
		bgs10MplsFecfilterIfindex			UShort,
		bgs10MplsFecfilterBorderId			Unsigned32
	}

bgs10MplsFecfilterRowStatus	OBJECT-TYPE
	SYNTAX		RowStatus
	MAX-ACCESS	read-create
	STATUS		current
	DESCRIPTION
		"."
	::= { bgs10MplsFecfilterEntry 1}

bgs10MplsFecfilterNet	OBJECT-TYPE
	SYNTAX		Unsigned32
	MAX-ACCESS	read-create
	STATUS		current
	DESCRIPTION
		"."
	::= { bgs10MplsFecfilterEntry 2}

bgs10MplsFecfilterMask	OBJECT-TYPE
	SYNTAX		Unsigned32
	MAX-ACCESS	read-create
	STATUS		current
	DESCRIPTION
		"."
	::= { bgs10MplsFecfilterEntry 3}

bgs10MplsFecfilterNextHop	OBJECT-TYPE
	SYNTAX		Unsigned32
	MAX-ACCESS	read-create
	STATUS		current
	DESCRIPTION
		"."
	::= { bgs10MplsFecfilterEntry 4}

bgs10MplsFecfilterIfindex	OBJECT-TYPE
	SYNTAX		UShort
	MAX-ACCESS	read-create
	STATUS		current
	DESCRIPTION
		"."
	::= { bgs10MplsFecfilterEntry 5}

bgs10MplsFecfilterBorderId	OBJECT-TYPE
	SYNTAX		Unsigned32
	MAX-ACCESS	read-create
	STATUS		current
	DESCRIPTION
		"."
	::= { bgs10MplsFecfilterEntry 6}

-- NetifTable
bgs10MplsNetifTable	OBJECT-TYPE
	SYNTAX		SEQUENCE OF ZXB10MplsNetifEntry
	MAX-ACCESS	not-accessible
	STATUS		current
	DESCRIPTION
		"A list of Definition of MPLS Netif Table entries."
	::= { bgs10Mpls 7}
	
bgs10MplsNetifEntry	OBJECT-TYPE
	SYNTAX		ZXB10MplsNetifEntry
	MAX-ACCESS	not-accessible
	STATUS		current
	DESCRIPTION
		"An entry in the table."
	INDEX {	
		bgs10MplsErlspIndex
		}
	::= { bgs10MplsNetifTable 1}
	
ZXB10MplsNetifEntry ::=
	SEQUENCE {
		bgs10MplsNetifRowStatus			RowStatus,
		bgs10MplsNetifNiName			OCTET STRING(SIZE(30)),
		bgs10MplsNetifNiCardid			UCHAR,		
		bgs10MplsNetifNiIfindex			UShort,		
		bgs10MplsNetifNiNiNum			UShort,		
		bgs10MplsNetifNiLogicNum		UShort,		
		bgs10MplsNetifNiType			UShort,		
		bgs10MplsNetifNiVpi				UShort,		
		bgs10MplsNetifNiVci				UShort,		
		bgs10MplsNetifNiLVpi			UShort,		
		bgs10MplsNetifNiLVci			UShort,		
		bgs10MplsNetifNiLCardType		UShort,		
		bgs10MplsNetifNiState			UShort,		
		bgs10MplsNetifNiIfindexType		UShort,		
		bgs10MplsNetifNiIp				UShort,		
		bgs10MplsNetifNiNet				UShort,		
		bgs10MplsNetifNiSubnet			UShort,		
		bgs10MplsNetifNiMask			UShort,		
		bgs10MplsNetifNiBrc				UShort,		
		bgs10MplsNetifNiNbrc			UShort,		
		bgs10MplsNetifNiMtu				UShort,		
		bgs10MplsNetifNiHwType			UShort,		
		bgs10MplsNetifNiHa				OCTET STRING(SIZE(6)),
		bgs10MplsNetifNiHb				OCTET STRING(SIZE(6)),
		bgs10MplsNetifNiMcahb			OCTET STRING(SIZE(6))
	}

bgs10MplsNetifRowStatus	OBJECT-TYPE
	SYNTAX		RowStatus
	MAX-ACCESS	read-create
	STATUS		current
	DESCRIPTION
		"."
	::= { bgs10MplsNetifEntry 1}

bgs10MplsNetifNiName	OBJECT-TYPE
	SYNTAX		OCTET STRING(SIZE(30))
	MAX-ACCESS	read-create
	STATUS		current
	DESCRIPTION
		"."
	::= { bgs10MplsNetifEntry 2}

bgs10MplsNetifNiCardid	OBJECT-TYPE
	SYNTAX		UCHAR
	MAX-ACCESS	read-create
	STATUS		current
	DESCRIPTION
		"."
	::= { bgs10MplsNetifEntry 3}

bgs10MplsNetifNiIfindex	OBJECT-TYPE
	SYNTAX		UShort
	MAX-ACCESS	read-create
	STATUS		current
	DESCRIPTION
		"."
	::= { bgs10MplsNetifEntry 4}

bgs10MplsNetifNiNiNum	OBJECT-TYPE
	SYNTAX		UShort
	MAX-ACCESS	read-create
	STATUS		current
	DESCRIPTION
		"."
	::= { bgs10MplsNetifEntry 5}

bgs10MplsNetifNiLogicNum	OBJECT-TYPE
	SYNTAX		UShort
	MAX-ACCESS	read-create
	STATUS		current
	DESCRIPTION
		"."
	::= { bgs10MplsNetifEntry 6}

bgs10MplsNetifNiType	OBJECT-TYPE
	SYNTAX		UShort
	MAX-ACCESS	read-create
	STATUS		current
	DESCRIPTION
		"."
	::= { bgs10MplsNetifEntry 7}

bgs10MplsNetifNiVpi	OBJECT-TYPE
	SYNTAX		UShort
	MAX-ACCESS	read-create
	STATUS		current
	DESCRIPTION
		"."
	::= { bgs10MplsNetifEntry 8}

bgs10MplsNetifNiVci	OBJECT-TYPE
	SYNTAX		UShort
	MAX-ACCESS	read-create
	STATUS		current
	DESCRIPTION
		"."
	::= { bgs10MplsNetifEntry 9}

bgs10MplsNetifNiLVpi	OBJECT-TYPE
	SYNTAX		UShort
	MAX-ACCESS	read-create
	STATUS		current
	DESCRIPTION
		"."
	::= { bgs10MplsNetifEntry 10}

bgs10MplsNetifNiLVci	OBJECT-TYPE
	SYNTAX		UShort
	MAX-ACCESS	read-create
	STATUS		current
	DESCRIPTION
		"."
	::= { bgs10MplsNetifEntry 11}

bgs10MplsNetifNiLCardType	OBJECT-TYPE
	SYNTAX		UShort
	MAX-ACCESS	read-create
	STATUS		current
	DESCRIPTION
		"."
	::= { bgs10MplsNetifEntry 12}

bgs10MplsNetifNiState	OBJECT-TYPE
	SYNTAX		UShort
	MAX-ACCESS	read-create
	STATUS		current
	DESCRIPTION
		"."
	::= { bgs10MplsNetifEntry 13}

bgs10MplsNetifNiIfindexType	OBJECT-TYPE
	SYNTAX		UShort
	MAX-ACCESS	read-create
	STATUS		current
	DESCRIPTION
		"."
	::= { bgs10MplsNetifEntry 14}

bgs10MplsNetifNiIp	OBJECT-TYPE
	SYNTAX		UShort
	MAX-ACCESS	read-create
	STATUS		current
	DESCRIPTION
		"."
	::= { bgs10MplsNetifEntry 15}

bgs10MplsNetifNiNet	OBJECT-TYPE
	SYNTAX		UShort
	MAX-ACCESS	read-create
	STATUS		current
	DESCRIPTION
		"."
	::= { bgs10MplsNetifEntry 16}

bgs10MplsNetifNiSubnet	OBJECT-TYPE
	SYNTAX		UShort
	MAX-ACCESS	read-create
	STATUS		current
	DESCRIPTION
		"."
	::= { bgs10MplsNetifEntry 17}

bgs10MplsNetifNiMask	OBJECT-TYPE
	SYNTAX		UShort
	MAX-ACCESS	read-create
	STATUS		current
	DESCRIPTION
		"."
	::= { bgs10MplsNetifEntry 18}

bgs10MplsNetifNiBrc	OBJECT-TYPE
	SYNTAX		UShort
	MAX-ACCESS	read-create
	STATUS		current
	DESCRIPTION
		"."
	::= { bgs10MplsNetifEntry 19}

bgs10MplsNetifNiNbrc	OBJECT-TYPE
	SYNTAX		UShort
	MAX-ACCESS	read-create
	STATUS		current
	DESCRIPTION
		"."
	::= { bgs10MplsNetifEntry 20}

bgs10MplsNetifNiMtu	OBJECT-TYPE
	SYNTAX		UShort
	MAX-ACCESS	read-create
	STATUS		current
	DESCRIPTION
		"."
	::= { bgs10MplsNetifEntry 21}

bgs10MplsNetifNiHwType	OBJECT-TYPE
	SYNTAX		UShort
	MAX-ACCESS	read-create
	STATUS		current
	DESCRIPTION
		"."
	::= { bgs10MplsNetifEntry 22}

bgs10MplsNetifNiHa	OBJECT-TYPE
	SYNTAX		OCTET STRING(SIZE(6))
	MAX-ACCESS	read-create
	STATUS		current
	DESCRIPTION
		"."
	::= { bgs10MplsNetifEntry 23}

bgs10MplsNetifNiHb	OBJECT-TYPE
	SYNTAX		OCTET STRING(SIZE(6))
	MAX-ACCESS	read-create
	STATUS		current
	DESCRIPTION
		"."
	::= { bgs10MplsNetifEntry 24}

bgs10MplsNetifNiMcahb	OBJECT-TYPE
	SYNTAX		OCTET STRING(SIZE(6))
	MAX-ACCESS	read-create
	STATUS		current
	DESCRIPTION
		"."
	::= { bgs10MplsNetifEntry 25}


--the SPVC table 
bgs10SPvc				OBJECT IDENTIFIER	::= { zxbgs10mib 43}
        
bgs10SPvcTable	OBJECT-TYPE
	SYNTAX		SEQUENCE OF BGS10SPvcEntry
	MAX-ACCESS	not-accessible
	STATUS		current
	DESCRIPTION
		"A list of SPVC configure information entries."
	::= { bgs10SPvc 1}
	
bgs10SPvcEntry	OBJECT-TYPE
	SYNTAX		BGS10SPvcEntry
	MAX-ACCESS	not-accessible
	STATUS		current
	DESCRIPTION
		"An entry in the table."
	INDEX {	bgs10SPvcLModule,
			bgs10SPvcLPort,
			bgs10SPvcLVpi,
			bgs10SPvcLVci,
			bgs10SPvcHAtmAddress
		}
	::= { bgs10SPvcTable 1}
	
BGS10SPvcEntry ::=
	SEQUENCE {
		bgs10SPvcRowStatus					RowStatus,
		bgs10SPvcLVpi						INTEGER,
		bgs10SPvcL2HtrafficDescrType		INTEGER,
		bgs10SPvcLModule					INTEGER,
		bgs10SPvcHModule					INTEGER,
		bgs10SPvcHPort						INTEGER,
		bgs10SPvcLPort						INTEGER,
		bgs10SPvcHVpi						INTEGER,
		bgs10SPvcL2HtrafficQosClass			INTEGER,
		bgs10SPvcH2LtrafficDescrType		INTEGER,
		bgs10SPvcH2LtrafficQosClass			INTEGER,
		bgs10SPvcPvcAdminStatus				INTEGER,
		bgs10SPvcConnectStruct				INTEGER,
		bgs10SPvcServiceCategory			INTEGER,
		bgs10SPvcPvcOperStatus				INTEGER,
		bgs10SPvcLCPType					INTEGER,
		bgs10SPvcHCPType					INTEGER,
		bgs10SPvcConnectType				INTEGER,
		bgs10SPvcUse						INTEGER,
		bgs10SPvcHVci						INTEGER,
		bgs10SPvcLVci						INTEGER,
		bgs10SPvcLAtmAddress				AtmAddr,
		bgs10SPvcL2HtrafficDescrParam1		Unsigned32,
		bgs10SPvcL2HtrafficDescrParam2		Unsigned32,
		bgs10SPvcL2HtrafficDescrParam3		Unsigned32,
		bgs10SPvcL2HtrafficDescrParam4		Unsigned32,
		bgs10SPvcL2HtrafficDescrParam5		Unsigned32,
		bgs10SPvcHAtmAddress				AtmAddr,
		bgs10SPvcH2LtrafficDescrParam1		Unsigned32,
		bgs10SPvcH2LtrafficDescrParam2		Unsigned32,
		bgs10SPvcH2LtrafficDescrParam3		Unsigned32,
		bgs10SPvcH2LtrafficDescrParam4		Unsigned32,
		bgs10SPvcH2LtrafficDescrParam5		Unsigned32,
		bgs10SPvcPMPconnectTag				UShort,
		bgs10SPvcCrossconnectIdentifier		UShort,
		bgs10SPvcCatchRM					BITS,
		bgs10SPvcAllowEFC					BITS,
		bgs10SPvcEPDFlag					BITS,
		bgs10SPvcFeeGleanFlag				BITS,
		bgs10SPvcRetries					UChar,
		bgs10SPvcInterval					UChar,
		bgs10SPvcPVCType					Unsigned32,
		bgs10SPvcAlarmStatus				UShort
	}
	
bgs10SPvcRowStatus	OBJECT-TYPE
	SYNTAX		RowStatus
	MAX-ACCESS	read-create
	STATUS		current
	DESCRIPTION
		"."
	::= { bgs10SPvcEntry 1}
	
bgs10SPvcLVpi	OBJECT-TYPE
	SYNTAX		INTEGER
	MAX-ACCESS	read-create
	STATUS		current
	DESCRIPTION
		"VPI connection's VPI."
	::= { bgs10SPvcEntry 2}
	
bgs10SPvcL2HtrafficDescrType	OBJECT-TYPE
	SYNTAX		INTEGER
	MAX-ACCESS	read-create
	STATUS		current
	DESCRIPTION
		"."
	::= { bgs10SPvcEntry 3}
	
bgs10SPvcLModule		OBJECT-TYPE
	SYNTAX		INTEGER
	MAX-ACCESS	read-create
	STATUS		current
	DESCRIPTION
		"."
	::= { bgs10SPvcEntry 4}
	
bgs10SPvcHModule	OBJECT-TYPE
	SYNTAX		INTEGER
	MAX-ACCESS	read-create
	STATUS		current
	DESCRIPTION
		"."
	::= { bgs10SPvcEntry 5}
	
bgs10SPvcHPort	OBJECT-TYPE
	SYNTAX		INTEGER
	MAX-ACCESS	read-create
	STATUS		current
	DESCRIPTION
		"."
	::= { bgs10SPvcEntry 6}
	
bgs10SPvcLPort	OBJECT-TYPE
	SYNTAX		INTEGER
	MAX-ACCESS	read-create
	STATUS		current
	DESCRIPTION
		"."
	::= { bgs10SPvcEntry 7}
	
bgs10SPvcHVpi	OBJECT-TYPE
	SYNTAX		INTEGER
	MAX-ACCESS	read-create
	STATUS		current
	DESCRIPTION
		"."
	::= { bgs10SPvcEntry 8}
	
bgs10SPvcL2HtrafficQosClass	OBJECT-TYPE
	SYNTAX		INTEGER
	MAX-ACCESS	read-create
	STATUS		current
	DESCRIPTION
		"."
	::= { bgs10SPvcEntry 9}
	
bgs10SPvcH2LtrafficDescrType	OBJECT-TYPE
	SYNTAX		INTEGER
	MAX-ACCESS	read-create
	STATUS		current
	DESCRIPTION
		"."
	::= { bgs10SPvcEntry 10}
	
bgs10SPvcH2LtrafficQosClass	OBJECT-TYPE
	SYNTAX		INTEGER
	MAX-ACCESS	read-create
	STATUS		current
	DESCRIPTION
		"."
	::= { bgs10SPvcEntry 11}
	
bgs10SPvcPvcAdminStatus	OBJECT-TYPE
	SYNTAX		INTEGER
	MAX-ACCESS	read-create
	STATUS		current
	DESCRIPTION
		"."
	::= { bgs10SPvcEntry 12}
	
bgs10SPvcConnectStruct	OBJECT-TYPE
	SYNTAX		INTEGER { 	singp2p(0),
							bip2p(1),
							singp2mp(2),
							singmp2p(3),
							mp2mp(4),
							bip2mp(5)}
	MAX-ACCESS	read-create
	STATUS		current
	DESCRIPTION
		"Pvc Connection type:
		--singal directional point to point(0)
		--bi-directional point to point (1)
		--singal directional point to multi-points (2)
		--singal directional multi-points to point (3)
		--multi-points to multi-points (4)
		--bi-dirctional point to multi-points (5)."
	::= { bgs10SPvcEntry 13}
	
bgs10SPvcServiceCategory	OBJECT-TYPE
	SYNTAX		INTEGER
	MAX-ACCESS	read-create
	STATUS		current
	DESCRIPTION
		"."
	::= { bgs10SPvcEntry 14}
	
bgs10SPvcPvcOperStatus	OBJECT-TYPE
	SYNTAX		INTEGER
	MAX-ACCESS	read-only
	STATUS		current
	DESCRIPTION
		"."
	::= { bgs10SPvcEntry 15}
	
bgs10SPvcLCPType	OBJECT-TYPE
	SYNTAX		INTEGER {	segEndPtNo(0),
							segEndPtYes(1),
							vpcConnectionEndPoint(2)
						}
	MAX-ACCESS	read-create
	STATUS		current
	DESCRIPTION
		"."
	::= { bgs10SPvcEntry 16}
	
bgs10SPvcHCPType	OBJECT-TYPE
	SYNTAX		INTEGER	{	segEndPtNo(0),
							segEndPtYes(1),
							vpcConnectionEndPoint(2)
						}
	MAX-ACCESS	read-create
	STATUS		current
	DESCRIPTION
		"."
	::= { bgs10SPvcEntry 17}
	
bgs10SPvcConnectType	OBJECT-TYPE
	SYNTAX		INTEGER
	MAX-ACCESS	read-create
	STATUS		current
	DESCRIPTION
		"."
	::= { bgs10SPvcEntry 18}
	
bgs10SPvcUse	OBJECT-TYPE
	SYNTAX		INTEGER { 	general(0),
							configureDirectVCC(1),
							controlDirectVCC(2),
							controlDistributeVCC(3),
							dataDirectVCC(4),
							multicastSendVCC(5),
							mulitcastForwardVCC(6)}
	MAX-ACCESS	read-create
	STATUS		current
	DESCRIPTION
		"."
	::= { bgs10SPvcEntry 19}

bgs10SPvcHVci	OBJECT-TYPE
	SYNTAX		INTEGER
	MAX-ACCESS	read-create
	STATUS		current
	DESCRIPTION
		"."
	::= { bgs10SPvcEntry 20}
	
bgs10SPvcLVci	OBJECT-TYPE
	SYNTAX		INTEGER
	MAX-ACCESS	read-create
	STATUS		current
	DESCRIPTION
		"."
	::= { bgs10SPvcEntry 21}		
	
bgs10SPvcLAtmAddress	OBJECT-TYPE
	SYNTAX		AtmAddr
	MAX-ACCESS	read-create
	STATUS		current
	DESCRIPTION
		"."
	::= { bgs10SPvcEntry 22}
				
bgs10SPvcL2HtrafficDescrParam1	OBJECT-TYPE
	SYNTAX		Unsigned32
	MAX-ACCESS	read-create
	STATUS		current
	DESCRIPTION
		"."
	::= { bgs10SPvcEntry 23}
	
bgs10SPvcL2HtrafficDescrParam2	OBJECT-TYPE
	SYNTAX		Unsigned32
	MAX-ACCESS	read-create
	STATUS		current
	DESCRIPTION
		"."
	::= { bgs10SPvcEntry 24}
	
bgs10SPvcL2HtrafficDescrParam3	OBJECT-TYPE
	SYNTAX		Unsigned32
	MAX-ACCESS	read-create
	STATUS		current
	DESCRIPTION
		"."
	::= { bgs10SPvcEntry 25}
	
bgs10SPvcL2HtrafficDescrParam4	OBJECT-TYPE
	SYNTAX		Unsigned32
	MAX-ACCESS	read-create
	STATUS		current
	DESCRIPTION
		"."
	::= { bgs10SPvcEntry 26}
	
bgs10SPvcL2HtrafficDescrParam5	OBJECT-TYPE
	SYNTAX		Unsigned32
	MAX-ACCESS	read-create
	STATUS		current
	DESCRIPTION
		"."
	::= { bgs10SPvcEntry 27}
	
bgs10SPvcHAtmAddress	OBJECT-TYPE
	SYNTAX		AtmAddr
	MAX-ACCESS	read-create
	STATUS		current
	DESCRIPTION
		"."
	::= { bgs10SPvcEntry 28}
	
bgs10SPvcH2LtrafficDescrParam1	OBJECT-TYPE
	SYNTAX		Unsigned32
	MAX-ACCESS	read-create
	STATUS		current
	DESCRIPTION
		"."
	::= { bgs10SPvcEntry 29}
	
bgs10SPvcH2LtrafficDescrParam2	OBJECT-TYPE
	SYNTAX		Unsigned32
	MAX-ACCESS	read-create
	STATUS		current
	DESCRIPTION
		"."
	::= { bgs10SPvcEntry 30}
	
bgs10SPvcH2LtrafficDescrParam3	OBJECT-TYPE
	SYNTAX		Unsigned32
	MAX-ACCESS	read-create
	STATUS		current
	DESCRIPTION
		"."
	::= { bgs10SPvcEntry 31}
	
bgs10SPvcH2LtrafficDescrParam4	OBJECT-TYPE
	SYNTAX		Unsigned32
	MAX-ACCESS	read-create
	STATUS		current
	DESCRIPTION
		"."
	::= { bgs10SPvcEntry 32}
	
bgs10SPvcH2LtrafficDescrParam5	OBJECT-TYPE
	SYNTAX		Unsigned32
	MAX-ACCESS	read-create
	STATUS		current
	DESCRIPTION
		"."
	::= { bgs10SPvcEntry 33} 
	
bgs10SPvcPMPconnectTag	OBJECT-TYPE
	SYNTAX		UShort
	MAX-ACCESS	read-only
	STATUS		current
	DESCRIPTION
		"the PMP connection tag."
	::= { bgs10SPvcEntry 34 }
	
bgs10SPvcCrossconnectIdentifier	OBJECT-TYPE
	SYNTAX		UShort
	MAX-ACCESS	read-only
	STATUS		current
	DESCRIPTION
		"the cross connection identifier."
	::= { bgs10SPvcEntry 35 } 
	
bgs10SPvcCatchRM	OBJECT-TYPE
	SYNTAX		BITS { not-catch(0),
					   catch(1)
					 }
	MAX-ACCESS	read-only
	STATUS		current
	DESCRIPTION
		"."
	::= { bgs10SPvcEntry 36 } 
	
bgs10SPvcAllowEFC	OBJECT-TYPE
	SYNTAX		BITS { not-allow(0),
					   allow(1)
					 }
	MAX-ACCESS	read-only
	STATUS		current
	DESCRIPTION
		"."
	::= { bgs10SPvcEntry 37 } 
	
bgs10SPvcEPDFlag		OBJECT-TYPE
	SYNTAX		BITS { not-set(0),
					   set(1)
					 }
	MAX-ACCESS	read-only
	STATUS		current
	DESCRIPTION
		"."
	::= { bgs10SPvcEntry 38 } 
	
bgs10SPvcFeeGleanFlag	OBJECT-TYPE
	SYNTAX		BITS { not-glean(0),
					   glean(1)
					 }
	MAX-ACCESS	read-only
	STATUS		current
	DESCRIPTION
		"."
	::= { bgs10SPvcEntry 39 } 

bgs10SPvcRetries	OBJECT-TYPE
	SYNTAX		UChar
	MAX-ACCESS	read-only
	STATUS		current
	DESCRIPTION
		"."
	::= { bgs10SPvcEntry 40 } 

bgs10SPvcInterval	OBJECT-TYPE
	SYNTAX		UChar
	MAX-ACCESS	read-only
	STATUS		current
	DESCRIPTION
		"."
	::= { bgs10SPvcEntry 41 } 

bgs10SPvcPVCType	OBJECT-TYPE
	SYNTAX		Unsigned32
	MAX-ACCESS	read-only
	STATUS		current
	DESCRIPTION
		"."
	::= { bgs10SPvcEntry 42 } 
	
bgs10SPvcAlarmStatus	OBJECT-TYPE
	SYNTAX		UShort
	MAX-ACCESS	read-only
	STATUS		current
	DESCRIPTION
		"."
	::= { bgs10SPvcEntry 43 } 
	
-- The CES SPVC confiugration 
bgs10CesSPVCConfigTable	OBJECT-TYPE
	SYNTAX		SEQUENCE OF BGS10CesSPVCConfigEntry
	MAX-ACCESS	not-accessible
	STATUS		current
	DESCRIPTION
		"."
	::= { zxbgs10mib 44 }

bgs10CesSPVCConfigEntry	OBJECT-TYPE
	SYNTAX		BGS10CesSPVCConfigEntry
	MAX-ACCESS	not-accessible
	STATUS		current
	DESCRIPTION
		"."
	INDEX { atmfCESConfEntry }
	::= { bgs10CesSPVCConfigTable 1 }

BGS10CesSPVCConfigEntry ::=
	SEQUENCE { 
		bgs10CesSPVCCbrIndex 		InterfaceIndex,
		bgs10CesSPVCAtmIndex 		CESConnectionPort,
		bgs10CesSPVCAtmVpi 			VpiInteger,
		bgs10CesSPVCAtmVci 			VciInteger,
		bgs10CesSPVCCbrService 		INTEGER,
		bgs10CesSPVCCbrClockMode 	INTEGER,
		bgs10CesSPVCCas 			INTEGER,
		bgs10CesSPVCPartialFill 	INTEGER,
		bgs10CesSPVCBufMaxSize 		INTEGER,
		bgs10CesSPVCCdvRxT 			INTEGER,
		bgs10CesSPVCCellLossIntegrationPeriod INTEGER,
		bgs10CesSPVCConnType 		INTEGER,
		bgs10CesSPVCLocalAddr 		AtmAddr,
		bgs10CesSPVCAdminStatus 	INTEGER,
		bgs10CesSPVCOperStatus 		INTEGER,
		bgs10CesSPVCConfRowStatus 	RowStatus,
		bgs10CesSPVCHCpType					UChar,
		bgs10CesSPVCCrossConnectIdentifier	UShort,
		bgs10CesSPVCCatchRM					BITS,		
		bgs10CesSPVCAllowEFC				BITS,
		bgs10CesSPVCEPDFlag					BITS,
		bgs10CesSPVCFeeGleanFlag			BITS,
		bgs10CesSPVCSvcOrPvcFlag			BITS,
		bgs10CesSPVCConnAtmAddress			AtmAddr,
		bgs10CesSPVCSpvcRetries				UChar,
		bgs10CesSPVCSpvcInterval			UChar,
		bgs10CesSPVCPVCType					UShort,
		bgs10CesSPVCAlarmStatus				UShort
	}

	bgs10CesSPVCCbrIndex OBJECT-TYPE	
		SYNTAX InterfaceIndex
		MAX-ACCESS not-accessible
		STATUS current
		DESCRIPTION
			"The value of this object is equal to MIB II's ifIndex value
			of the CBR interface, channel, or bundle that is being
			cross-connected to an ATM VCL."
		::= { bgs10CesSPVCConfigEntry 1 }

	bgs10CesSPVCAtmIndex OBJECT-TYPE
		SYNTAX CESConnectionPort
		MAX-ACCESS read-create
		STATUS current
		DESCRIPTION
			"The value of this object is equal to MIB II's
			ifIndex value of the ATM Port interface mapped
			through this CES IWF to a CBR interface. This value
			is overwritten whenever an active or passive SVC is
			established.
			The distinguished value zero indicates that no ATM
			interface has been specified."
		::= { bgs10CesSPVCConfigEntry 2 }
	
	bgs10CesSPVCAtmVpi OBJECT-TYPE
		SYNTAX VpiInteger
		MAX-ACCESS read-create
		STATUS current
		DESCRIPTION
			"The value of this object is equal to the VPI used
			by the ATM VCL mapped through this CES IWF to a CBR
			interface. This value is overwritten whenever an
			active or passive SVC is established.
			The value is not relevant if no ATM interface has been
			specified (i.e., atmfCESAtmIndex is set to zero)."
		::= { bgs10CesSPVCConfigEntry 3 }

	bgs10CesSPVCAtmVci OBJECT-TYPE
		SYNTAX VciInteger
		MAX-ACCESS read-create
		STATUS current
		DESCRIPTION
			"The value of this object is equal to the VCI used
			by the ATM VCL mapped through this CES IWF to a CBR
			interface. This value is overwritten whenever an
			active or passive SVC is established.
			The distinguished value zero indicates that no ATM
			VCL has been specified."
		::= { bgs10CesSPVCConfigEntry 4 }
	
	bgs10CesSPVCCbrService OBJECT-TYPE
		SYNTAX INTEGER {
			unstructured(1),
			structured(2)
		}		
		MAX-ACCESS read-create
		STATUS current
		DESCRIPTION
			"Define if DSx/Ex service isas structured or unstructurednot. A
			structured(2) interface is some nx64kbKbps. An unstructured
			(1) interface is 1.544Mbps, 2.048Mbps, 6.312Mbps, 44.736 Mbps,
			or 34.368 Mbps. unstructured(1) passes all bits through the
			ATM network. strucutured(2) passes data bits through the
			ATM network, and may also pass signalling bits
			At this time, only unstructured mode is defined for the
			44.736 Mbps and 34.368 Mbps services."
		::= { bgs10CesSPVCConfigEntry 5 }

	bgs10CesSPVCCbrClockMode OBJECT-TYPE
		SYNTAX INTEGER {
			synchronous(1),
			srts(2),
			adaptive(3)
		}
		MAX-ACCESS read-create
		STATUS current
		DESCRIPTION
			"Define if DSx/Ex service clocking mode. This maps into
			transmit clock source of CBR interface.
			For structured modes this value, if present, must be set to
			synchronous(1)."
		DEFVAL { synchronous }
		::= { bgs10CesSPVCConfigEntry 6 }
	
	bgs10CesSPVCCas OBJECT-TYPE
		SYNTAX INTEGER {
			basic(1),
			e1Cas(2),
			ds1SfCas(3),
			ds1EsfCas(4),
			j2Cas(5)
		}
		MAX-ACCESS read-create
		STATUS current
		DESCRIPTION
			"This parameter selects which AAL1 Format should be used:
			Basic does not carry CAS bits, and uses a single 125 usec frame.
			e1Cas, ds1SfCas, dS1EsfCas and j2Cas carry CAS bits in a
			multiframe structure for E1, DS1 SF, DS1 ESF and J2
			respectively.
			This applies to structured interfaces only. Default is
			basic (1). For unstructured interfaces this value, if present,
			must be set to the default of basic (1)."
		DEFVAL { basic }
		::= { bgs10CesSPVCConfigEntry 7 }

	bgs10CesSPVCPartialFill OBJECT-TYPE
		SYNTAX INTEGER (0 .. 47)
		MAX-ACCESS read-create
		STATUS current
		DESCRIPTION
			"If partial cell fill is used, the number of user octets per
			cell must be set with this parameter. Setting this parameter
			to zero disables partial cell fill, and causes all cells to
			be completely filled before they are sent."
		DEFVAL { 0 } -- Partial Cell Fill not used
		::= { bgs10CesSPVCConfigEntry 8 }
	
	bgs10CesSPVCBufMaxSize OBJECT-TYPE
		SYNTAX INTEGER (1..65536)
		UNITS "10 usec"
		MAX-ACCESS read-create
		STATUS current
		DESCRIPTION
			"Define maximum size in 10 microsecond increments of the
			reassembly buffer. Some implementations may want allow the
			maximum buffer size to be programmed to a size less than the
			physical limit to reduce the maximum delay through a circuit."
		DEFVAL { 128 }
		::= { bgs10CesSPVCConfigEntry 9 }
	
	bgs10CesSPVCCdvRxT OBJECT-TYPE
		SYNTAX INTEGER (1..65535)
		UNITS "10 usec"
		MAX-ACCESS read-create
		STATUS current
		DESCRIPTION
			"The maximum cell arrival jitter in 10 usec increments that
			the reassembly process will tolerate in the cell stream
			without producing errors on the CBR service interface."
		DEFVAL { 100 }
		::= { bgs10CesSPVCConfigEntry 10 }

	bgs10CesSPVCCellLossIntegrationPeriod OBJECT-TYPE
		SYNTAX INTEGER (1000 .. 65535)
		UNITS "msec"
		MAX-ACCESS read-create
		STATUS current
		DESCRIPTION
			"The time in milliseconds for the cell loss integration period.
			If a cells are continuously lost for this period of time,
			atmfCESCellLossStatus is set to loss (2). The
			default definition is 2500."
		DEFVAL { 2500 }
		::= { bgs10CesSPVCConfigEntry 11 }

	bgs10CesSPVCConnType OBJECT-TYPE
SYNTAX INTEGER {
other(1),
pvc(2),
activeSvc(3),
passiveSvc(4)
}
MAX-ACCESS read-create
STATUS current
DESCRIPTION
"The type of ATM connectivity between associated CES IWF's.
Valid values are:
other - none of the types specified below
pvc - supporting connectivity is a permanent
virtual connection
activeSvc - attempt calls whenever none established
passiveSvc - accept calls"
::= { bgs10CesSPVCConfigEntry 12 }

bgs10CesSPVCLocalAddr OBJECT-TYPE
SYNTAX AtmAddr
MAX-ACCESS read-create
STATUS current
DESCRIPTION
"The ATM address of the local CES IWF process. This address
may be used by the automatic SVC establishment procedures to
identify the intended recipient CES IWF of an incoming automatic
SVC call request. Optionally, the MAX-ACCESS of this object
may be read-only, for those implementations where it is
not desired to manually configure this address."
::= { bgs10CesSPVCConfigEntry 13 }

bgs10CesSPVCAdminStatus OBJECT-TYPE
SYNTAX INTEGER {
up(1),
down(2)
}
MAX-ACCESS read-create
STATUS current
DESCRIPTION
"The desired administrative status of the CES interworking
function. The up and down states indicate that the traffic
flow is enabled or disabled respectively across the CES
interworking function."
::= { bgs10CesSPVCConfigEntry 14 }

bgs10CesSPVCOperStatus OBJECT-TYPE
SYNTAX INTEGER {
up(1),
down(2),
unknown(3)
}
MAX-ACCESS read-only
STATUS current
DESCRIPTION
"The operational status of the CES interworking function.
The up and down states indicate that the traffic flow is
enabled or disabled respectively across the CES interworking
function. The unknown state indicates that the state of the
CES interworking function cannot be determined. The state
will be down or unknown if the supporting CBR or ATM
interfaces are down or unknown, respectively."
::= { bgs10CesSPVCConfigEntry 15 }

bgs10CesSPVCConfRowStatus OBJECT-TYPE
SYNTAX RowStatus
MAX-ACCESS read-create
STATUS current
DESCRIPTION
"This object is used to create new rows in this table, modify
existing rows, and to delete existing rows."
::= { bgs10CesSPVCConfigEntry 16 }
	
bgs10CesSPVCHCpType	OBJECT-TYPE
	SYNTAX		UChar
	MAX-ACCESS	read-create
	STATUS		current
	DESCRIPTION
		"The high CP type of CES."
	::= {  bgs10CesSPVCConfigEntry 17 }
	
bgs10CesSPVCCrossConnectIdentifier	OBJECT-TYPE
	SYNTAX		UShort
	MAX-ACCESS	read-create
	STATUS		current
	DESCRIPTION
		"the cross connection identifier."
	::= {	bgs10CesSPVCConfigEntry 18 }

bgs10CesSPVCCatchRM	OBJECT-TYPE
	SYNTAX		BITS {  not-catch(0),
						catch(1)
					 }
	MAX-ACCESS	read-create
	STATUS		current
	DESCRIPTION
		"."
	::= { bgs10CesSPVCConfigEntry 19}

bgs10CesSPVCAllowEFC	OBJECT-TYPE
	SYNTAX		BITS {  not-allow(0),
						allow(1)
					 }
	MAX-ACCESS	read-create
	STATUS		current
	DESCRIPTION
		"."
	::= { bgs10CesSPVCConfigEntry 20}

bgs10CesSPVCEPDFlag	OBJECT-TYPE
	SYNTAX		BITS {  not-set(0),
						set(1)
					 }
	MAX-ACCESS	read-create
	STATUS		current
	DESCRIPTION
		"."
	::= { bgs10CesSPVCConfigEntry 21}
	
bgs10CesSPVCFeeGleanFlag	OBJECT-TYPE
	SYNTAX		BITS {  not-glean(0),
						glean(1)
					 }
	MAX-ACCESS	read-create
	STATUS		current
	DESCRIPTION
		"."
	::= { bgs10CesSPVCConfigEntry 22}
	
bgs10CesSPVCSvcOrPvcFlag	OBJECT-TYPE
	SYNTAX		BITS {  pvc(0),
						svc(1)
					 }
	MAX-ACCESS	read-create
	STATUS		current
	DESCRIPTION
		"."
	::= { bgs10CesSPVCConfigEntry 23}

bgs10CesSPVCConnAtmAddress	OBJECT-TYPE
	SYNTAX		AtmAddr
	MAX-ACCESS	read-create
	STATUS		current
	DESCRIPTION
		"."
	::= { bgs10CesSPVCConfigEntry 24}

bgs10CesSPVCSpvcRetries	OBJECT-TYPE
	SYNTAX		UChar
	MAX-ACCESS	read-create
	STATUS		current
	DESCRIPTION
		"."
	::= { bgs10CesSPVCConfigEntry 25}

bgs10CesSPVCSpvcInterval	OBJECT-TYPE
	SYNTAX		UChar
	MAX-ACCESS	read-create
	STATUS		current
	DESCRIPTION
		"."
	::= { bgs10CesSPVCConfigEntry 26}

bgs10CesSPVCPVCType	OBJECT-TYPE
	SYNTAX		UShort
	MAX-ACCESS	read-create
	STATUS		current
	DESCRIPTION
		"."
	::= { bgs10CesSPVCConfigEntry 27}

bgs10CesSPVCAlarmStatus	OBJECT-TYPE
	SYNTAX		UShort
	MAX-ACCESS	read-create
	STATUS		current
	DESCRIPTION
		"."
	::= { bgs10CesSPVCConfigEntry 28}

--the SPVP table 
bgs10SPvp	OBJECT IDENTIFIER	::= { zxbgs10mib 45}
        
bgs10SPvpTable	OBJECT-TYPE
	SYNTAX		SEQUENCE OF BGS10SPvpEntry
	MAX-ACCESS	not-accessible
	STATUS		current
	DESCRIPTION
		"A list of SPVP configure information entries."
	::= { bgs10SPvp 1}
	
bgs10SPvpEntry	OBJECT-TYPE
	SYNTAX		BGS10SPvpEntry
	MAX-ACCESS	not-accessible
	STATUS		current
	DESCRIPTION
		"An entry in the table."
	INDEX {	bgs10SPvpLModule,
			bgs10SPvpLPort,
			bgs10SPvpLVpi,
			bgs10SPvpLVci,
			bgs10SPvpHAtmAddress
		}
	::= { bgs10SPvpTable 1}
	
BGS10SPvpEntry ::=
	SEQUENCE {
		bgs10SPvpRowStatus					RowStatus,
		bgs10SPvpLVpi						INTEGER,
		bgs10SPvpL2HtrafficDescrType		INTEGER,
		bgs10SPvpLModule					INTEGER,
		bgs10SPvpHModule					INTEGER,
		bgs10SPvpHPort						INTEGER,
		bgs10SPvpLPort						INTEGER,
		bgs10SPvpHVpi						INTEGER,
		bgs10SPvpL2HtrafficQosClass			INTEGER,
		bgs10SPvpH2LtrafficDescrType		INTEGER,
		bgs10SPvpH2LtrafficQosClass			INTEGER,
		bgs10SPvpPvcAdminStatus				INTEGER,
		bgs10SPvpConnectStruct				INTEGER,
		bgs10SPvpServiceCategory			INTEGER,
		bgs10SPvpPvcOperStatus				INTEGER,
		bgs10SPvpLCPType					INTEGER,
		bgs10SPvpHCPType					INTEGER,
		bgs10SPvpConnectType				INTEGER,
		bgs10SPvpUse						INTEGER,
		bgs10SPvpHVci						INTEGER,
		bgs10SPvpLVci						INTEGER,
		bgs10SPvpLAtmAddress				AtmAddr,
		bgs10SPvpL2HtrafficDescrParam1		Unsigned32,
		bgs10SPvpL2HtrafficDescrParam2		Unsigned32,
		bgs10SPvpL2HtrafficDescrParam3		Unsigned32,
		bgs10SPvpL2HtrafficDescrParam4		Unsigned32,
		bgs10SPvpL2HtrafficDescrParam5		Unsigned32,
		bgs10SPvpHAtmAddress				AtmAddr,
		bgs10SPvpH2LtrafficDescrParam1		Unsigned32,
		bgs10SPvpH2LtrafficDescrParam2		Unsigned32,
		bgs10SPvpH2LtrafficDescrParam3		Unsigned32,
		bgs10SPvpH2LtrafficDescrParam4		Unsigned32,
		bgs10SPvpH2LtrafficDescrParam5		Unsigned32,
		bgs10SPvpPMPconnectTag				UShort,
		bgs10SPvpCrossconnectIdentifier		UShort,
		bgs10SPvpCatchRM					BITS,
		bgs10SPvpAllowEFC					BITS,
		bgs10SPvpEPDFlag					BITS,
		bgs10SPvpFeeGleanFlag				BITS,
		bgs10SPvpRetries					UChar,
		bgs10SPvpInterval					UChar,
		bgs10SPvpPVCType					Unsigned32,
		bgs10SPvpAlarmStatus				UShort
	}
	
bgs10SPvpRowStatus	OBJECT-TYPE
	SYNTAX		RowStatus
	MAX-ACCESS	read-create
	STATUS		current
	DESCRIPTION
		"."
	::= { bgs10SPvpEntry 1}
	
bgs10SPvpLVpi	OBJECT-TYPE
	SYNTAX		INTEGER
	MAX-ACCESS	read-create
	STATUS		current
	DESCRIPTION
		"VPI connection's VPI."
	::= { bgs10SPvpEntry 2}
	
bgs10SPvpL2HtrafficDescrType	OBJECT-TYPE
	SYNTAX		INTEGER
	MAX-ACCESS	read-create
	STATUS		current
	DESCRIPTION
		"."
	::= { bgs10SPvpEntry 3}
	
bgs10SPvpLModule		OBJECT-TYPE
	SYNTAX		INTEGER
	MAX-ACCESS	read-create
	STATUS		current
	DESCRIPTION
		"."
	::= { bgs10SPvpEntry 4}
	
bgs10SPvpHModule	OBJECT-TYPE
	SYNTAX		INTEGER
	MAX-ACCESS	read-create
	STATUS		current
	DESCRIPTION
		"."
	::= { bgs10SPvpEntry 5}
	
bgs10SPvpHPort	OBJECT-TYPE
	SYNTAX		INTEGER
	MAX-ACCESS	read-create
	STATUS		current
	DESCRIPTION
		"."
	::= { bgs10SPvpEntry 6}
	
bgs10SPvpLPort	OBJECT-TYPE
	SYNTAX		INTEGER
	MAX-ACCESS	read-create
	STATUS		current
	DESCRIPTION
		"."
	::= { bgs10SPvpEntry 7}
	
bgs10SPvpHVpi	OBJECT-TYPE
	SYNTAX		INTEGER
	MAX-ACCESS	read-create
	STATUS		current
	DESCRIPTION
		"."
	::= { bgs10SPvpEntry 8}
	
bgs10SPvpL2HtrafficQosClass	OBJECT-TYPE
	SYNTAX		INTEGER
	MAX-ACCESS	read-create
	STATUS		current
	DESCRIPTION
		"."
	::= { bgs10SPvpEntry 9}
	
bgs10SPvpH2LtrafficDescrType	OBJECT-TYPE
	SYNTAX		INTEGER
	MAX-ACCESS	read-create
	STATUS		current
	DESCRIPTION
		"."
	::= { bgs10SPvpEntry 10}
	
bgs10SPvpH2LtrafficQosClass	OBJECT-TYPE
	SYNTAX		INTEGER
	MAX-ACCESS	read-create
	STATUS		current
	DESCRIPTION
		"."
	::= { bgs10SPvpEntry 11}
	
bgs10SPvpPvcAdminStatus	OBJECT-TYPE
	SYNTAX		INTEGER
	MAX-ACCESS	read-create
	STATUS		current
	DESCRIPTION
		"."
	::= { bgs10SPvpEntry 12}
	
bgs10SPvpConnectStruct	OBJECT-TYPE
	SYNTAX		INTEGER { 	singp2p(0),
							bip2p(1),
							singp2mp(2),
							singmp2p(3),
							mp2mp(4),
							bip2mp(5)}
	MAX-ACCESS	read-create
	STATUS		current
	DESCRIPTION
		"Pvc Connection type:
		--singal directional point to point(0)
		--bi-directional point to point (1)
		--singal directional point to multi-points (2)
		--singal directional multi-points to point (3)
		--multi-points to multi-points (4)
		--bi-dirctional point to multi-points (5)."
	::= { bgs10SPvpEntry 13}
	
bgs10SPvpServiceCategory	OBJECT-TYPE
	SYNTAX		INTEGER
	MAX-ACCESS	read-create
	STATUS		current
	DESCRIPTION
		"."
	::= { bgs10SPvpEntry 14}
	
bgs10SPvpPvcOperStatus	OBJECT-TYPE
	SYNTAX		INTEGER
	MAX-ACCESS	read-only
	STATUS		current
	DESCRIPTION
		"."
	::= { bgs10SPvpEntry 15}
	
bgs10SPvpLCPType	OBJECT-TYPE
	SYNTAX		INTEGER {	segEndPtNo(0),
							segEndPtYes(1),
							vpcConnectionEndPoint(2)
						}
	MAX-ACCESS	read-create
	STATUS		current
	DESCRIPTION
		"."
	::= { bgs10SPvpEntry 16}
	
bgs10SPvpHCPType	OBJECT-TYPE
	SYNTAX		INTEGER	{	segEndPtNo(0),
							segEndPtYes(1),
							vpcConnectionEndPoint(2)
						}
	MAX-ACCESS	read-create
	STATUS		current
	DESCRIPTION
		"."
	::= { bgs10SPvpEntry 17}
	
bgs10SPvpConnectType	OBJECT-TYPE
	SYNTAX		INTEGER
	MAX-ACCESS	read-create
	STATUS		current
	DESCRIPTION
		"."
	::= { bgs10SPvpEntry 18}
	
bgs10SPvpUse	OBJECT-TYPE
	SYNTAX		INTEGER { 	general(0),
							configureDirectVCC(1),
							controlDirectVCC(2),
							controlDistributeVCC(3),
							dataDirectVCC(4),
							multicastSendVCC(5),
							mulitcastForwardVCC(6)}
	MAX-ACCESS	read-create
	STATUS		current
	DESCRIPTION
		"."
	::= { bgs10SPvpEntry 19}

bgs10SPvpHVci	OBJECT-TYPE
	SYNTAX		INTEGER
	MAX-ACCESS	read-create
	STATUS		current
	DESCRIPTION
		"."
	::= { bgs10SPvpEntry 20}
	
bgs10SPvpLVci	OBJECT-TYPE
	SYNTAX		INTEGER
	MAX-ACCESS	read-create
	STATUS		current
	DESCRIPTION
		"."
	::= { bgs10SPvpEntry 21}		
	
bgs10SPvpLAtmAddress	OBJECT-TYPE
	SYNTAX		AtmAddr
	MAX-ACCESS	read-create
	STATUS		current
	DESCRIPTION
		"."
	::= { bgs10SPvpEntry 22}
				
bgs10SPvpL2HtrafficDescrParam1	OBJECT-TYPE
	SYNTAX		Unsigned32
	MAX-ACCESS	read-create
	STATUS		current
	DESCRIPTION
		"."
	::= { bgs10SPvpEntry 23}
	
bgs10SPvpL2HtrafficDescrParam2	OBJECT-TYPE
	SYNTAX		Unsigned32
	MAX-ACCESS	read-create
	STATUS		current
	DESCRIPTION
		"."
	::= { bgs10SPvpEntry 24}
	
bgs10SPvpL2HtrafficDescrParam3	OBJECT-TYPE
	SYNTAX		Unsigned32
	MAX-ACCESS	read-create
	STATUS		current
	DESCRIPTION
		"."
	::= { bgs10SPvpEntry 25}
	
bgs10SPvpL2HtrafficDescrParam4	OBJECT-TYPE
	SYNTAX		Unsigned32
	MAX-ACCESS	read-create
	STATUS		current
	DESCRIPTION
		"."
	::= { bgs10SPvpEntry 26}
	
bgs10SPvpL2HtrafficDescrParam5	OBJECT-TYPE
	SYNTAX		Unsigned32
	MAX-ACCESS	read-create
	STATUS		current
	DESCRIPTION
		"."
	::= { bgs10SPvpEntry 27}
	
bgs10SPvpHAtmAddress	OBJECT-TYPE
	SYNTAX		AtmAddr
	MAX-ACCESS	read-create
	STATUS		current
	DESCRIPTION
		"."
	::= { bgs10SPvpEntry 28}
	
bgs10SPvpH2LtrafficDescrParam1	OBJECT-TYPE
	SYNTAX		Unsigned32
	MAX-ACCESS	read-create
	STATUS		current
	DESCRIPTION
		"."
	::= { bgs10SPvpEntry 29}
	
bgs10SPvpH2LtrafficDescrParam2	OBJECT-TYPE
	SYNTAX		Unsigned32
	MAX-ACCESS	read-create
	STATUS		current
	DESCRIPTION
		"."
	::= { bgs10SPvpEntry 30}
	
bgs10SPvpH2LtrafficDescrParam3	OBJECT-TYPE
	SYNTAX		Unsigned32
	MAX-ACCESS	read-create
	STATUS		current
	DESCRIPTION
		"."
	::= { bgs10SPvpEntry 31}
	
bgs10SPvpH2LtrafficDescrParam4	OBJECT-TYPE
	SYNTAX		Unsigned32
	MAX-ACCESS	read-create
	STATUS		current
	DESCRIPTION
		"."
	::= { bgs10SPvpEntry 32}
	
bgs10SPvpH2LtrafficDescrParam5	OBJECT-TYPE
	SYNTAX		Unsigned32
	MAX-ACCESS	read-create
	STATUS		current
	DESCRIPTION
		"."
	::= { bgs10SPvpEntry 33} 
	
bgs10SPvpPMPconnectTag	OBJECT-TYPE
	SYNTAX		UShort
	MAX-ACCESS	read-only
	STATUS		current
	DESCRIPTION
		"the PMP connection tag."
	::= { bgs10SPvpEntry 34 }
	
bgs10SPvpCrossconnectIdentifier	OBJECT-TYPE
	SYNTAX		UShort
	MAX-ACCESS	read-only
	STATUS		current
	DESCRIPTION
		"the cross connection identifier."
	::= { bgs10SPvpEntry 35 } 
	
bgs10SPvpCatchRM	OBJECT-TYPE
	SYNTAX		BITS { not-catch(0),
					   catch(1)
					 }
	MAX-ACCESS	read-only
	STATUS		current
	DESCRIPTION
		"."
	::= { bgs10SPvpEntry 36 } 
	
bgs10SPvpAllowEFC	OBJECT-TYPE
	SYNTAX		BITS { not-allow(0),
					   allow(1)
					 }
	MAX-ACCESS	read-only
	STATUS		current
	DESCRIPTION
		"."
	::= { bgs10SPvpEntry 37 } 
	
bgs10SPvpEPDFlag		OBJECT-TYPE
	SYNTAX		BITS { not-set(0),
					   set(1)
					 }
	MAX-ACCESS	read-only
	STATUS		current
	DESCRIPTION
		"."
	::= { bgs10SPvpEntry 38 } 
	
bgs10SPvpFeeGleanFlag	OBJECT-TYPE
	SYNTAX		BITS { not-glean(0),
					   glean(1)
					 }
	MAX-ACCESS	read-only
	STATUS		current
	DESCRIPTION
		"."
	::= { bgs10SPvpEntry 39 } 

bgs10SPvpRetries	OBJECT-TYPE
	SYNTAX		UChar
	MAX-ACCESS	read-only
	STATUS		current
	DESCRIPTION
		"."
	::= { bgs10SPvpEntry 40 } 

bgs10SPvpInterval	OBJECT-TYPE
	SYNTAX		UChar
	MAX-ACCESS	read-only
	STATUS		current
	DESCRIPTION
		"."
	::= { bgs10SPvpEntry 41 } 

bgs10SPvpPVCType	OBJECT-TYPE
	SYNTAX		Unsigned32
	MAX-ACCESS	read-only
	STATUS		current
	DESCRIPTION
		"."
	::= { bgs10SPvpEntry 42 } 

bgs10SPvpAlarmStatus	OBJECT-TYPE
	SYNTAX		UShort
	MAX-ACCESS	read-only
	STATUS		current
	DESCRIPTION
		"."
	::= { bgs10SPvpEntry 43 } 

-- ZXB10 Version
bgs10Version	OBJECT IDENTIFIER	::= { zxbgs10mib 46}
	
bgs10VersionRowStatus OBJECT-TYPE 
	SYNTAX		INTEGER
	MAX-ACCESS	read-write
	STATUS		current
	DESCRIPTION
		""
	::= { bgs10Version 1}

bgs10MIBVersion	OBJECT-TYPE 
	SYNTAX		OCTET STRING(SIZE(50))
	MAX-ACCESS	read-write
	STATUS		current
	DESCRIPTION
		""
	::= { bgs10Version 2}
	
bgs10MIBVersionModule OBJECT-TYPE
	SYNTAX		INTEGER
	MAX-ACCESS	read-write
	STATUS		current
	DESCRIPTION
		""
	::= { bgs10Version 3}
	
-- LdpTrace
bgs10LdpTrace	OBJECT IDENTIFIER	::= { zxbgs10mib 47}
	
bgs10LdpTraceRowStatus OBJECT-TYPE 
	SYNTAX		UChar
	MAX-ACCESS	read-write
	STATUS		current
	DESCRIPTION
		""
	::= { bgs10LdpTrace 1}

bgs10LdpTraceModule	OBJECT-TYPE 
	SYNTAX		UChar
	MAX-ACCESS	read-write
	STATUS		current
	DESCRIPTION
		""
	::= { bgs10LdpTrace 2}
	
bgs10LdpTraceIfIndex	OBJECT-TYPE 
	SYNTAX		UShort
	MAX-ACCESS	read-write
	STATUS		current
	DESCRIPTION
		""
	::= { bgs10LdpTrace 3}

bgs10LdpTraceOutIfIndex	OBJECT-TYPE 
	SYNTAX		UShort
	MAX-ACCESS	read-write
	STATUS		current
	DESCRIPTION
		""
	::= { bgs10LdpTrace 4}

bgs10LdpTraceLocalLspId	OBJECT-TYPE 
	SYNTAX		UShort
	MAX-ACCESS	read-write
	STATUS		current
	DESCRIPTION
		""
	::= { bgs10LdpTrace 5}

bgs10LdpTraceIngressId	OBJECT-TYPE 
	SYNTAX		Unsigned32
	MAX-ACCESS	read-write
	STATUS		current
	DESCRIPTION
		""
	::= { bgs10LdpTrace 6}
	
bgs10LdpTraceLdpFlag	OBJECT-TYPE 
	SYNTAX		UChar
	MAX-ACCESS	read-write
	STATUS		current
	DESCRIPTION
		""
	::= { bgs10LdpTrace 7}

bgs10LdpTraceNiLdpFlag	OBJECT-TYPE 
	SYNTAX		UChar
	MAX-ACCESS	read-write
	STATUS		current
	DESCRIPTION
		""
	::= { bgs10LdpTrace 8}

bgs10LdpTraceLspFlag	OBJECT-TYPE 
	SYNTAX		UChar
	MAX-ACCESS	read-write
	STATUS		current
	DESCRIPTION
		""
	::= { bgs10LdpTrace 9}	
	
	
bgs10LdpTraceErNotifyFlag	OBJECT-TYPE 
	SYNTAX		UChar
	MAX-ACCESS	read-write
	STATUS		current
	DESCRIPTION
		""
	::= { bgs10LdpTrace 10}

bgs10LdpTraceErrcode	OBJECT-TYPE 
	SYNTAX		Unsigned32
	MAX-ACCESS	read-write
	STATUS		current
	DESCRIPTION
		""
	::= { bgs10LdpTrace 11}
	
bgs10PPVCServer	OBJECT IDENTIFIER	::= { zxbgs10mib 48}
	
bgs10PPVCServerRowStatus OBJECT-TYPE 
	SYNTAX		UChar
	MAX-ACCESS	read-write
	STATUS		current
	DESCRIPTION
		""
	::= { bgs10PPVCServer 1}
	
bgs10PPVCServerTimerType OBJECT-TYPE 
	SYNTAX		UChar
	MAX-ACCESS	read-write
	STATUS		current
	DESCRIPTION
		""
	::= { bgs10PPVCServer 2}

bgs10PPVCServerNewValue OBJECT-TYPE 
	SYNTAX		UShort
	MAX-ACCESS	read-write
	STATUS		current
	DESCRIPTION
		""
	::= { bgs10PPVCServer 3}

bgs10PPVCServerActCause OBJECT-TYPE 
	SYNTAX		UChar
	MAX-ACCESS	read-write
	STATUS		current
	DESCRIPTION
		""
	::= { bgs10PPVCServer 4}

bgs10PPVCServerActResult OBJECT-TYPE 
	SYNTAX		UShort
	MAX-ACCESS	read-write
	STATUS		current
	DESCRIPTION
		""
	::= { bgs10PPVCServer 5}

bgs10PPVCServerLPort OBJECT-TYPE 
	SYNTAX		UChar
	MAX-ACCESS	read-write
	STATUS		current
	DESCRIPTION
		""
	::= { bgs10PPVCServer 6}

bgs10PPVCServerLVPI OBJECT-TYPE 
	SYNTAX		UShort
	MAX-ACCESS	read-write
	STATUS		current
	DESCRIPTION
		""
	::= { bgs10PPVCServer 7}

bgs10PPVCServerLVCI OBJECT-TYPE 
	SYNTAX		UShort
	MAX-ACCESS	read-write
	STATUS		current
	DESCRIPTION
		""
	::= { bgs10PPVCServer 8}

bgs10PPVCServerLModule OBJECT-TYPE 
	SYNTAX		UChar
	MAX-ACCESS	read-write
	STATUS		current
	DESCRIPTION
		""
	::= { bgs10PPVCServer 9}

-- bgs10NMPSVCTable
bgs10NMPSVCTable	OBJECT-TYPE
	SYNTAX		SEQUENCE OF BGS10NMPSVCEntry
	MAX-ACCESS	not-accessible
	STATUS		current
	DESCRIPTION
		"."
	::= { zxbgs10mib 49}
	
bgs10NMPSVCEntry	OBJECT-TYPE
	SYNTAX		BGS10NMPSVCEntry
	MAX-ACCESS	not-accessible
	STATUS		current
	DESCRIPTION
		"An entry in the table."
	INDEX {	
		bgs10NMPSVCLModule,
		bgs10NMPSVCLPort,
		bgs10NMPSVCLVPI,
		bgs10NMPSVCLVCI
		}
	::= { bgs10NMPSVCTable 1}
	
BGS10NMPSVCEntry ::=
	SEQUENCE {
		bgs10NMPSVCRowStatus				RowStatus,
		bgs10NMPSVCLModule					UChar,
		bgs10NMPSVCLPort					UChar,
		bgs10NMPSVCLVPI						UShort,
		bgs10NMPSVCLVCI						UShort,
		bgs10NMPSVCResult					UShort,
		bgs10NMPSVCBearingEntity			UChar,
		bgs10NMPSVCLStatus					UChar,
		bgs10NMPSVCWStatus					UChar,
		bgs10NMPSVCPStatus					UChar
	}

bgs10NMPSVCRowStatus OBJECT-TYPE 
	SYNTAX		RowStatus
	MAX-ACCESS	read-write
	STATUS		current
	DESCRIPTION
		""
	::= { bgs10NMPSVCEntry 1}

bgs10NMPSVCLModule OBJECT-TYPE 
	SYNTAX		UChar
	MAX-ACCESS	read-write
	STATUS		current
	DESCRIPTION
		""
	::= { bgs10NMPSVCEntry 2}

bgs10NMPSVCLPort OBJECT-TYPE 
	SYNTAX		UChar
	MAX-ACCESS	read-write
	STATUS		current
	DESCRIPTION
		""
	::= { bgs10NMPSVCEntry 3}

bgs10NMPSVCLVPI OBJECT-TYPE 
	SYNTAX		UShort
	MAX-ACCESS	read-write
	STATUS		current
	DESCRIPTION
		""
	::= { bgs10NMPSVCEntry 4}

bgs10NMPSVCLVCI OBJECT-TYPE 
	SYNTAX		UShort
	MAX-ACCESS	read-write
	STATUS		current
	DESCRIPTION
		""
	::= { bgs10NMPSVCEntry 5}

bgs10NMPSVCResult OBJECT-TYPE 
	SYNTAX		UShort
	MAX-ACCESS	read-write
	STATUS		current
	DESCRIPTION
		""
	::= { bgs10NMPSVCEntry 6}

bgs10NMPSVCBearingEntity OBJECT-TYPE 
	SYNTAX		UChar
	MAX-ACCESS	read-write
	STATUS		current
	DESCRIPTION
		""
	::= { bgs10NMPSVCEntry 7}

bgs10NMPSVCLStatus OBJECT-TYPE 
	SYNTAX		UChar
	MAX-ACCESS	read-write
	STATUS		current
	DESCRIPTION
		""
	::= { bgs10NMPSVCEntry 8}

bgs10NMPSVCWStatus OBJECT-TYPE 
	SYNTAX		UChar
	MAX-ACCESS	read-write
	STATUS		current
	DESCRIPTION
		""
	::= { bgs10NMPSVCEntry 9}

bgs10NMPSVCPStatus OBJECT-TYPE 
	SYNTAX		UChar
	MAX-ACCESS	read-write
	STATUS		current
	DESCRIPTION
		""
	::= { bgs10NMPSVCEntry 10}

--the NmsIDInfo table         
bgs10NmsIDInfoTable	OBJECT-TYPE
  	SYNTAX		SEQUENCE OF ZXB10NmsIDInfoEntry
  	MAX-ACCESS	not-accessible
  	STATUS		current
  	DESCRIPTION
  		"."
  	::= { zxbgs10mib 50}
	
bgs10NmsIDInfoEntry	OBJECT-TYPE
  	SYNTAX		ZXB10NmsIDInfoEntry
	MAX-ACCESS	not-accessible
	STATUS		current
	DESCRIPTION
		"An entry in the table."
	INDEX {	
		bgs10NmsDstNetid
		}
	::= { bgs10NmsIDInfoTable 1}
	
ZXB10NmsIDInfoEntry ::=
	SEQUENCE {
		bgs10NmsIDInfoRowStatus				RowStatus,
		bgs10NmsGatewayIP					IpAddress,
		bgs10NmsDstNetid					Unsigned32,
		bgs10NmsDstNetMask					Unsigned32,
		bgs10NmsDstIndex					Unsigned32
	}
	
bgs10NmsIDInfoRowStatus	OBJECT-TYPE
	SYNTAX		RowStatus
	MAX-ACCESS	read-create
	STATUS		current
	DESCRIPTION
		"."
	::= { bgs10NmsIDInfoEntry 1}
	
bgs10NmsGatewayIP	OBJECT-TYPE
	SYNTAX		IpAddress
	MAX-ACCESS	read-create
	STATUS		current
	DESCRIPTION
		"."
	::= { bgs10NmsIDInfoEntry 2}

bgs10NmsDstNetid	OBJECT-TYPE
	SYNTAX		Unsigned32
	MAX-ACCESS	read-create
	STATUS		current
	DESCRIPTION
		"."
	::= { bgs10NmsIDInfoEntry 3}

bgs10NmsDstNetMask	OBJECT-TYPE
	SYNTAX		Unsigned32
	MAX-ACCESS	read-create
	STATUS		current
	DESCRIPTION
		"."
	::= { bgs10NmsIDInfoEntry 4}

bgs10NmsDstIndex	OBJECT-TYPE
	SYNTAX		Unsigned32
	MAX-ACCESS	read-create
	STATUS		current
	DESCRIPTION
		"."
	::= { bgs10NmsIDInfoEntry 5}

-- bgs10NMPSVPTable
bgs10NMPSVPTable	OBJECT-TYPE
	SYNTAX		SEQUENCE OF BGS10NMPSVPEntry
	MAX-ACCESS	not-accessible
	STATUS		current
	DESCRIPTION
		"."
	::= { zxbgs10mib 51}
	
bgs10NMPSVPEntry	OBJECT-TYPE
	SYNTAX		BGS10NMPSVPEntry
	MAX-ACCESS	not-accessible
	STATUS		current
	DESCRIPTION
		"An entry in the table."
	INDEX {	
		bgs10NMPSVPLModule,
		bgs10NMPSVPLPort,
		bgs10NMPSVPLVPI
		}
	::= { bgs10NMPSVPTable 1}
	
BGS10NMPSVPEntry ::=
	SEQUENCE {
		bgs10NMPSVPRowStatus				RowStatus,
		bgs10NMPSVPLModule					UChar,
		bgs10NMPSVPLPort					UChar,
		bgs10NMPSVPLVPI						UShort,
		bgs10NMPSVPResult					UShort,
		bgs10NMPSVPBearingEntity			UChar,
		bgs10NMPSVPLStatus					UChar,
		bgs10NMPSVPWStatus					UChar,
		bgs10NMPSVPPStatus					UChar
	}

bgs10NMPSVPRowStatus OBJECT-TYPE 
	SYNTAX		RowStatus
	MAX-ACCESS	read-write
	STATUS		current
	DESCRIPTION
		""
	::= { bgs10NMPSVPEntry 1}

bgs10NMPSVPLModule OBJECT-TYPE 
	SYNTAX		UChar
	MAX-ACCESS	read-write
	STATUS		current
	DESCRIPTION
		""
	::= { bgs10NMPSVPEntry 2}

bgs10NMPSVPLPort OBJECT-TYPE 
	SYNTAX		UChar
	MAX-ACCESS	read-write
	STATUS		current
	DESCRIPTION
		""
	::= { bgs10NMPSVPEntry 3}

bgs10NMPSVPLVPI OBJECT-TYPE 
	SYNTAX		UShort
	MAX-ACCESS	read-write
	STATUS		current
	DESCRIPTION
		""
	::= { bgs10NMPSVPEntry 4}

bgs10NMPSVPResult OBJECT-TYPE 
	SYNTAX		UShort
	MAX-ACCESS	read-write
	STATUS		current
	DESCRIPTION
		""
	::= { bgs10NMPSVPEntry 5}

bgs10NMPSVPBearingEntity OBJECT-TYPE 
	SYNTAX		UChar
	MAX-ACCESS	read-write
	STATUS		current
	DESCRIPTION
		""
	::= { bgs10NMPSVPEntry 6}

bgs10NMPSVPLStatus OBJECT-TYPE 
	SYNTAX		UChar
	MAX-ACCESS	read-write
	STATUS		current
	DESCRIPTION
		""
	::= { bgs10NMPSVPEntry 7}

bgs10NMPSVPWStatus OBJECT-TYPE 
	SYNTAX		UChar
	MAX-ACCESS	read-write
	STATUS		current
	DESCRIPTION
		""
	::= { bgs10NMPSVPEntry 8}

bgs10NMPSVPPStatus OBJECT-TYPE 
	SYNTAX		UChar
	MAX-ACCESS	read-write
	STATUS		current
	DESCRIPTION
		""
	::= { bgs10NMPSVPEntry 9}

-- bgs10NMPSFRTable
bgs10NMPSFRTable	OBJECT-TYPE
	SYNTAX		SEQUENCE OF BGS10NMPSFREntry
	MAX-ACCESS	not-accessible
	STATUS		current
	DESCRIPTION
		"."
	::= { zxbgs10mib 52}
	
bgs10NMPSFREntry	OBJECT-TYPE
	SYNTAX		BGS10NMPSFREntry
	MAX-ACCESS	not-accessible
	STATUS		current
	DESCRIPTION
		"An entry in the table."
	INDEX {	
		bgs10NMPSFRLModule,
		bgs10NMPSFRIfindex,
		bgs10NMPSFRDLCI
		}
	::= { bgs10NMPSFRTable 1}
	
BGS10NMPSFREntry ::=
	SEQUENCE {
		bgs10NMPSFRRowStatus				RowStatus,
		bgs10NMPSFRLModule					UChar,
		bgs10NMPSFRIfindex					UShort,
		bgs10NMPSFRDLCI						UShort,
		bgs10NMPSFRResult					UShort,
		bgs10NMPSFRBearingEntity			UChar,
		bgs10NMPSFRLStatus					UChar,
		bgs10NMPSFRWStatus					UChar,
		bgs10NMPSFRPStatus					UChar
	}

bgs10NMPSFRRowStatus OBJECT-TYPE 
	SYNTAX		RowStatus
	MAX-ACCESS	read-write
	STATUS		current
	DESCRIPTION
		""
	::= { bgs10NMPSFREntry 1}

bgs10NMPSFRLModule OBJECT-TYPE 
	SYNTAX		UChar
	MAX-ACCESS	read-write
	STATUS		current
	DESCRIPTION
		""
	::= { bgs10NMPSFREntry 2}

bgs10NMPSFRIfindex OBJECT-TYPE 
	SYNTAX		UShort
	MAX-ACCESS	read-write
	STATUS		current
	DESCRIPTION
		""
	::= { bgs10NMPSFREntry 3}

bgs10NMPSFRDLCI OBJECT-TYPE 
	SYNTAX		UShort
	MAX-ACCESS	read-write
	STATUS		current
	DESCRIPTION
		""
	::= { bgs10NMPSFREntry 4}

bgs10NMPSFRResult OBJECT-TYPE 
	SYNTAX		UShort
	MAX-ACCESS	read-write
	STATUS		current
	DESCRIPTION
		""
	::= { bgs10NMPSFREntry 5}

bgs10NMPSFRBearingEntity OBJECT-TYPE 
	SYNTAX		UChar
	MAX-ACCESS	read-write
	STATUS		current
	DESCRIPTION
		""
	::= { bgs10NMPSFREntry 6}

bgs10NMPSFRLStatus OBJECT-TYPE 
	SYNTAX		UChar
	MAX-ACCESS	read-write
	STATUS		current
	DESCRIPTION
		""
	::= { bgs10NMPSFREntry 7}

bgs10NMPSFRWStatus OBJECT-TYPE 
	SYNTAX		UChar
	MAX-ACCESS	read-write
	STATUS		current
	DESCRIPTION
		""
	::= { bgs10NMPSFREntry 8}

bgs10NMPSFRPStatus OBJECT-TYPE 
	SYNTAX		UChar
	MAX-ACCESS	read-write
	STATUS		current
	DESCRIPTION
		""
	::= { bgs10NMPSFREntry 9}

-- bgs10NMPSCESTable
bgs10NMPSCESTable	OBJECT-TYPE
	SYNTAX		SEQUENCE OF BGS10NMPSCESEntry
	MAX-ACCESS	not-accessible
	STATUS		current
	DESCRIPTION
		"."
	::= { zxbgs10mib 53}
	
bgs10NMPSCESEntry	OBJECT-TYPE
	SYNTAX		BGS10NMPSCESEntry
	MAX-ACCESS	not-accessible
	STATUS		current
	DESCRIPTION
		"An entry in the table."
	INDEX {	
		bgs10NMPSCESIfindex
		}
	::= { bgs10NMPSCESTable 1}
	
BGS10NMPSCESEntry ::=
	SEQUENCE {
		bgs10NMPSCESRowStatus				RowStatus,
		bgs10NMPSCESIfindex					UShort,
		bgs10NMPSCESResult					UShort,
		bgs10NMPSCESBearingEntity			UChar,
		bgs10NMPSCESLStatus					UChar,
		bgs10NMPSCESWStatus					UChar,
		bgs10NMPSCESPStatus					UChar
	}

bgs10NMPSCESRowStatus OBJECT-TYPE 
	SYNTAX		RowStatus
	MAX-ACCESS	read-write
	STATUS		current
	DESCRIPTION
		""
	::= { bgs10NMPSCESEntry 1}

bgs10NMPSCESIfindex OBJECT-TYPE 
	SYNTAX		UShort
	MAX-ACCESS	read-write
	STATUS		current
	DESCRIPTION
		""
	::= { bgs10NMPSCESEntry 2}

bgs10NMPSCESResult OBJECT-TYPE 
	SYNTAX		UShort
	MAX-ACCESS	read-write
	STATUS		current
	DESCRIPTION
		""
	::= { bgs10NMPSCESEntry 3}

bgs10NMPSCESBearingEntity OBJECT-TYPE 
	SYNTAX		UChar
	MAX-ACCESS	read-write
	STATUS		current
	DESCRIPTION
		""
	::= { bgs10NMPSCESEntry 4}

bgs10NMPSCESLStatus OBJECT-TYPE 
	SYNTAX		UChar
	MAX-ACCESS	read-write
	STATUS		current
	DESCRIPTION
		""
	::= { bgs10NMPSCESEntry 5}

bgs10NMPSCESWStatus OBJECT-TYPE 
	SYNTAX		UChar
	MAX-ACCESS	read-write
	STATUS		current
	DESCRIPTION
		""
	::= { bgs10NMPSCESEntry 6}

bgs10NMPSCESPStatus OBJECT-TYPE 
	SYNTAX		UChar
	MAX-ACCESS	read-write
	STATUS		current
	DESCRIPTION
		""
	::= { bgs10NMPSCESEntry 7}

--bgs10NMSServer
bgs10NMSServer	OBJECT-TYPE
	SYNTAX		SEQUENCE OF BGS10NMSServerEntry
	MAX-ACCESS	not-accessible
	STATUS		current
	DESCRIPTION
		"."
	::= { zxbgs10mib 54}
	
bgs10NMSServerEntry	OBJECT-TYPE
	SYNTAX		BGS10NMSServerEntry
	MAX-ACCESS	not-accessible
	STATUS		current
	DESCRIPTION
		"An entry in the table."
	INDEX {	
		bgs10NMSServerIpAddress
		}
	::= { bgs10NMSServer 1}
	
BGS10NMSServerEntry ::=
	SEQUENCE {
		bgs10NMSServerRowStatus				RowStatus,
		bgs10NMSServerIpAddress				IpAddress
	}

bgs10NMSServerRowStatus OBJECT-TYPE 
	SYNTAX		RowStatus
	MAX-ACCESS	read-write
	STATUS		current
	DESCRIPTION
		""
	::= { bgs10NMSServerEntry 1}

bgs10NMSServerIpAddress OBJECT-TYPE 
	SYNTAX		IpAddress
	MAX-ACCESS	read-write
	STATUS		current
	DESCRIPTION
		""
	::= { bgs10NMSServerEntry 2}

--dsx1ConfigTable
dsx1ConfigTable OBJECT-TYPE
	SYNTAX	SEQUENCE OF E1ConfEntry
	MAX-ACCESS	not-accessible
	STATUS	current
	DESCRIPTION
		"A table of T1/E1 switch port configuration information."
	::= { zxbgs10mib 55 }

dsx1ConfigEntry OBJECT-TYPE
	SYNTAX	E1ConfEntry
	MAX-ACCESS	not-accessible
	STATUS	current
	DESCRIPTION
		"A table entry containing T1/E1 configuration information for each
		port. Not all RFC1406 configuration table variables are
		included, and some are modified."
	INDEX	{ dsx1ConfModule, dsx1ConfPort }
	::= { dsx1ConfigTable 1 }

E1ConfEntry ::=
	SEQUENCE {
		dsx1RowStatus			RowStatus,
		dsx1ConfModule			INTEGER,
		dsx1ConfPort			INTEGER,
		dsx1ConfLineType		INTEGER,
		dsx1ConfLineCoding		INTEGER,
		dsx1ConfLoopbackConfig	INTEGER,
		dsx1ConfLineStatus		INTEGER,
        dsx1ConfSignalMode      INTEGER,
		dsx1ConfTxClockSource	INTEGER,
		dsx1ConfIdleCells		INTEGER,
		dsx1ConfRxScrambling	INTEGER,
		dsx1ConfTxScrambling	INTEGER,
		dsx1ConfChannelNumber	INTEGER,
		dsx1ConfChannelization	INTEGER
}

dsx1RowStatus OBJECT-TYPE
	SYNTAX	RowStatus
	MAX-ACCESS	read-write
	STATUS	current
	DESCRIPTION
		"."
	::= { dsx1ConfigEntry 1 }

dsx1ConfModule OBJECT-TYPE
	SYNTAX	INTEGER
	MAX-ACCESS	read-write
	STATUS	current
	DESCRIPTION
		"The network module of this port."
	::= { dsx1ConfigEntry 2 }

dsx1ConfPort OBJECT-TYPE
	SYNTAX	INTEGER
	MAX-ACCESS	read-write
	STATUS	current
	DESCRIPTION
		"The number of this port."
	::= { dsx1ConfigEntry 3 }

dsx1ConfLineType OBJECT-TYPE
	SYNTAX	INTEGER {
                     other(1),
                     dsx1E1(4),
                     dsx1E1CRC(5),
                     dsx1E1MF(6),
                     dsx1E1CRCMF(7),
                     dsx1E1Unframed(9),
                     dsx1Unframed(8),
                     dsx1ESF(2),
                     dsx1D4(3)
		}
	MAX-ACCESS	read-write
	STATUS	current
	DESCRIPTION
		"This variable indicates the variety of E1 Line implementing
		this circuit. The type of circuit affects the number of bits
		per second that the circuit can reasonably carry, as well as
		the interpretation of the usage and error statistics. This
		variable is defined in the rfc1406 configuration table as
		dsx1LineType.

		According to rfc1406, the different values are:
                 dsx1ESF         Extended SuperFrame DS1 (T1.107)
                 dsx1D4          AT&T D4 format DS1 (T1.107)
                 dsx1E1          ITU-T Recommendation G.704
                                  (Table 4a)
                 dsx1E1-CRC      ITU-T Recommendation G.704
                                  (Table 4b)
                 dsxE1-MF        G.704 (Table 4a) with TS16
                                  multiframing enabled
                 dsx1E1-CRC-MF   G.704 (Table 4b) with TS16
                                  multiframing enabled
                 dsx1Unframed    DS1 with No Framing
                 dsx1E1Unframed  E1 with No Framing (G.703)"
 	::= { dsx1ConfigEntry 4 }

dsx1ConfLineCoding OBJECT-TYPE
	SYNTAX	INTEGER
	MAX-ACCESS	read-write
	STATUS	current
	DESCRIPTION
		"This variable describes the variety of Zero Code suppression
		used on this link, which in turn affects a number of its
		characteristics. e1AMI(3) refers to a mode wherein no zero
		code suppression is present and the line encoding does not
		solve the problem directly. In this application, the higher
		layer must provide data which meets or exceeds the pulse
		density re-quirements, such as inverting HDLC data. This
		variable is defined in the rfc1406 configuration table as
		dsx1LineCoding."
	::= { dsx1ConfigEntry 5 }

dsx1ConfLoopbackConfig OBJECT-TYPE
	SYNTAX	INTEGER {
                      dsx1NoLoop(1),
                      dsx1PayloadLoop(2),
                      dsx1LineLoop(3),
                      dsx1OtherLoop(4),
                      dsx1InwardLoop(5),
                      dsx1DualLoop(6)
		}
	MAX-ACCESS	read-write
	STATUS	current
	DESCRIPTION
		"This variable represents the loopback configuration of the E1
		interface. This variable is defined in the rfc1406
		configuration table as dsx1LoopbackConfig, with slightly
		different values.

		e1NoLoop (1) means that the interface is not in a loopback
		state.

		e1LineLoop (2) means that cells that are processed by the
		receiving component are not written into the receive FIFO, but
		into the transmit FIFO for retransmission.

		e1PayloadLoop (3) means that the receive signal is looped back
		for retransmission after it has passed through the port's
		reframing function.

		e1DiagLoop (4) means that the transmit data stream is looped
		back to the receiver.

		e1OtherLoop (5) means that the interface is in a loopback that
		is not defined here."
	DEFVAL	{ 1 }
	::= { dsx1ConfigEntry 6 }

dsx1ConfLineStatus OBJECT-TYPE
	SYNTAX	INTEGER (1..65534)
	MAX-ACCESS	read-write
	STATUS	current
	DESCRIPTION
		"This variable indicates the Line Status of the interface. A
		similar object is defined in the rfc1406 configuration table as
		dsx1LineStatus. The variable contains loopback state
		information and failure state information. It is a bit map
		represented as a sum. The e1NoAlarm should be set if and only
		if no other flag is set.

		The various bit positions are:
      1     dsx1NoAlarm           No alarm present
      2     dsx1RcvFarEndLOF      Far end LOF (a.k.a., Yellow Alarm)
      4     dsx1XmtFarEndLOF      Near end sending LOF Indication
      8     dsx1RcvAIS            Far end sending AIS
     16     dsx1XmtAIS            Near end sending AIS
     32     dsx1LossOfFrame       Near end LOF (a.k.a., Red Alarm)
     64     dsx1LossOfSignal      Near end Loss Of Signal
    128     dsx1LoopbackState     Near end is looped
    256     dsx1T16AIS            E1 TS16 AIS
    512     dsx1RcvFarEndLOMF     Far End Sending TS16 LOMF
   1024     dsx1XmtFarEndLOMF     Near End Sending TS16 LOMF
   2048     dsx1RcvTestCode       Near End detects a test code
   4096     dsx1OtherFailure      any line status not defined here
   8192     dsx1UnavailSigState   Near End in Unavailable Signal
                                  State
  16384     dsx1NetEquipOOS       Carrier Equipment Out of Service
  32768     dsx1RcvPayloadAIS     DS2 Payload AIS
  65536     dsx1Ds2PerfThreshold  DS2 Performance Threshold
                                  Exceeded"
	::= { dsx1ConfigEntry 7 }

     dsx1ConfSignalMode OBJECT-TYPE
          SYNTAX  INTEGER
          MAX-ACCESS  read-write
          STATUS  current
          DESCRIPTION
            "."
    ::= { dsx1ConfigEntry 8 }

dsx1ConfTxClockSource OBJECT-TYPE
	SYNTAX	INTEGER {
                     loopTiming(1),
                     localTiming(2),
                     throughTiming(3)
		}
	MAX-ACCESS	read-write
	STATUS	current
	DESCRIPTION
		"The source of the transmit clock. rxTiming(1) indicated that
		the recovered receive clock is used as the transmit clock.
		localTiming(2) indicates that a local source clock is used as
		the transmit clock. To determine which local source clock is
		used advise the ntGlobalClock in the netmodTimingTable for this
		netmod (refer to the Fore-Switch-MIB for more information)."
	DEFVAL	{ 2 }
	::= { dsx1ConfigEntry 9 }

dsx1ConfIdleCells OBJECT-TYPE
	SYNTAX	INTEGER {
		unassigned(1),
		idle(2)
		}
	MAX-ACCESS	read-write
	STATUS	current
	DESCRIPTION
		"This variable indicates the types of cells that should be sent
		in case there is no real data to send. According to the ATM
		Forum, Unassigned cells should be sent (octet 1-3 are 0's,
		octet 4 is 0000xxx0, where x is 'don't care'). According to the
		CCITT specifications, Idle cells should be sent (everything is
		'0' except for the CLP bit which is '1'). By default,
		unassigned cells are transmitted is case there is no data to
		send."
	DEFVAL	{ 1 }
	::= { dsx1ConfigEntry 10 }

     
dsx1ConfRxScrambling OBJECT-TYPE
	SYNTAX  INTEGER {
		descrambling(1),
		noDescrambling(2)
		}
	MAX-ACCESS  read-write
	STATUS  current
	DESCRIPTION
		"This variable indicates whether the information is being
		descrambled on receiving. It should be set the same as the
		transmitting side."
	DEFVAL { 1 }
	::= { dsx1ConfigEntry 11 }

dsx1ConfTxScrambling OBJECT-TYPE
	SYNTAX  INTEGER {
		scrambling(1),
		noScrambling(2)
		}
	MAX-ACCESS  read-write
	STATUS  current
	DESCRIPTION
		"This variable indicates whether the information (48 octet
		payload) is being scrambled before transmitting. It should
		be set the same as the receiving side."
	DEFVAL { 1 }
	::= { dsx1ConfigEntry 12 }

     dsx1ConfChannelNumber  OBJECT-TYPE
          SYNTAX      INTEGER (0..28)
          MAX-ACCESS  read-write
          STATUS      current
          DESCRIPTION
                 "This variable represents the channel number of
                 the DS1/E1 on its parent Ds2/E2 or DS3/E3.  A
                 value of 0 indicated this DS1/E1 does not have a
                 parent DS3/E3."

     ::= { dsx1ConfigEntry 13 }

     dsx1ConfChannelization  OBJECT-TYPE
          SYNTAX      INTEGER {
                         disabled(1),
                         enabledDs0(2)
                      }
          MAX-ACCESS  read-write
          STATUS      current
          DESCRIPTION
                 "Indicates whether this ds1/e1 is channelized or
                 unchannelized.  The value of enabledDs0 indicates
                 that this is a DS1 channelized into DS0s.  The
                 value of enabledDs1 indicated that this is a DS2
                 channelized into DS1s.  Setting this value will
                 cause the creation or deletion of entries in the
                 ifTable for the DS0s that are within the DS1."
     ::= { dsx1ConfigEntry 14 }

-- dsx3ConfigTable
dsx3ConfigTable OBJECT-TYPE
	SYNTAX	SEQUENCE OF E3ConfEntry
	MAX-ACCESS	not-accessible
	STATUS	current
	DESCRIPTION
		"A table of T3/E3 switch port configuration information."
	::= { zxbgs10mib 56 }

dsx3ConfigEntry OBJECT-TYPE
	SYNTAX	E3ConfEntry
	MAX-ACCESS	not-accessible
	STATUS	current
	DESCRIPTION
		"A table entry containing T3/E3 configuration information for each
		port. Not all RFC1406 configuration table variables are
		included, and some are modified."
	INDEX	{ 
		dsx3ConfModule, 
		dsx3ConfPort
		}
	::= { dsx3ConfigTable 1 }

E3ConfEntry ::=
	SEQUENCE {
		dsx3RowStatus			RowStatus,
		dsx3ConfModule			INTEGER,
		dsx3ConfPort			INTEGER,
		dsx3ConfLineType		INTEGER,
		dsx3ConfLineCoding		INTEGER,
		dsx3ConfLoopbackConfig	INTEGER,
		dsx3ConfLineStatus		INTEGER,
		dsx3ConfTxClockSource	INTEGER,
		dsx3ConfIdleCells		INTEGER,
		dsx3ConfRxScrambling	INTEGER,
		dsx3ConfTxScrambling	INTEGER,
		dsx3ConfChannelization	INTEGER,
		dsx3Ds1ForRemoteLoop	INTEGER
}

dsx3RowStatus OBJECT-TYPE
	SYNTAX	RowStatus
	MAX-ACCESS	read-write
	STATUS	current
	DESCRIPTION
		"."
	::= { dsx3ConfigEntry 1 }

dsx3ConfModule OBJECT-TYPE
	SYNTAX	INTEGER
	MAX-ACCESS	read-write
	STATUS	current
	DESCRIPTION
		"The network module of this port."
	::= { dsx3ConfigEntry 2 }

dsx3ConfPort OBJECT-TYPE
	SYNTAX	INTEGER
	MAX-ACCESS	read-write
	STATUS	current
	DESCRIPTION
		"The number of this port."
	::= { dsx3ConfigEntry 3 }

dsx3ConfLineType OBJECT-TYPE
	SYNTAX	INTEGER {
                     e3other(6),
                     e3Framed(7),
                     e3Plcp(8),
                     dsx3ClearChannel(5),
                     dsx3other(1),
                     dsx3M23(2),
                     dsx3SYNTRAN(3),
                     dsx3CbitParity(4)
		}
          MAX-ACCESS  read-write
          STATUS  current
          DESCRIPTION
                 "This variable indicates the variety of DS3 C-bit
                 or E3 application implementing this interface. The
                 type of interface affects the interpretation of
                 the usage and error statistics.  The rate of DS3
                 is 44.736 Mbps and E3 is 34.368 Mbps.  The
                 dsx3ClearChannel value means that the C-bits are
                 not used except for sending/receiving AIS.
                 The values, in sequence, describe:

                 TITLE:            SPECIFICATION:
                 dsx3M23            ANSI T1.107-1988 [9]
                 dsx3SYNTRAN        ANSI T1.107-1988 [9]
                 dsx3CbitParity     ANSI T1.107a-1990 [9a]
                 dsx3ClearChannel   ANSI T1.102-1987 [8]
                 e3Framed           CCITT G.751 [12]
                 e3Plcp             ETSI T/NA(91)18 [13]."
          ::= { dsx3ConfigEntry 4 }

dsx3ConfLineCoding OBJECT-TYPE
          SYNTAX  INTEGER {
                     dsx3Other(1),
                     e3HDB3(3),
                     dsx3B3ZS(2)
                 }
          MAX-ACCESS  read-write
          STATUS  current
          DESCRIPTION
                 "This variable describes the variety of Zero Code
                 Suppression used on this interface, which in turn
                 affects a number of its characteristics.

                 dsx3B3ZS and e3HDB3 refer to the use of specified
                 patterns of normal bits and bipolar violations
                 which are used to replace sequences of zero bits
                 of a specified length."
          ::= { dsx3ConfigEntry 5 }

dsx3ConfLoopbackConfig OBJECT-TYPE
	SYNTAX	INTEGER {
		ds3NoLoop (1),
		ds3PayloadLoop (3),
		ds3LineLoop (5),
		ds3OtherLoop (6)
		}
	MAX-ACCESS	read-write
	STATUS	current
	DESCRIPTION
		"This variable represents the loopback configuration of the DS3
		interface. This variable is defined in the rfc1407
		configuration table as dsx3LoopbackConfig, with slightly
		different values.

		ds3NoLoop (1) means that the interface is not in a loopback
		state.

		ds3CellLoop (2) means that cells that are processed by the
		receiving component are not written into the receive FIFO, but
		into the transmit FIFO for retransmission.

		ds3PayloadLoop (3) means that the receive signal is looped back
		for retransmission after it has passed through the port's
		reframing function.

		ds3DiagLoop (4) means that the transmit data stream is looped
		back to the receiver.

		ds3LineLoop (5) is only supported on series B and later
		netmods.

		ds3OtherLoop (6) means that the interface is in a loopback that
		is not defined here."
	DEFVAL	{ 1 }
	::= { dsx3ConfigEntry 6 }

dsx3ConfLineStatus OBJECT-TYPE
          SYNTAX  INTEGER (1..4095)
          MAX-ACCESS  read-write
          STATUS  current
          DESCRIPTION
                 "This variable indicates the Line Status of the
                 interface.  It contains loopback state information
                 and failure state information.  The dsx3LineStatus
                 is a bit map represented as a sum, therefore, it
                 can represent multiple failures and a loopback
                 (see dsx3LoopbackConfig object for the type of
                 loopback) simultaneously.  The dsx3NoAlarm must be
                 set if and only if no other flag is set.

                 If the dsx3loopbackState bit is set, the loopback
                 in effect can be determined from the
                 dsx3loopbackConfig object.
       The various bit positions are:
        1     dsx3NoAlarm         No alarm present
        2     dsx3RcvRAIFailure   Receiving Yellow/Remote
                                  Alarm Indication
        4     dsx3XmitRAIAlarm    Transmitting Yellow/Remote
                                  Alarm Indication
        8     dsx3RcvAIS          Receiving AIS failure state
       16     dsx3XmitAIS         Transmitting AIS
       32     dsx3LOF             Receiving LOF failure state
       64     dsx3LOS             Receiving LOS failure state
      128     dsx3LoopbackState   Looping the received signal
      256     dsx3RcvTestCode     Receiving a Test Pattern
      512     dsx3OtherFailure    any line status not defined
                                  here
     1024     dsx3UnavailSigState Near End in Unavailable Signal
                                  State
     2048     dsx3NetEquipOOS     Carrier Equipment Out of Service"
     ::= { dsx3ConfigEntry 7 }

dsx3ConfTxClockSource OBJECT-TYPE
     SYNTAX  INTEGER {
                loopTiming(1),
                localTiming(2),
                throughTiming(3)
            }
     MAX-ACCESS  read-write
     STATUS  current
     DESCRIPTION
            "The source of Transmit Clock.

            loopTiming indicates that the recovered receive clock
            is used as the transmit clock.

            localTiming indicates that a local clock source is used
            or that an external clock is attached to the box
            containing the interface.

            throughTiming indicates that transmit clock is derived
            from the recovered receive clock of another DS3
            interface."
          ::= { dsx3ConfigEntry 8 }

dsx3ConfIdleCells OBJECT-TYPE
	SYNTAX	INTEGER {
		unassigned(1),
		idle(2)
		}
	MAX-ACCESS	read-write
	STATUS	current
	DESCRIPTION
		"This variable indicates the types of cells that should be sent
		in case there is no real data to send. According to the ATM
		Forum, Unassigned cells should be sent (octet 1-3 are 0's,
		octet 4 is 0000xxx0, where x is 'don't care'). According to the
		CCITT specifications, Idle cells should be sent (everything is
		'0' except for the CLP bit which is '1'). By default,
		unassigned cells are transmitted is case there is no data to
		send."
	DEFVAL	{ 1 }
	::= { dsx3ConfigEntry 9 }

dsx3ConfRxScrambling OBJECT-TYPE
	SYNTAX	INTEGER {
		descrambling(1),
		noDescrambling(2)
		}
	MAX-ACCESS	read-write
	STATUS	current
	DESCRIPTION
		"This variable indicates whether the information is being
		descrambled on receiving. It should be set the same as the
		transmitting side."
	DEFVAL	{ 2 }
	::= { dsx3ConfigEntry 10 }

dsx3ConfTxScrambling OBJECT-TYPE
	SYNTAX	INTEGER {
		scrambling(1),
		noScrambling(2)
		}
	MAX-ACCESS	read-write
	STATUS	current
	DESCRIPTION
		"This variable indicates whether the information (48 octet
		payload) is being scrambled before transmitting. It should be
		set the same as the receiving side."
	DEFVAL	{ 2 }
	::= { dsx3ConfigEntry 11 }

     dsx3ConfChannelization  OBJECT-TYPE
          SYNTAX      INTEGER {
                         disabled(1),
                         enabledDs1(2),
                         enabledDs2(3)
                      }
          MAX-ACCESS  read-write
          STATUS      current
          DESCRIPTION
                 "Indicates whether this ds3/e3 is channelized or
                 unchannelized.  The value of enabledDs1 indicates
                 that this is a DS3 channelized into DS1s.  The
                 value of enabledDs3 indicated that this is a DS3
                 channelized into DS2s.  Setting this object will
                 cause the creation or deletion of DS2 or DS1
                 entries in the ifTable.  "
     ::= { dsx3ConfigEntry 12 }

     dsx3Ds1ForRemoteLoop  OBJECT-TYPE
          SYNTAX      INTEGER (0..29)

          MAX-ACCESS  read-write
          STATUS      current
          DESCRIPTION
                 "Indicates which ds1/e1 on this ds3/e3 will be
                 indicated in the remote ds1 loopback request.  A
                 value of 0 means no DS1 will be looped.  A value
                 of 29 means all ds1s/e1s will be looped."
     ::= { dsx3ConfigEntry 13 }

-- bgs10IfTSTable
bgs10TSTable OBJECT-TYPE
	SYNTAX	SEQUENCE OF BGS10TSEntry
	MAX-ACCESS	not-accessible
	STATUS	current
	DESCRIPTION
		"A table of T3/E3 switch port configuration information."
	::= { zxbgs10mib 57 }

bgs10TSEntry OBJECT-TYPE
	SYNTAX	BGS10TSEntry
	MAX-ACCESS	not-accessible
	STATUS	current
	DESCRIPTION
		"A table entry containing T3/E3 configuration information for each
		port. Not all RFC1406 configuration table variables are
		included, and some are modified."
	INDEX	{ 
		bgs10TSIfindex
		}
	::= { bgs10TSTable 1 }
	
BGS10TSEntry ::=
	SEQUENCE {
		bgs10TSRowStatus		RowStatus,
		bgs10TSSerType			UCHAR,
		bgs10TSAALType			UCHAR,
		bgs10TSTSNo				INTEGER,
		bgs10TSIfindex			UShort
}

bgs10TSRowStatus OBJECT-TYPE
	SYNTAX	RowStatus
	MAX-ACCESS	read-write
	STATUS	current
	DESCRIPTION
		"."
	::= { bgs10TSEntry 1 }

bgs10TSSerType OBJECT-TYPE
	SYNTAX	UCHAR
	MAX-ACCESS	read-write
	STATUS	current
	DESCRIPTION
		"."
	::= { bgs10TSEntry 2 }

bgs10TSAALType OBJECT-TYPE
	SYNTAX	UCHAR
	MAX-ACCESS	read-write
	STATUS	current
	DESCRIPTION
		"."
	::= { bgs10TSEntry 3 }

bgs10TSTSNo OBJECT-TYPE
	SYNTAX	INTEGER
	MAX-ACCESS	read-write
	STATUS	current
	DESCRIPTION
		"."
	::= { bgs10TSEntry 4 }

bgs10TSIfindex OBJECT-TYPE
	SYNTAX	UShort
	MAX-ACCESS	read-write
	STATUS	current
	DESCRIPTION
		"."
	::= { bgs10TSEntry 5 }

-- bgs10Rs232PortTable
bgs10Rs232PortTable OBJECT-TYPE
	SYNTAX	SEQUENCE OF BGS10Rs232PortEntry
	MAX-ACCESS	not-accessible
	STATUS	current
	DESCRIPTION
		"A table of Rs232 Port. V.24/V.35"
	::= { zxbgs10mib 58 }

bgs10Rs232PortEntry OBJECT-TYPE
	SYNTAX	BGS10Rs232PortEntry
	MAX-ACCESS	not-accessible
	STATUS	current
	DESCRIPTION
		"."
	INDEX	{ 
		bgs10rs232PortConfModule,
		bgs10rs232PortConfPort
		}
	::= { bgs10Rs232PortTable 1 }
	
BGS10Rs232PortEntry ::=
	SEQUENCE {
		bgs10rs232PortRowStatus				RowStatus,
		bgs10rs232PortConfModule			UCHAR,
		bgs10rs232PortConfPort				UCHAR,
		bgs10rs232PortType					UCHAR,
		bgs10rs232PortOutSpeed				UCHAR,
		bgs10rs232SyncPortRTSCTSDelay		INTEGER,
		bgs10rs232PortInFlowType			INTEGER,
		bgs10rs232PortOutFlowType			INTEGER,
		bgs10rs232SyncPortClockSource		INTEGER,
		bgs10rs232SyncPortRole				INTEGER,
		bgs10rs232SyncPortRTSControl		INTEGER,
		bgs10rs232SyncPortIdlePattern		INTEGER,
		bgs10rs232PortRTSState				INTEGER,
		bgs10rs232PortCTSState				INTEGER,
		bgs10rs232PortDSRState				INTEGER,
		bgs10rs232PortDTRState				INTEGER,
		bgs10rs232PortDCDState				INTEGER
}

bgs10rs232PortRowStatus OBJECT-TYPE
	SYNTAX	RowStatus
	MAX-ACCESS	read-write
	STATUS	current
	DESCRIPTION
		"."
	::= { bgs10Rs232PortEntry 1 }

bgs10rs232PortConfModule OBJECT-TYPE
	SYNTAX	UCHAR
	MAX-ACCESS	read-write
	STATUS	current
	DESCRIPTION
		"."
	::= { bgs10Rs232PortEntry 2 }

bgs10rs232PortConfPort OBJECT-TYPE
	SYNTAX	UCHAR
	MAX-ACCESS	read-write
	STATUS	current
	DESCRIPTION
		"."
	::= { bgs10Rs232PortEntry 3 }

bgs10rs232PortType OBJECT-TYPE
	SYNTAX	UCHAR
	MAX-ACCESS	read-write
	STATUS	current
	DESCRIPTION
		"."
	::= { bgs10Rs232PortEntry 4 }

bgs10rs232PortOutSpeed OBJECT-TYPE
	SYNTAX	UCHAR
	MAX-ACCESS	read-write
	STATUS	current
	DESCRIPTION
		"."
	::= { bgs10Rs232PortEntry 5 }

bgs10rs232SyncPortRTSCTSDelay OBJECT-TYPE
	SYNTAX	INTEGER
	MAX-ACCESS	read-write
	STATUS	current
	DESCRIPTION
		"."
	::= { bgs10Rs232PortEntry 6 }

bgs10rs232PortInFlowType OBJECT-TYPE
	SYNTAX	INTEGER
	MAX-ACCESS	read-write
	STATUS	current
	DESCRIPTION
		"."
	::= { bgs10Rs232PortEntry 7 }

bgs10rs232PortOutFlowType OBJECT-TYPE
	SYNTAX	INTEGER
	MAX-ACCESS	read-write
	STATUS	current
	DESCRIPTION
		"."
	::= { bgs10Rs232PortEntry 8 }

bgs10rs232SyncPortClockSource OBJECT-TYPE
	SYNTAX	INTEGER
	MAX-ACCESS	read-write
	STATUS	current
	DESCRIPTION
		"."
	::= { bgs10Rs232PortEntry 9 }

bgs10rs232SyncPortRole OBJECT-TYPE
	SYNTAX	INTEGER
	MAX-ACCESS	read-write
	STATUS	current
	DESCRIPTION
		"."
	::= { bgs10Rs232PortEntry 10 }

bgs10rs232SyncPortRTSControl OBJECT-TYPE
	SYNTAX	INTEGER
	MAX-ACCESS	read-write
	STATUS	current
	DESCRIPTION
		"."
	::= { bgs10Rs232PortEntry 11 }

bgs10rs232SyncPortIdlePattern OBJECT-TYPE
	SYNTAX	INTEGER
	MAX-ACCESS	read-write
	STATUS	current
	DESCRIPTION
		"."
	::= { bgs10Rs232PortEntry 12 }

bgs10rs232PortRTSState OBJECT-TYPE
	SYNTAX	INTEGER
	MAX-ACCESS	read-write
	STATUS	current
	DESCRIPTION
		"."
	::= { bgs10Rs232PortEntry 13 }

bgs10rs232PortCTSState OBJECT-TYPE
	SYNTAX	INTEGER
	MAX-ACCESS	read-write
	STATUS	current
	DESCRIPTION
		"."
	::= { bgs10Rs232PortEntry 14 }

bgs10rs232PortDSRState OBJECT-TYPE
	SYNTAX	INTEGER
	MAX-ACCESS	read-write
	STATUS	current
	DESCRIPTION
		"."
	::= { bgs10Rs232PortEntry 15 }

bgs10rs232PortDTRState OBJECT-TYPE
	SYNTAX	INTEGER
	MAX-ACCESS	read-write
	STATUS	current
	DESCRIPTION
		"."
	::= { bgs10Rs232PortEntry 16 }

bgs10rs232PortDCDState OBJECT-TYPE
	SYNTAX	INTEGER
	MAX-ACCESS	read-write
	STATUS	current
	DESCRIPTION
		"."
	::= { bgs10Rs232PortEntry 17 }

-- bgs10Tp25ConfigTable
bgs10Tp25ConfigTable OBJECT-TYPE
	SYNTAX	SEQUENCE OF BGS10Tp25ConfigEntry
	MAX-ACCESS	not-accessible
	STATUS	current
	DESCRIPTION
		""
	::= { zxbgs10mib 59 }

bgs10Tp25ConfigEntry OBJECT-TYPE
	SYNTAX	BGS10Tp25ConfigEntry
	MAX-ACCESS	not-accessible
	STATUS	current
	DESCRIPTION
		"."
	INDEX	{ 
		bgs10Tp25ConfModule,
		bgs10Tp25ConfPort
		}
	::= { bgs10Tp25ConfigTable 1 }
	
BGS10Tp25ConfigEntry ::=
	SEQUENCE {
		bgs10Tp25RowStatus			RowStatus,
		bgs10Tp25ConfModule			UCHAR,
		bgs10Tp25ConfPort			UCHAR,
		bgs10Tp25MediaType			UCHAR,
		bgs10Tp25LoopbackConfig		UCHAR,
		bgs10Tp25RxTiming			UCHAR		
}

bgs10Tp25RowStatus OBJECT-TYPE
	SYNTAX	RowStatus
	MAX-ACCESS	read-write
	STATUS	current
	DESCRIPTION
		"."
	::= { bgs10Tp25ConfigEntry 1 }

bgs10Tp25ConfModule OBJECT-TYPE
	SYNTAX	UCHAR
	MAX-ACCESS	read-write
	STATUS	current
	DESCRIPTION
		"."
	::= { bgs10Tp25ConfigEntry 2 }

bgs10Tp25ConfPort OBJECT-TYPE
	SYNTAX	UCHAR
	MAX-ACCESS	read-write
	STATUS	current
	DESCRIPTION
		"."
	::= { bgs10Tp25ConfigEntry 3 }

bgs10Tp25MediaType OBJECT-TYPE
	SYNTAX	UCHAR
	MAX-ACCESS	read-write
	STATUS	current
	DESCRIPTION
		"."
	::= { bgs10Tp25ConfigEntry 4 }

bgs10Tp25LoopbackConfig OBJECT-TYPE
	SYNTAX	UCHAR
	MAX-ACCESS	read-write
	STATUS	current
	DESCRIPTION
		"."
	::= { bgs10Tp25ConfigEntry 5 }

bgs10Tp25RxTiming OBJECT-TYPE
	SYNTAX	UCHAR
	MAX-ACCESS	read-write
	STATUS	current
	DESCRIPTION
		"."
	::= { bgs10Tp25ConfigEntry 6 }
	
-- bgs10SDHConfigTable
bgs10SDHConfigTable OBJECT-TYPE
	SYNTAX	SEQUENCE OF BGS10SDHConfigEntry
	MAX-ACCESS	not-accessible
	STATUS	current
	DESCRIPTION
		""
	::= { zxbgs10mib 60 }

bgs10SDHConfigEntry OBJECT-TYPE
	SYNTAX	BGS10SDHConfigEntry
	MAX-ACCESS	not-accessible
	STATUS	current
	DESCRIPTION
		"."
	INDEX	{ 
		bgs10SDHSonetConfModule,
		bgs10SDHSonetConfPort
		}
	::= { bgs10SDHConfigTable 1 }
	
BGS10SDHConfigEntry ::=
	SEQUENCE {
		bgs10SDHRowStatus			RowStatus,
		bgs10SDHSonetConfModule		UCHAR,
		bgs10SDHSonetConfPort		UCHAR,
		bgs10SDHMediumType			UCHAR,
		bgs10SDHLineType			UCHAR,
		bgs10SDHLineCodeing			UCHAR,
		bgs10SDHTxClockSource		UCHAR,
		bgs10SDHTxClockClass		UCHAR,
		bgs10SDHRxClockClass		UCHAR,
		bgs10SDHTxScrambling		UCHAR,
		bgs10SDHRxScrambling		UCHAR,
		bgs10SDHIdleUnassignedCells		UCHAR,
		bgs10SDHCellHead			INTEGER
}

bgs10SDHRowStatus OBJECT-TYPE
	SYNTAX	RowStatus
	MAX-ACCESS	read-write
	STATUS	current
	DESCRIPTION
		"."
	::= { bgs10SDHConfigEntry 1 }

bgs10SDHSonetConfModule OBJECT-TYPE
	SYNTAX	UCHAR
	MAX-ACCESS	read-write
	STATUS	current
	DESCRIPTION
		"."
	::= { bgs10SDHConfigEntry 2 }

bgs10SDHSonetConfPort OBJECT-TYPE
	SYNTAX	UCHAR
	MAX-ACCESS	read-write
	STATUS	current
	DESCRIPTION
		"."
	::= { bgs10SDHConfigEntry 3 }

bgs10SDHMediumType OBJECT-TYPE
	SYNTAX	UCHAR
	MAX-ACCESS	read-write
	STATUS	current
	DESCRIPTION
		"."
	::= { bgs10SDHConfigEntry 4 }

bgs10SDHLineType OBJECT-TYPE
	SYNTAX	UCHAR
	MAX-ACCESS	read-write
	STATUS	current
	DESCRIPTION
		"."
	::= { bgs10SDHConfigEntry 5 }

bgs10SDHLineCodeing OBJECT-TYPE
	SYNTAX	UCHAR
	MAX-ACCESS	read-write
	STATUS	current
	DESCRIPTION
		"."
	::= { bgs10SDHConfigEntry 6 }

bgs10SDHTxClockSource OBJECT-TYPE
	SYNTAX	UCHAR
	MAX-ACCESS	read-write
	STATUS	current
	DESCRIPTION
		"."
	::= { bgs10SDHConfigEntry 7 }

bgs10SDHTxClockClass OBJECT-TYPE
	SYNTAX	UCHAR
	MAX-ACCESS	read-write
	STATUS	current
	DESCRIPTION
		"."
	::= { bgs10SDHConfigEntry 8 }

bgs10SDHRxClockClass OBJECT-TYPE
	SYNTAX	UCHAR
	MAX-ACCESS	read-write
	STATUS	current
	DESCRIPTION
		"."
	::= { bgs10SDHConfigEntry 9 }

bgs10SDHTxScrambling OBJECT-TYPE
	SYNTAX	UCHAR
	MAX-ACCESS	read-write
	STATUS	current
	DESCRIPTION
		"."
	::= { bgs10SDHConfigEntry 10 }

bgs10SDHRxScrambling OBJECT-TYPE
	SYNTAX	UCHAR
	MAX-ACCESS	read-write
	STATUS	current
	DESCRIPTION
		"."
	::= { bgs10SDHConfigEntry 11 }

bgs10SDHIdleUnassignedCells OBJECT-TYPE
	SYNTAX	UCHAR
	MAX-ACCESS	read-write
	STATUS	current
	DESCRIPTION
		"."
	::= { bgs10SDHConfigEntry 12 }

bgs10SDHCellHead OBJECT-TYPE
	SYNTAX	INTEGER
	MAX-ACCESS	read-write
	STATUS	current
	DESCRIPTION
		"."
	::= { bgs10SDHConfigEntry 13 }

-- bgs10IMAGroupConfTable
bgs10IMAGroupConfTable OBJECT-TYPE
	SYNTAX	SEQUENCE OF BGS10IMAGroupConfEntry
	MAX-ACCESS	not-accessible
	STATUS	current
	DESCRIPTION
		""
	::= { zxbgs10mib 61 }

bgs10IMAGroupConfEntry OBJECT-TYPE
	SYNTAX	BGS10IMAGroupConfEntry
	MAX-ACCESS	not-accessible
	STATUS	current
	DESCRIPTION
		"."
	INDEX {
		bgs10ImaGroupBetaValue
		}
	::= { bgs10IMAGroupConfTable 1 }
	
BGS10IMAGroupConfEntry ::=
	SEQUENCE {
		bgs10ImaGroupRowStatus			RowStatus,
		bgs10ImaGroupBetaValue			UCHAR,
		bgs10ImaGroupGammaValue			UCHAR,
		bgs10ImaGroupAlphaValue			UCHAR,
		bgs10ImaGroupMinNumTxLinks		UCHAR,
		bgs10ImaGroupNeTxClkMode		UCHAR,
		bgs10ImaGroupMinNumRxLinks		UCHAR,
		bgs10ImaGroupNumTxCfgLnks		UCHAR,
		bgs10ImaGroupNumRxCfgLnks		UCHAR,
		bgs10ImaGroupSymmetry			UCHAR,
		bgs10ImaGroupTxFrameLength		UCHAR,
		bgs10ImaGroupTxTimingRefLink		UCHAR,
		bgs10ImaGroupTxImaId			UCHAR,
		bgs10ImaGroupDiffDelayMax		UCHAR,
		bgs10ImaOamLabel			UCHAR,
		bgs10GroupAdminStatus			UCHAR,
		bgs10ImaGroupFlag			UCHAR,
		bgs10StatisticsTime			Unsigned32,
		bgs10ImaGroupNeState			UCHAR,
		bgs10ImaAlarmType				UCHAR
}

bgs10ImaGroupRowStatus OBJECT-TYPE
	SYNTAX	RowStatus
	MAX-ACCESS	read-write
	STATUS	current
	DESCRIPTION
		"."
	::= { bgs10IMAGroupConfEntry 1 }

bgs10ImaGroupBetaValue OBJECT-TYPE
	SYNTAX	UCHAR
	MAX-ACCESS	read-write
	STATUS	current
	DESCRIPTION
		"."
	::= { bgs10IMAGroupConfEntry 2 }

bgs10ImaGroupGammaValue OBJECT-TYPE
	SYNTAX	UCHAR
	MAX-ACCESS	read-write
	STATUS	current
	DESCRIPTION
		"."
	::= { bgs10IMAGroupConfEntry 3 }

bgs10ImaGroupAlphaValue OBJECT-TYPE
	SYNTAX	UCHAR
	MAX-ACCESS	read-write
	STATUS	current
	DESCRIPTION
		"."
	::= { bgs10IMAGroupConfEntry 4 }

bgs10ImaGroupMinNumTxLinks OBJECT-TYPE
	SYNTAX	UCHAR
	MAX-ACCESS	read-write
	STATUS	current
	DESCRIPTION
		"."
	::= { bgs10IMAGroupConfEntry 5 }

bgs10ImaGroupNeTxClkMode OBJECT-TYPE
	SYNTAX	UCHAR
	MAX-ACCESS	read-write
	STATUS	current
	DESCRIPTION
		"."
	::= { bgs10IMAGroupConfEntry 6 }

bgs10ImaGroupMinNumRxLinks OBJECT-TYPE
	SYNTAX	UCHAR
	MAX-ACCESS	read-write
	STATUS	current
	DESCRIPTION
		"."
	::= { bgs10IMAGroupConfEntry 7 }

bgs10ImaGroupNumTxCfgLnks OBJECT-TYPE
	SYNTAX	UCHAR
	MAX-ACCESS	read-write
	STATUS	current
	DESCRIPTION
		"."
	::= { bgs10IMAGroupConfEntry 8 }

bgs10ImaGroupNumRxCfgLnks OBJECT-TYPE
	SYNTAX	UCHAR
	MAX-ACCESS	read-write
	STATUS	current
	DESCRIPTION
		"."
	::= { bgs10IMAGroupConfEntry 9 }

bgs10ImaGroupSymmetry OBJECT-TYPE
	SYNTAX	UCHAR
	MAX-ACCESS	read-write
	STATUS	current
	DESCRIPTION
		"."
	::= { bgs10IMAGroupConfEntry 10 }

bgs10ImaGroupTxFrameLength OBJECT-TYPE
	SYNTAX	UCHAR
	MAX-ACCESS	read-write
	STATUS	current
	DESCRIPTION
		"."
	::= { bgs10IMAGroupConfEntry 11 }

bgs10ImaGroupTxTimingRefLink OBJECT-TYPE
	SYNTAX	UCHAR
	MAX-ACCESS	read-write
	STATUS	current
	DESCRIPTION
		"."
	::= { bgs10IMAGroupConfEntry 12 }

bgs10ImaGroupTxImaId OBJECT-TYPE
	SYNTAX	UCHAR
	MAX-ACCESS	read-write
	STATUS	current
	DESCRIPTION
		"."
	::= { bgs10IMAGroupConfEntry 13 }

bgs10ImaGroupDiffDelayMax OBJECT-TYPE
	SYNTAX	UCHAR
	MAX-ACCESS	read-write
	STATUS	current
	DESCRIPTION
		"."
	::= { bgs10IMAGroupConfEntry 14 }

bgs10ImaOamLabel OBJECT-TYPE
	SYNTAX	UCHAR
	MAX-ACCESS	read-write
	STATUS	current
	DESCRIPTION
		"."
	::= { bgs10IMAGroupConfEntry 15 }

bgs10GroupAdminStatus OBJECT-TYPE
	SYNTAX	UCHAR
	MAX-ACCESS	read-write
	STATUS	current
	DESCRIPTION
		"."
	::= { bgs10IMAGroupConfEntry 16 }

bgs10ImaGroupFlag OBJECT-TYPE
	SYNTAX	UCHAR
	MAX-ACCESS	read-write
	STATUS	current
	DESCRIPTION
		"."
	::= { bgs10IMAGroupConfEntry 17 }

bgs10StatisticsTime OBJECT-TYPE
	SYNTAX	Unsigned32
	MAX-ACCESS	read-write
	STATUS	current
	DESCRIPTION
		"."
	::= { bgs10IMAGroupConfEntry 18 }

bgs10ImaGroupNeState OBJECT-TYPE
	SYNTAX	UCHAR
	MAX-ACCESS	read-write
	STATUS	current
	DESCRIPTION
		"."
	::= { bgs10IMAGroupConfEntry 19 }

bgs10ImaAlarmType OBJECT-TYPE
	SYNTAX	UCHAR
	MAX-ACCESS	read-write
	STATUS	current
	DESCRIPTION
		"."
	::= { bgs10IMAGroupConfEntry 20 }

-- bgs10IMALinkConfTable
bgs10IMALinkConfTable OBJECT-TYPE
	SYNTAX	SEQUENCE OF BGS10IMALinkConfEntry
	MAX-ACCESS	not-accessible
	STATUS	current
	DESCRIPTION
		""
	::= { zxbgs10mib 62 }

bgs10IMALinkConfEntry OBJECT-TYPE
	SYNTAX	BGS10IMALinkConfEntry
	MAX-ACCESS	not-accessible
	STATUS	current
	DESCRIPTION
		"."
	INDEX {
		bgs10ImaLinkTxLid
		}
	::= { bgs10IMALinkConfTable 1 }
	
BGS10IMALinkConfEntry ::=
	SEQUENCE {
		bgs10ImaLinkRowStatus			RowStatus,
		bgs10ImaLinkTxLid			UCHAR,
		bgs10ImaLinkTxStat			UCHAR,
		bgs10ImaLinkRxStat			UCHAR,
		bgs10ImaLinkGroupIndex			UCHAR,
		bgs10ImaLinkFlag			UCHAR,
		bgs10ImaLinkStatisticsTime		Unsigned32,
		bgs10imaLinkNeTxAdminStatus		UCHAR,
		bgs10imaLinkNeRxAdminStatus		UCHAR
}

bgs10ImaLinkRowStatus OBJECT-TYPE
	SYNTAX	RowStatus
	MAX-ACCESS	read-write
	STATUS	current
	DESCRIPTION
		"."
	::= { bgs10IMALinkConfEntry 1 }

bgs10ImaLinkTxLid OBJECT-TYPE
	SYNTAX		UCHAR
	MAX-ACCESS	read-write
	STATUS	current
	DESCRIPTION
		"."
	::= { bgs10IMALinkConfEntry 2 }

bgs10ImaLinkTxStat OBJECT-TYPE
	SYNTAX		UCHAR
	MAX-ACCESS	read-write
	STATUS	current
	DESCRIPTION
		"."
	::= { bgs10IMALinkConfEntry 3 }

bgs10ImaLinkRxStat OBJECT-TYPE
	SYNTAX		UCHAR
	MAX-ACCESS	read-write
	STATUS	current
	DESCRIPTION
		"."
	::= { bgs10IMALinkConfEntry 4 }

bgs10ImaLinkGroupIndex OBJECT-TYPE
	SYNTAX		UCHAR
	MAX-ACCESS	read-write
	STATUS	current
	DESCRIPTION
		"."
	::= { bgs10IMALinkConfEntry 5 }

bgs10ImaLinkFlag OBJECT-TYPE
	SYNTAX		UCHAR
	MAX-ACCESS	read-write
	STATUS	current
	DESCRIPTION
		"."
	::= { bgs10IMALinkConfEntry 6 }

bgs10ImaLinkStatisticsTime OBJECT-TYPE
	SYNTAX		Unsigned32
	MAX-ACCESS	read-write
	STATUS	current
	DESCRIPTION
		"."
	::= { bgs10IMALinkConfEntry 7 }

bgs10imaLinkNeTxAdminStatus OBJECT-TYPE
	SYNTAX		UCHAR
	MAX-ACCESS	read-write
	STATUS	current
	DESCRIPTION
		"."
	::= { bgs10IMALinkConfEntry 8 }

bgs10imaLinkNeRxAdminStatus 	OBJECT-TYPE
	SYNTAX		UCHAR
	MAX-ACCESS	read-write
	STATUS	current
	DESCRIPTION
		"."
	::= { bgs10IMALinkConfEntry 9 }


-- bgs10LogicIfDlciTable
bgs10LogicIfDlciTable OBJECT-TYPE
	SYNTAX	SEQUENCE OF BGS10LogicIfDlciEntry
	MAX-ACCESS	not-accessible
	STATUS	current
	DESCRIPTION
		""
	::= { zxbgs10mib 63 }

bgs10LogicIfDlciEntry OBJECT-TYPE
	SYNTAX	BGS10LogicIfDlciEntry
	MAX-ACCESS	not-accessible
	STATUS	current
	DESCRIPTION
		"."
	INDEX {
		bgs10LogicIfDlcimodule,
		bgs10LogicIfDlciLogicIf
		}
	::= { bgs10LogicIfDlciTable 1 }
	
BGS10LogicIfDlciEntry ::=
	SEQUENCE {
		bgs10LogicIfDlciRowStatus		RowStatus,
		bgs10LogicIfDlcimodule			UCHAR,
		bgs10LogicIfDlciSer2Type		UCHAR,
		bgs10LogicIfDlciSer3Type		UCHAR,
		bgs10LogicIfDlciProtocal		UCHAR,
		bgs10LogicIfDlciLogicIf			UShort,
		bgs10LogicIfDlciDLCI			Unsigned32,
		bgs10LogicIfDlciIfindex			UShort,
		bgs10LogicIfDlciAddrType		UCHAR
}

bgs10LogicIfDlciRowStatus OBJECT-TYPE
	SYNTAX	RowStatus
	MAX-ACCESS	read-write
	STATUS	current
	DESCRIPTION
		"."
	::= { bgs10LogicIfDlciEntry 1 }

bgs10LogicIfDlcimodule OBJECT-TYPE
	SYNTAX	UCHAR
	MAX-ACCESS	read-write
	STATUS	current
	DESCRIPTION
		"."
	::= { bgs10LogicIfDlciEntry 2 }

bgs10LogicIfDlciSer2Type OBJECT-TYPE
	SYNTAX	UCHAR
	MAX-ACCESS	read-write
	STATUS	current
	DESCRIPTION
		"."
	::= { bgs10LogicIfDlciEntry 3 }

bgs10LogicIfDlciSer3Type OBJECT-TYPE
	SYNTAX	UCHAR
	MAX-ACCESS	read-write
	STATUS	current
	DESCRIPTION
		"."
	::= { bgs10LogicIfDlciEntry 4 }

bgs10LogicIfDlciProtocal OBJECT-TYPE
	SYNTAX	UCHAR
	MAX-ACCESS	read-write
	STATUS	current
	DESCRIPTION
		"."
	::= { bgs10LogicIfDlciEntry 5 }

bgs10LogicIfDlciLogicIf OBJECT-TYPE
	SYNTAX	UShort
	MAX-ACCESS	read-write
	STATUS	current
	DESCRIPTION
		"."
	::= { bgs10LogicIfDlciEntry 6 }

bgs10LogicIfDlciDLCI OBJECT-TYPE
	SYNTAX	Unsigned32
	MAX-ACCESS	read-write
	STATUS	current
	DESCRIPTION
		"."
	::= { bgs10LogicIfDlciEntry 7 }

bgs10LogicIfDlciIfindex OBJECT-TYPE
	SYNTAX	UShort
	MAX-ACCESS	read-write
	STATUS	current
	DESCRIPTION
		"."
	::= { bgs10LogicIfDlciEntry 8 }

bgs10LogicIfDlciAddrType OBJECT-TYPE
	SYNTAX	UCHAR
	MAX-ACCESS	read-write
	STATUS	current
	DESCRIPTION
		"."
	::= { bgs10LogicIfDlciEntry 9 }

-- bgs10LogicIfIPTable
bgs10LogicIfIPTable OBJECT-TYPE
	SYNTAX	SEQUENCE OF BGS10LogicIfIPEntry
	MAX-ACCESS	not-accessible
	STATUS	current
	DESCRIPTION
		""
	::= { zxbgs10mib 64 }

bgs10LogicIfIPEntry OBJECT-TYPE
	SYNTAX	BGS10LogicIfIPEntry
	MAX-ACCESS	not-accessible
	STATUS	current
	DESCRIPTION
		"."
	INDEX {
		bgs10LogicIfIPmodule,
		bgs10LogicIfIPIPAddress
		}
	::= { bgs10LogicIfIPTable 1 }
	
BGS10LogicIfIPEntry ::=
	SEQUENCE {
		bgs10LogicIfIPRowStatus		RowStatus,
		bgs10LogicIfIPmodule		UCHAR,
		bgs10LogicIfIPSer2Type		UCHAR,
		bgs10LogicIfIPSer3Type		UCHAR,
		bgs10LogicIfIPLogicIf		UShort,
		bgs10LogicIfIPIPAddress		Unsigned32,
		bgs10LogicIfIPSubnetMask	Unsigned32
}

bgs10LogicIfIPRowStatus OBJECT-TYPE
	SYNTAX	RowStatus
	MAX-ACCESS	read-write
	STATUS	current
	DESCRIPTION
		"."
	::= { bgs10LogicIfIPEntry 1 }

bgs10LogicIfIPmodule OBJECT-TYPE
	SYNTAX	UCHAR
	MAX-ACCESS	read-write
	STATUS	current
	DESCRIPTION
		"."
	::= { bgs10LogicIfIPEntry 2 }

bgs10LogicIfIPSer2Type OBJECT-TYPE
	SYNTAX	UCHAR
	MAX-ACCESS	read-write
	STATUS	current
	DESCRIPTION
		"."
	::= { bgs10LogicIfIPEntry 3 }

bgs10LogicIfIPSer3Type OBJECT-TYPE
	SYNTAX	UCHAR
	MAX-ACCESS	read-write
	STATUS	current
	DESCRIPTION
		"."
	::= { bgs10LogicIfIPEntry 4 }

bgs10LogicIfIPLogicIf OBJECT-TYPE
	SYNTAX	UShort
	MAX-ACCESS	read-write
	STATUS	current
	DESCRIPTION
		"."
	::= { bgs10LogicIfIPEntry 5 }

bgs10LogicIfIPIPAddress OBJECT-TYPE
	SYNTAX	Unsigned32
	MAX-ACCESS	read-write
	STATUS	current
	DESCRIPTION
		"."
	::= { bgs10LogicIfIPEntry 6 }

bgs10LogicIfIPSubnetMask OBJECT-TYPE
	SYNTAX	Unsigned32
	MAX-ACCESS	read-write
	STATUS	current
	DESCRIPTION
		"."
	::= { bgs10LogicIfIPEntry 7 }

-- bgs10VLANPortConfigTable
bgs10VLANPortConfigTable OBJECT-TYPE
	SYNTAX	SEQUENCE OF BGS10VLANPortConfigEntry
	MAX-ACCESS	not-accessible
	STATUS	current
	DESCRIPTION
		""
	::= { zxbgs10mib 65 }

bgs10VLANPortConfigEntry OBJECT-TYPE
	SYNTAX	BGS10VLANPortConfigEntry
	MAX-ACCESS	not-accessible
	STATUS	current
	DESCRIPTION
		"."
	INDEX {
		bgs10VLANPortConfigPortName
		}
	::= { bgs10VLANPortConfigTable 1 }
	
BGS10VLANPortConfigEntry ::=
	SEQUENCE {
		bgs10VLANPortConfigRowStatus		RowStatus,
		bgs10VLANPortConfigPortName		OCTET STRING(SIZE(32)),
		bgs10VLANPortConfigPortAddr		OCTET STRING,
		bgs10VLANPortConfigPVID			Unsigned32,
		bgs10VLANPortConfigPortType		Unsigned32,
		bgs10VLANPortConfigFrameType		Unsigned32,
		bgs10VLANPortConfigIngressSet		Unsigned32,
		bgs10VLANPortConfigStpEnabled		UCHAR,
		bgs10VLANPortConfigPathCost			Unsigned32,
		bgs10VLANPortConfigPriority			UCHAR
}

bgs10VLANPortConfigRowStatus	OBJECT-TYPE
	SYNTAX		RowStatus
	MAX-ACCESS	read-write
	STATUS		current
	DESCRIPTION
		"."
	::= { bgs10VLANPortConfigEntry 1 }

bgs10VLANPortConfigPortName	OBJECT-TYPE
	SYNTAX		OCTET STRING(SIZE(32))
	MAX-ACCESS	read-write
	STATUS		current
	DESCRIPTION
		"."
	::= { bgs10VLANPortConfigEntry 2 }

bgs10VLANPortConfigPortAddr	OBJECT-TYPE
	SYNTAX		OCTET STRING
	MAX-ACCESS	read-write
	STATUS		current
	DESCRIPTION
		"."
	::= { bgs10VLANPortConfigEntry 3 }

bgs10VLANPortConfigPVID		OBJECT-TYPE
	SYNTAX		Unsigned32
	MAX-ACCESS	read-write
	STATUS		current
	DESCRIPTION
		"."
	::= { bgs10VLANPortConfigEntry 4 }

bgs10VLANPortConfigPortType	OBJECT-TYPE
	SYNTAX		Unsigned32
	MAX-ACCESS	read-write
	STATUS		current
	DESCRIPTION
		"."
	::= { bgs10VLANPortConfigEntry 5 }

bgs10VLANPortConfigFrameType	OBJECT-TYPE
	SYNTAX		Unsigned32
	MAX-ACCESS	read-write
	STATUS		current
	DESCRIPTION
		"."
	::= { bgs10VLANPortConfigEntry 6 }

bgs10VLANPortConfigIngressSet	OBJECT-TYPE
	SYNTAX		Unsigned32
	MAX-ACCESS	read-write
	STATUS		current
	DESCRIPTION
		"."
	::= { bgs10VLANPortConfigEntry 7 }

bgs10VLANPortConfigStpEnabled	OBJECT-TYPE
	SYNTAX		UCHAR
	MAX-ACCESS	read-write
	STATUS		current
	DESCRIPTION
		"."
	::= { bgs10VLANPortConfigEntry 8 }

bgs10VLANPortConfigPathCost	OBJECT-TYPE
	SYNTAX		Unsigned32
	MAX-ACCESS	read-write
	STATUS		current
	DESCRIPTION
		"."
	::= { bgs10VLANPortConfigEntry 9 }

bgs10VLANPortConfigPriority	OBJECT-TYPE
	SYNTAX		UCHAR
	MAX-ACCESS	read-write
	STATUS		current
	DESCRIPTION
		"."
	::= { bgs10VLANPortConfigEntry 10 }

-- bgs10VLANBridgeConfigTable
bgs10VLANBridgeConfigTable OBJECT-TYPE
	SYNTAX	SEQUENCE OF BGS10VLANBridgeConfigEntry
	MAX-ACCESS	not-accessible
	STATUS	current
	DESCRIPTION
		""
	::= { zxbgs10mib 66 }

bgs10VLANBridgeConfigEntry OBJECT-TYPE
	SYNTAX	BGS10VLANBridgeConfigEntry
	MAX-ACCESS	not-accessible
	STATUS	current
	DESCRIPTION
		"."
	INDEX {
		bgs10VLANBridgeConfigAddr
		}
	::= { bgs10VLANBridgeConfigTable 1 }
	
BGS10VLANBridgeConfigEntry ::=
	SEQUENCE {
		bgs10VLANBridgeConfigRowStatus		RowStatus,
		bgs10VLANBridgeConfigAddr		OCTET STRING,
		bgs10VLANBridgeConfigBridgeName		OCTET STRING(SIZE(32)),
		bgs10VLANBridgeConfigUpTime		Unsigned32,
		bgs10VLANBridgeConfigAgeingtime		Unsigned32,
		bgs10VLANBridgeConfigStpEnabled		UCHAR,
		bgs10VLANBridgeConfigMaxAge			Unsigned32,
		bgs10VLANBridgeConfigHelloTime		Unsigned32,
		bgs10VLANBridgeConfigForwardDelay	Unsigned32,
		bgs10VLANBridgeConfigPriority		UShort
	}

bgs10VLANBridgeConfigRowStatus	OBJECT-TYPE
	SYNTAX		RowStatus
	MAX-ACCESS	read-write
	STATUS		current
	DESCRIPTION
		"."
	::= { bgs10VLANBridgeConfigEntry 1 }

bgs10VLANBridgeConfigAddr	OBJECT-TYPE
	SYNTAX		OCTET STRING
	MAX-ACCESS	read-write
	STATUS		current
	DESCRIPTION
		"."
	::= { bgs10VLANBridgeConfigEntry 2 }

bgs10VLANBridgeConfigBridgeName	OBJECT-TYPE
	SYNTAX		OCTET STRING(SIZE(32))
	MAX-ACCESS	read-write
	STATUS		current
	DESCRIPTION
		"."
	::= { bgs10VLANBridgeConfigEntry 3 }

bgs10VLANBridgeConfigUpTime	OBJECT-TYPE
	SYNTAX		Unsigned32
	MAX-ACCESS	read-write
	STATUS		current
	DESCRIPTION
		"."
	::= { bgs10VLANBridgeConfigEntry 4 }

bgs10VLANBridgeConfigAgeingtime	OBJECT-TYPE
	SYNTAX		Unsigned32
	MAX-ACCESS	read-write
	STATUS		current
	DESCRIPTION
		"."
	::= { bgs10VLANBridgeConfigEntry 5 }

bgs10VLANBridgeConfigStpEnabled	OBJECT-TYPE
	SYNTAX		UCHAR
	MAX-ACCESS	read-write
	STATUS		current
	DESCRIPTION
		"."
	::= { bgs10VLANBridgeConfigEntry 6 }

bgs10VLANBridgeConfigMaxAge	OBJECT-TYPE
	SYNTAX		Unsigned32
	MAX-ACCESS	read-write
	STATUS		current
	DESCRIPTION
		"."
	::= { bgs10VLANBridgeConfigEntry 7 }

bgs10VLANBridgeConfigHelloTime	OBJECT-TYPE
	SYNTAX		Unsigned32
	MAX-ACCESS	read-write
	STATUS		current
	DESCRIPTION
		"."
	::= { bgs10VLANBridgeConfigEntry 8 }

bgs10VLANBridgeConfigForwardDelay	OBJECT-TYPE
	SYNTAX		Unsigned32
	MAX-ACCESS	read-write
	STATUS		current
	DESCRIPTION
		"."
	::= { bgs10VLANBridgeConfigEntry 9 }

bgs10VLANBridgeConfigPriority	OBJECT-TYPE
	SYNTAX		UShort
	MAX-ACCESS	read-write
	STATUS		current
	DESCRIPTION
		"."
	::= { bgs10VLANBridgeConfigEntry 10 }

-- bgs10VLANFilterConfigTable
bgs10VLANFilterConfigTable OBJECT-TYPE
	SYNTAX	SEQUENCE OF BGS10VLANFilterConfigEntry
	MAX-ACCESS	not-accessible
	STATUS	current
	DESCRIPTION
		""
	::= { zxbgs10mib 67 }

bgs10VLANFilterConfigEntry OBJECT-TYPE
	SYNTAX	BGS10VLANFilterConfigEntry
	MAX-ACCESS	not-accessible
	STATUS	current
	DESCRIPTION
		"."
	INDEX {
		bgs10VLANFilterConfigSourceAddr,
		bgs10VLANFilterConfigModule,
		bgs10VLANFilterConfigVlanID
		}
	::= { bgs10VLANFilterConfigTable 1 }
	
BGS10VLANFilterConfigEntry ::=
	SEQUENCE {
		bgs10VLANFilterConfigRowStatus		RowStatus,
		bgs10VLANFilterConfigSourceAddr		OCTET STRING,
		bgs10VLANFilterConfigPort		UShort,
		bgs10VLANFilterConfigModule		UCHAR,
		bgs10VLANFilterConfigVlanID		UShort,
		bgs10VLANFilterConfigFilterType		UShort						
	}

bgs10VLANFilterConfigRowStatus	OBJECT-TYPE
	SYNTAX		RowStatus
	MAX-ACCESS	read-write
	STATUS		current
	DESCRIPTION
		"."
	::= { bgs10VLANFilterConfigEntry 1 }

bgs10VLANFilterConfigSourceAddr	OBJECT-TYPE
	SYNTAX		OCTET STRING
	MAX-ACCESS	read-write
	STATUS		current
	DESCRIPTION
		"."
	::= { bgs10VLANFilterConfigEntry 2 }

bgs10VLANFilterConfigPort	OBJECT-TYPE
	SYNTAX		UShort
	MAX-ACCESS	read-write
	STATUS		current
	DESCRIPTION
		"."
	::= { bgs10VLANFilterConfigEntry 3 }

bgs10VLANFilterConfigModule	OBJECT-TYPE
	SYNTAX		UCHAR
	MAX-ACCESS	read-write
	STATUS		current
	DESCRIPTION
		"."
	::= { bgs10VLANFilterConfigEntry 4 }

bgs10VLANFilterConfigVlanID	OBJECT-TYPE
	SYNTAX		UShort
	MAX-ACCESS	read-write
	STATUS		current
	DESCRIPTION
		"."
	::= { bgs10VLANFilterConfigEntry 5 }

bgs10VLANFilterConfigFilterType	OBJECT-TYPE
	SYNTAX		UShort
	MAX-ACCESS	read-write
	STATUS		current
	DESCRIPTION
		"."
	::= { bgs10VLANFilterConfigEntry 6 }

-- bgs10VLANConfigTable
bgs10VLANConfigTable OBJECT-TYPE
	SYNTAX	SEQUENCE OF BGS10VLANConfigEntry
	MAX-ACCESS	not-accessible
	STATUS	current
	DESCRIPTION
		""
	::= { zxbgs10mib 68 }

bgs10VLANConfigEntry OBJECT-TYPE
	SYNTAX	BGS10VLANConfigEntry
	MAX-ACCESS	not-accessible
	STATUS	current
	DESCRIPTION
		"."
	INDEX {
		bgs10VLANBridgeConfigAddr
		}
	::= { bgs10VLANConfigTable 1 }
	
BGS10VLANConfigEntry ::=
	SEQUENCE {
		bgs10VLANConfigRowStatus	RowStatus,
		bgs10VLANConfigModule		UCHAR,				
		bgs10VLANConfigVlanID		UCHAR,				
		bgs10VLANConfigPortId		OCTET STRING,
		bgs10VLANConfigTagSet		OCTET STRING,
		bgs10VLANConfigFID			UShort
	}

bgs10VLANConfigRowStatus	OBJECT-TYPE
	SYNTAX		RowStatus
	MAX-ACCESS	read-write
	STATUS		current
	DESCRIPTION
		"."
	::= { bgs10VLANConfigEntry 1 }

bgs10VLANConfigModule	OBJECT-TYPE
	SYNTAX		UCHAR
	MAX-ACCESS	read-write
	STATUS		current
	DESCRIPTION
		"."
	::= { bgs10VLANConfigEntry 2 }

bgs10VLANConfigVlanID	OBJECT-TYPE
	SYNTAX		UCHAR
	MAX-ACCESS	read-write
	STATUS		current
	DESCRIPTION
		"."
	::= { bgs10VLANConfigEntry 3 }

bgs10VLANConfigPortId	OBJECT-TYPE
	SYNTAX		OCTET STRING
	MAX-ACCESS	read-write
	STATUS		current
	DESCRIPTION
		"."
	::= { bgs10VLANConfigEntry 4 }

bgs10VLANConfigTagSet	OBJECT-TYPE
	SYNTAX		OCTET STRING
	MAX-ACCESS	read-write
	STATUS		current
	DESCRIPTION
		"."
	::= { bgs10VLANConfigEntry 5 }

bgs10VLANConfigFID	OBJECT-TYPE
	SYNTAX		UShort
	MAX-ACCESS	read-write
	STATUS		current
	DESCRIPTION
		"."
	::= { bgs10VLANConfigEntry 6 }

-- bgs10IMAGroupStatTable
bgs10IMAGroupStatTable OBJECT-TYPE
	SYNTAX	SEQUENCE OF BGS10IMAGroupStatEntry
	MAX-ACCESS	not-accessible
	STATUS	current
	DESCRIPTION
		""
	::= { zxbgs10mib 69 }

bgs10IMAGroupStatEntry OBJECT-TYPE
	SYNTAX	BGS10IMAGroupStatEntry
	MAX-ACCESS	not-accessible
	STATUS	current
	DESCRIPTION
		"."
	INDEX {
		bgs10ImaGroupBetaValue
		}
	::= { bgs10IMAGroupStatTable 1 }
	
BGS10IMAGroupStatEntry ::=
	SEQUENCE {
		bgs10ImaGroupStatRowStatus	        RowStatus,
		bgs10ImaGroupStatFeState	        UCHAR,
		bgs10ImaGroupStatTestProcStatus		UCHAR,
		bgs10ImaGroupStatFeTxClkMode	        UCHAR,
		bgs10ImaGroupStatFailureStatus		UCHAR,
		bgs10ImaGroupStatNumTxActLnks		UCHAR,
		bgs10ImaGroupStatNumRxActLnks		UCHAR,
		bgs10ImaGroupStatRxFrameLength		UCHAR,
		bgs10ImaGroupStatRxTimingRefLink     	UCHAR,		
		bgs10ImaGroupStatLastChange	        Unsigned32,
		bgs10ImaGroupStatRunningSecs	        Unsigned32,
		bgs10ImaGroupStatUnavailSecs	        Unsigned32,
		bgs10ImaGroupStatNeNUMFailures		Unsigned32,
		bgs10ImaGroupStatFeNUMFailures		Unsigned32,
		bgs10ImaGroupStatTxAvailCellRate     	Unsigned32,
		bgs10ImaGroupStatRxAvailCellRate     	Unsigned32,
		bgs10ImaGroupStatTestLinkIfIndex     	UShort,
		bgs10ImaGroupStatTestPattern	        UShort,
		bgs10ImaGroupStatRxImaId	        UCHAR,
		bgs10ImaGroupStatLeastDelayLink		UCHAR,
                bgs10ImaGroupStatDiffDelayMaxObs     	UCHAR
}

bgs10ImaGroupStatRowStatus OBJECT-TYPE
	SYNTAX	RowStatus
	MAX-ACCESS	read-write
	STATUS	current
	DESCRIPTION
		"."
	::= { bgs10IMAGroupStatEntry 1 }

bgs10ImaGroupStatFeState OBJECT-TYPE
	SYNTAX	UCHAR
	MAX-ACCESS	read-write
	STATUS	current
	DESCRIPTION
		"."
	::= { bgs10IMAGroupStatEntry 2 }

bgs10ImaGroupStatTestProcStatus OBJECT-TYPE
	SYNTAX	UCHAR
	MAX-ACCESS	read-write
	STATUS	current
	DESCRIPTION
		"."
	::= { bgs10IMAGroupStatEntry 3 }

bgs10ImaGroupStatFeTxClkMode OBJECT-TYPE
	SYNTAX	UCHAR
	MAX-ACCESS	read-write
	STATUS	current
	DESCRIPTION
		"."
	::= { bgs10IMAGroupStatEntry 4 }

bgs10ImaGroupStatFailureStatus OBJECT-TYPE
	SYNTAX	UCHAR
	MAX-ACCESS	read-write
	STATUS	current
	DESCRIPTION
		"."
	::= { bgs10IMAGroupStatEntry 5 }

bgs10ImaGroupStatNumTxActLnks OBJECT-TYPE
	SYNTAX	UCHAR
	MAX-ACCESS	read-write
	STATUS	current
	DESCRIPTION
		"."
	::= { bgs10IMAGroupStatEntry 6 }

bgs10ImaGroupStatNumRxActLnks OBJECT-TYPE
	SYNTAX	UCHAR
	MAX-ACCESS	read-write
	STATUS	current
	DESCRIPTION
		"."
	::= { bgs10IMAGroupStatEntry 7 }

bgs10ImaGroupStatRxFrameLength OBJECT-TYPE
	SYNTAX	UCHAR
	MAX-ACCESS	read-write
	STATUS	current
	DESCRIPTION
		"."
	::= { bgs10IMAGroupStatEntry 8 }

bgs10ImaGroupStatRxTimingRefLink OBJECT-TYPE
	SYNTAX	UCHAR
	MAX-ACCESS	read-write
	STATUS	current
	DESCRIPTION
		"."
	::= { bgs10IMAGroupStatEntry 9 }

bgs10ImaGroupStatLastChange OBJECT-TYPE
	SYNTAX	Unsigned32
	MAX-ACCESS	read-write
	STATUS	current
	DESCRIPTION
		"."
	::= { bgs10IMAGroupStatEntry 10 }

bgs10ImaGroupStatRunningSecs OBJECT-TYPE
	SYNTAX	Unsigned32
	MAX-ACCESS	read-write
	STATUS	current
	DESCRIPTION
		"."
	::= { bgs10IMAGroupStatEntry 11 }

bgs10ImaGroupStatUnavailSecs OBJECT-TYPE
	SYNTAX	Unsigned32
	MAX-ACCESS	read-write
	STATUS	current
	DESCRIPTION
		"."
	::= { bgs10IMAGroupStatEntry 12 }

bgs10ImaGroupStatNeNUMFailures OBJECT-TYPE
	SYNTAX	Unsigned32
	MAX-ACCESS	read-write
	STATUS	current
	DESCRIPTION
		"."
	::= { bgs10IMAGroupStatEntry 13 }

bgs10ImaGroupStatFeNUMFailures OBJECT-TYPE
	SYNTAX	Unsigned32
	MAX-ACCESS	read-write
	STATUS	current
	DESCRIPTION
		"."
	::= { bgs10IMAGroupStatEntry 14 }

bgs10ImaGroupStatTxAvailCellRate OBJECT-TYPE
	SYNTAX	Unsigned32
	MAX-ACCESS	read-write
	STATUS	current
	DESCRIPTION
		"."
	::= { bgs10IMAGroupStatEntry 15 }

bgs10ImaGroupStatRxAvailCellRate OBJECT-TYPE
	SYNTAX	Unsigned32
	MAX-ACCESS	read-write
	STATUS	current
	DESCRIPTION
		"."
	::= { bgs10IMAGroupStatEntry 16 }

bgs10ImaGroupStatTestLinkIfIndex OBJECT-TYPE
	SYNTAX	UShort
	MAX-ACCESS	read-write
	STATUS	current
	DESCRIPTION
		"."
	::= { bgs10IMAGroupStatEntry 17 }

bgs10ImaGroupStatTestPattern OBJECT-TYPE
	SYNTAX	UShort
	MAX-ACCESS	read-write
	STATUS	current
	DESCRIPTION
		"."
	::= { bgs10IMAGroupStatEntry 18 }

bgs10ImaGroupStatRxImaId OBJECT-TYPE
	SYNTAX	UCHAR
	MAX-ACCESS	read-write
	STATUS	current
	DESCRIPTION
		"."
	::= { bgs10IMAGroupStatEntry 19 }

bgs10ImaGroupStatLeastDelayLink OBJECT-TYPE
	SYNTAX	UCHAR
	MAX-ACCESS	read-write
	STATUS	current
	DESCRIPTION
		"."
	::= { bgs10IMAGroupStatEntry 20 }

bgs10ImaGroupStatDiffDelayMaxObs OBJECT-TYPE
	SYNTAX	UCHAR
	MAX-ACCESS	read-write
	STATUS	current
	DESCRIPTION
		"."
	::= { bgs10IMAGroupStatEntry 21 }

-- bgs10IMALinkStatTable
bgs10IMALinkStatTable OBJECT-TYPE
	SYNTAX	SEQUENCE OF BGS10IMALinkStatEntry
	MAX-ACCESS	not-accessible
	STATUS	current
	DESCRIPTION
		""
	::= { zxbgs10mib 70 }

bgs10IMALinkStatEntry OBJECT-TYPE
	SYNTAX	BGS10IMALinkStatEntry
	MAX-ACCESS	not-accessible
	STATUS	current
	DESCRIPTION
		"."
	INDEX {
		bgs10ImaLinkStatFeTxState
		}
	::= { bgs10IMALinkStatTable 1 }
	
BGS10IMALinkStatEntry ::=
	SEQUENCE {
		bgs10ImaLinkStatRowStatus         	 RowStatus,
		bgs10ImaLinkStatFeTxState		 Unsigned32,
		bgs10ImaLinkStatFeRxState		 Unsigned32,
		bgs10ImaLinkStatNeRxFailureStatus	 Unsigned32,
		bgs10ImaLinkStatFeRxFailureStatus	 Unsigned32,
		bgs10ImaLinkStatTestProcStatus	 	 Unsigned32,
		bgs10ImaLinkStatRxLid		 	 Unsigned32,
		bgs10ImaLinkStatRelDelay        	 UCHAR,  
		bgs10ImaLinkStatImaViolations   	 Unsigned32,  
		bgs10ImaLinkStatOifAnomalies    	 Unsigned32,	
		bgs10ImaLinkStatNeSevErroredSec 	 Unsigned32,
		bgs10ImaLinkStatFeSevErroredSec 	 Unsigned32,
		bgs10ImaLinkStatNeUnavailSec    	 Unsigned32,
		bgs10ImaLinkStatFeUnavailSec    	 Unsigned32,
		bgs10ImaLinkStatNeTxUnusableSec 	 Unsigned32,
		bgs10ImaLinkStatNeRxUnusableSec 	 Unsigned32,
		bgs10ImaLinkStatFeTxUnusableSec 	 Unsigned32,  
		bgs10ImaLinkStatFeRxUnusableSec 	 Unsigned32,  
		bgs10ImaLinkStatNeTxNumFailures 	 Unsigned32,  
		bgs10ImaLinkStatNeRxNumFailures 	 Unsigned32,  
		bgs10ImaLinkStatFeTxNumFailures 	 Unsigned32,  
		bgs10ImaLinkStatFeRxNumFailures      	 Unsigned32,  
		bgs10ImaLinkStatTxStuffs             	 Unsigned32,  
		bgs10ImaLinkStatRxStuffs             	 Unsigned32,  
		bgs10ImaLinkStatRxTestPattern        	 UCHAR                      
}                    
                                                     
bgs10ImaLinkStatRowStatus OBJECT-TYPE
	SYNTAX	RowStatus
	MAX-ACCESS	read-write
	STATUS	current
	DESCRIPTION
		"."
	::= { bgs10IMALinkStatEntry 1 }

bgs10ImaLinkStatFeTxState OBJECT-TYPE
	SYNTAX	Unsigned32
	MAX-ACCESS	read-write
	STATUS	current
	DESCRIPTION
		"."
	::= { bgs10IMALinkStatEntry 2 }

bgs10ImaLinkStatFeRxState OBJECT-TYPE
	SYNTAX	Unsigned32
	MAX-ACCESS	read-write
	STATUS	current
	DESCRIPTION
		"."
	::= { bgs10IMALinkStatEntry 3 }

bgs10ImaLinkStatNeRxFailureStatus OBJECT-TYPE
	SYNTAX	Unsigned32
	MAX-ACCESS	read-write
	STATUS	current
	DESCRIPTION
		"."
	::= { bgs10IMALinkStatEntry 4 }

bgs10ImaLinkStatFeRxFailureStatus OBJECT-TYPE
	SYNTAX	Unsigned32
	MAX-ACCESS	read-write
	STATUS	current
	DESCRIPTION
		"."
	::= { bgs10IMALinkStatEntry 5 }

bgs10ImaLinkStatTestProcStatus OBJECT-TYPE
	SYNTAX	Unsigned32
	MAX-ACCESS	read-write
	STATUS	current
	DESCRIPTION
		"."
	::= { bgs10IMALinkStatEntry 6 }

bgs10ImaLinkStatRxLid OBJECT-TYPE
	SYNTAX	Unsigned32
	MAX-ACCESS	read-write
	STATUS	current
	DESCRIPTION
		"."
	::= { bgs10IMALinkStatEntry 7 }

bgs10ImaLinkStatRelDelay OBJECT-TYPE
	SYNTAX	UCHAR
	MAX-ACCESS	read-write
	STATUS	current
	DESCRIPTION
		"."
	::= { bgs10IMALinkStatEntry 8 }

bgs10ImaLinkStatImaViolations OBJECT-TYPE
	SYNTAX	Unsigned32
	MAX-ACCESS	read-write
	STATUS	current
	DESCRIPTION
		"."
	::= { bgs10IMALinkStatEntry 9 }

bgs10ImaLinkStatOifAnomalies OBJECT-TYPE
	SYNTAX	Unsigned32
	MAX-ACCESS	read-write
	STATUS	current
	DESCRIPTION
		"."
	::= { bgs10IMALinkStatEntry 10 }

bgs10ImaLinkStatNeSevErroredSec OBJECT-TYPE
	SYNTAX	Unsigned32
	MAX-ACCESS	read-write
	STATUS	current
	DESCRIPTION
		"."
	::= { bgs10IMALinkStatEntry 11 }

bgs10ImaLinkStatFeSevErroredSec OBJECT-TYPE
	SYNTAX	Unsigned32
	MAX-ACCESS	read-write
	STATUS	current
	DESCRIPTION
		"."
	::= { bgs10IMALinkStatEntry 12 }

bgs10ImaLinkStatNeUnavailSec OBJECT-TYPE
	SYNTAX	Unsigned32
	MAX-ACCESS	read-write
	STATUS	current
	DESCRIPTION
		"."
	::= { bgs10IMALinkStatEntry 13 }

bgs10ImaLinkStatFeUnavailSec OBJECT-TYPE
	SYNTAX	Unsigned32
	MAX-ACCESS	read-write
	STATUS	current
	DESCRIPTION
		"."
	::= { bgs10IMALinkStatEntry 14 }

bgs10ImaLinkStatNeTxUnusableSec OBJECT-TYPE
	SYNTAX	Unsigned32
	MAX-ACCESS	read-write
	STATUS	current
	DESCRIPTION
		"."
	::= { bgs10IMALinkStatEntry 15 }

bgs10ImaLinkStatNeRxUnusableSec OBJECT-TYPE
	SYNTAX	Unsigned32
	MAX-ACCESS	read-write
	STATUS	current
	DESCRIPTION
		"."
	::= { bgs10IMALinkStatEntry 16 }

bgs10ImaLinkStatFeTxUnusableSec OBJECT-TYPE
	SYNTAX	Unsigned32
	MAX-ACCESS	read-write
	STATUS	current
	DESCRIPTION
		"."
	::= { bgs10IMALinkStatEntry 17 }

bgs10ImaLinkStatFeRxUnusableSec OBJECT-TYPE
	SYNTAX	Unsigned32
	MAX-ACCESS	read-write
	STATUS	current
	DESCRIPTION
		"."
	::= { bgs10IMALinkStatEntry 18 }

bgs10ImaLinkStatNeTxNumFailures OBJECT-TYPE
	SYNTAX	Unsigned32
	MAX-ACCESS	read-write
	STATUS	current
	DESCRIPTION
		"."
	::= { bgs10IMALinkStatEntry 19 }

bgs10ImaLinkStatNeRxNumFailures OBJECT-TYPE
	SYNTAX	Unsigned32
	MAX-ACCESS	read-write
	STATUS	current
	DESCRIPTION
		"."
	::= { bgs10IMALinkStatEntry 20 }

bgs10ImaLinkStatFeTxNumFailures OBJECT-TYPE
	SYNTAX	Unsigned32
	MAX-ACCESS	read-write
	STATUS	current
	DESCRIPTION
		"."
	::= { bgs10IMALinkStatEntry 21 }

bgs10ImaLinkStatFeRxNumFailures OBJECT-TYPE
	SYNTAX	Unsigned32
	MAX-ACCESS	read-write
	STATUS	current
	DESCRIPTION
		"."
	::= { bgs10IMALinkStatEntry 22 }

bgs10ImaLinkStatTxStuffs OBJECT-TYPE
	SYNTAX	Unsigned32
	MAX-ACCESS	read-write
	STATUS	current
	DESCRIPTION
		"."
	::= { bgs10IMALinkStatEntry 23 }

bgs10ImaLinkStatRxStuffs OBJECT-TYPE
	SYNTAX	Unsigned32
	MAX-ACCESS	read-write
	STATUS	current
	DESCRIPTION
		"."
	::= { bgs10IMALinkStatEntry 24 }

bgs10ImaLinkStatRxTestPattern OBJECT-TYPE
	SYNTAX	UCHAR
	MAX-ACCESS	read-write
	STATUS	current
	DESCRIPTION
		"."
	::= { bgs10IMALinkStatEntry 25 }

-- bgs10MPEGNodePriorityTable
bgs10MPEGNodePriorityTable OBJECT-TYPE
	SYNTAX	SEQUENCE OF BGS10MPEGNodePriorityEntry
	MAX-ACCESS	not-accessible
	STATUS	current
	DESCRIPTION
		""
	::= { zxbgs10mib 71 }

bgs10MPEGNodePriorityEntry OBJECT-TYPE
	SYNTAX	BGS10MPEGNodePriorityEntry
	MAX-ACCESS	not-accessible
	STATUS	current
	DESCRIPTION
		"."
	INDEX {
		bgs10MPEGNodePriorityPriority
		}
	::= { bgs10MPEGNodePriorityTable 1 }
	
BGS10MPEGNodePriorityEntry ::=
	SEQUENCE {
		bgs10MPEGNodePriorityRowStatus		RowStatus,
		bgs10MPEGNodePriorityPriority		UCHAR,
		bgs10MPEGNodePriorityIPAddress		IpAddress,
		bgs10MPEGNodePriorityControlNode	UCHAR
}                    
                                                     
bgs10MPEGNodePriorityRowStatus OBJECT-TYPE
	SYNTAX	RowStatus
	MAX-ACCESS	read-write
	STATUS	current
	DESCRIPTION
		"."
	::= { bgs10MPEGNodePriorityEntry 1 }

bgs10MPEGNodePriorityPriority OBJECT-TYPE
	SYNTAX	UCHAR
	MAX-ACCESS	read-write
	STATUS	current
	DESCRIPTION
		"."
	::= { bgs10MPEGNodePriorityEntry 2 }

bgs10MPEGNodePriorityIPAddress OBJECT-TYPE
	SYNTAX	IpAddress
	MAX-ACCESS	read-write
	STATUS	current
	DESCRIPTION
		"."
	::= { bgs10MPEGNodePriorityEntry 3 }

bgs10MPEGNodePriorityControlNode OBJECT-TYPE
	SYNTAX	UCHAR
	MAX-ACCESS	read-write
	STATUS	current
	DESCRIPTION
		"."
	::= { bgs10MPEGNodePriorityEntry 4 }

-- bgs10MPEGEncodePortTable
bgs10MPEGEncodePortTable OBJECT-TYPE
	SYNTAX	SEQUENCE OF BGS10MPEGEncodePortEntry
	MAX-ACCESS	not-accessible
	STATUS	current
	DESCRIPTION
		""
	::= { zxbgs10mib 72 }

bgs10MPEGEncodePortEntry OBJECT-TYPE
	SYNTAX	BGS10MPEGEncodePortEntry
	MAX-ACCESS	not-accessible
	STATUS	current
	DESCRIPTION
		"."
	INDEX {
		bgs10MPEGEncodePortSourceNode,
		bgs10MPEGEncodePortSourceModule,
		bgs10MPEGEncodePortSourcePort
		}
	::= { bgs10MPEGEncodePortTable 1 }
	
BGS10MPEGEncodePortEntry ::=
	SEQUENCE {
		bgs10MPEGEncodePortRowStatus		RowStatus,
		bgs10MPEGEncodePortSourceNode		UCHAR,
		bgs10MPEGEncodePortSourceModule		UCHAR,
		bgs10MPEGEncodePortSourcePort		UShort,
		bgs10MPEGEncodePortFrameScale		INTEGER,
		bgs10MPEGEncodePortVideoSystem		INTEGER,
		bgs10MPEGEncodePortRate				INTEGER,
		bgs10MPEGEncodePortADNo				INTEGER
}                    
                                                     
bgs10MPEGEncodePortRowStatus OBJECT-TYPE
	SYNTAX	RowStatus
	MAX-ACCESS	read-write
	STATUS	current
	DESCRIPTION
		"."
	::= { bgs10MPEGEncodePortEntry 1 }

bgs10MPEGEncodePortSourceNode OBJECT-TYPE
	SYNTAX	UCHAR
	MAX-ACCESS	read-write
	STATUS	current
	DESCRIPTION
		"."
	::= { bgs10MPEGEncodePortEntry 2 }

bgs10MPEGEncodePortSourceModule OBJECT-TYPE
	SYNTAX	UCHAR
	MAX-ACCESS	read-write
	STATUS	current
	DESCRIPTION
		"."
	::= { bgs10MPEGEncodePortEntry 3 }

bgs10MPEGEncodePortSourcePort OBJECT-TYPE
	SYNTAX	UShort
	MAX-ACCESS	read-write
	STATUS	current
	DESCRIPTION
		"."
	::= { bgs10MPEGEncodePortEntry 4 }

bgs10MPEGEncodePortFrameScale OBJECT-TYPE
	SYNTAX	INTEGER
	MAX-ACCESS	read-write
	STATUS	current
	DESCRIPTION
		"."
	::= { bgs10MPEGEncodePortEntry 5 }

bgs10MPEGEncodePortVideoSystem OBJECT-TYPE
	SYNTAX	INTEGER
	MAX-ACCESS	read-write
	STATUS	current
	DESCRIPTION
		"."
	::= { bgs10MPEGEncodePortEntry 6 }

bgs10MPEGEncodePortRate OBJECT-TYPE
	SYNTAX	INTEGER
	MAX-ACCESS	read-write
	STATUS	current
	DESCRIPTION
		"."
	::= { bgs10MPEGEncodePortEntry 7 }

bgs10MPEGEncodePortADNo OBJECT-TYPE
	SYNTAX	INTEGER
	MAX-ACCESS	read-write
	STATUS	current
	DESCRIPTION
		"."
	::= { bgs10MPEGEncodePortEntry 8 }

-- bgs10RadiusClient
bgs10RadiusClient OBJECT-TYPE
	SYNTAX	SEQUENCE OF BGS10RadiusClientEntry
	MAX-ACCESS	not-accessible
	STATUS	current
	DESCRIPTION
		""
	::= { zxbgs10mib 73 }

bgs10RadiusClientEntry OBJECT-TYPE
	SYNTAX	BGS10RadiusClientEntry
	MAX-ACCESS	not-accessible
	STATUS	current
	DESCRIPTION
		"."
	INDEX {
		bgs10RadiusClinetIspType
		}
	::= { bgs10RadiusClient 1 }
	
BGS10RadiusClientEntry ::=
	SEQUENCE {
		bgs10RadiusClinetRowStatus		RowStatus,
		bgs10RadiusClinetIspName		OCTET STRING(SIZE(33)),
		bgs10RadiusClinetIspDscpt1		OCTET STRING(SIZE(40)),
		bgs10RadiusClinetIspDscpt2		OCTET STRING(SIZE(40)),
		bgs10RadiusClinetIspDscpt3		OCTET STRING(SIZE(21)),
		bgs10RadiusClinetIspScrt		OCTET STRING(SIZE(17)),
		bgs10RadiusClinetIspType		UCHAR,
		bgs10RadiusClinetClientAddr		Unsigned32,
		bgs10RadiusClinetDNS1stAddr   	Unsigned32,
		bgs10RadiusClinetDNS2ndAddr   	Unsigned32,
		bgs10RadiusAuthClientInvalidServerAddresses		Unsigned32,
		bgs10RadiusAuthClientIdentifier					OCTET STRING(SIZE(32)),
		bgs10RadiusAuthServerIndex1						Unsigned32,
		bgs10RadiusAuthServerAddress1					IpAddress,
		bgs10RadiusAuthClientServerPortNumber1			Unsigned32,
		bgs10RadiusAuthClientRoundTripTime1				TimeTicks,
		bgs10RadiusAuthClientAccessRequests1			Unsigned32,
		bgs10RadiusAuthClientAccessRetransmissions1		Unsigned32,
		bgs10RadiusAuthClientAccessAccepts1				Unsigned32,
		bgs10RadiusAuthClientAccessRejects1  			Unsigned32,
		bgs10RadiusAuthClientAccessChallenges1			Unsigned32,
		bgs10RadiusAuthClientMalformedAccessResponses1	Unsigned32,
		bgs10RadiusAuthClientBadAuthenticatorss1		Unsigned32,
		bgs10RadiusAuthClientPendingRequests1  			Unsigned32,
		bgs10RadiusAuthClientTimeouts1 					Unsigned32,
		bgs10RadiusAuthClientUnknownTypes1				Unsigned32,
		bgs10RadiusAuthClientPacketsDropped1			Unsigned32,
		bgs10RadiusAuthServerIndex2						Unsigned32,
		bgs10RadiusAuthServerAddress2					IpAddress,
		bgs10RadiusAuthClientServerPortNumber2			Unsigned32,
		bgs10RadiusAuthClientRoundTripTime2				TimeTicks,
		bgs10RadiusAuthClientAccessRequests2			Unsigned32,
		bgs10RadiusAuthClientAccessRetransmissions2		Unsigned32,
		bgs10RadiusAuthClientAccessAccepts2				Unsigned32,
		bgs10RadiusAuthClientAccessRejects2  			Unsigned32,
		bgs10RadiusAuthClientAccessChallenges2			Unsigned32,
		bgs10RadiusAuthClientMalformedAccessResponses2	Unsigned32,
		bgs10RadiusAuthClientBadAuthenticatorss2		Unsigned32,
		bgs10RadiusAuthClientPendingRequests2  			Unsigned32,
		bgs10RadiusAuthClientTimeouts2 					Unsigned32,
		bgs10RadiusAuthClientUnknownTypes2				Unsigned32,
		bgs10RadiusAuthClientPacketsDropped2			Unsigned32,
		bgs10RadiusAuthServerIndex3						Unsigned32,
		bgs10RadiusAuthServerAddress3					IpAddress,
		bgs10RadiusAuthClientServerPortNumber3			Unsigned32,
		bgs10RadiusAuthClientRoundTripTime3				TimeTicks,
		bgs10RadiusAuthClientAccessRequests3			Unsigned32,
		bgs10RadiusAuthClientAccessRetransmissions3		Unsigned32,
		bgs10RadiusAuthClientAccessAccepts3				Unsigned32,
		bgs10RadiusAuthClientAccessRejects3  			Unsigned32,
		bgs10RadiusAuthClientAccessChallenges3			Unsigned32,
		bgs10RadiusAuthClientMalformedAccessResponses3	Unsigned32,
		bgs10RadiusAuthClientBadAuthenticatorss3		Unsigned32,
		bgs10RadiusAuthClientPendingRequests3  			Unsigned32,
		bgs10RadiusAuthClientTimeouts3 					Unsigned32,
		bgs10RadiusAuthClientUnknownTypes3				Unsigned32,
		bgs10RadiusAuthClientPacketsDropped3			Unsigned32,
		bgs10RadiusAuthServerIndex4						Unsigned32,
		bgs10RadiusAuthServerAddress4					IpAddress,
		bgs10RadiusAuthClientServerPortNumber4			Unsigned32,
		bgs10RadiusAuthClientRoundTripTime4				TimeTicks,
		bgs10RadiusAuthClientAccessRequests4			Unsigned32,
		bgs10RadiusAuthClientAccessRetransmissions4		Unsigned32,
		bgs10RadiusAuthClientAccessAccepts4				Unsigned32,
		bgs10RadiusAuthClientAccessRejects4  			Unsigned32,
		bgs10RadiusAuthClientAccessChallenges4			Unsigned32,
		bgs10RadiusAuthClientMalformedAccessResponses4	Unsigned32,
		bgs10RadiusAuthClientBadAuthenticatorss4		Unsigned32,
		bgs10RadiusAuthClientPendingRequests4  			Unsigned32,
		bgs10RadiusAuthClientTimeouts4 					Unsigned32,
		bgs10RadiusAuthClientUnknownTypes4				Unsigned32,
		bgs10RadiusAuthClientPacketsDropped4			Unsigned32,
		bgs10RadiusAuthServerIndex5						Unsigned32,
		bgs10RadiusAuthServerAddress5					IpAddress,
		bgs10RadiusAuthClientServerPortNumber5			Unsigned32,
		bgs10RadiusAuthClientRoundTripTime5				TimeTicks,
		bgs10RadiusAuthClientAccessRequests5			Unsigned32,
		bgs10RadiusAuthClientAccessRetransmissions5		Unsigned32,
		bgs10RadiusAuthClientAccessAccepts5				Unsigned32,
		bgs10RadiusAuthClientAccessRejects5  			Unsigned32,
		bgs10RadiusAuthClientAccessChallenges5			Unsigned32,
		bgs10RadiusAuthClientMalformedAccessResponses5	Unsigned32,
		bgs10RadiusAuthClientBadAuthenticatorss5		Unsigned32,
		bgs10RadiusAuthClientPendingRequests5  			Unsigned32,
		bgs10RadiusAuthClientTimeouts5 					Unsigned32,
		bgs10RadiusAuthClientUnknownTypes5				Unsigned32,
		bgs10RadiusAuthClientPacketsDropped5			Unsigned32,
		bgs10RadiusAccClientInvalidServerAddresses		Unsigned32,
		bgs10RadiusAccClientIdentifier					OCTET STRING(SIZE(32)),
	    bgs10RadiusAccServerIndex1             			Unsigned32,
	    bgs10RadiusAccServerAddress1           			IpAddress,
	    bgs10RadiusAccClientServerPortNumber1  			Unsigned32,
	    bgs10RadiusAccClientRoundTripTime1     			TimeTicks,
	    bgs10RadiusAccClientRequests1          			Unsigned32,
	    bgs10RadiusAccClientRetransmissions1   			Unsigned32,
	    bgs10RadiusAccClientResponses1         			Unsigned32,
	    bgs10RadiusAccClientMalformedResponses1			Unsigned32,
	    bgs10RadiusAccClientBadAuthenticators1 			Unsigned32,
	    bgs10RadiusAccClientPendingRequests1   			Unsigned32,
	    bgs10RadiusAccClientTimeouts1          			Unsigned32,
	    bgs10RadiusAccClientUnknownTypes1      			Unsigned32,
		bgs10RadiusAccClientPacketsDropped1    			Unsigned32,
	    bgs10RadiusAccServerIndex2             			Unsigned32,
	    bgs10RadiusAccServerAddress2           			IpAddress,
	    bgs10RadiusAccClientServerPortNumber2  			Unsigned32,
	    bgs10RadiusAccClientRoundTripTime2     			TimeTicks,
	    bgs10RadiusAccClientRequests2          			Unsigned32,
	    bgs10RadiusAccClientRetransmissions2   			Unsigned32,
	    bgs10RadiusAccClientResponses2         			Unsigned32,
	    bgs10RadiusAccClientMalformedResponses2			Unsigned32,
	    bgs10RadiusAccClientBadAuthenticators2 			Unsigned32,
	    bgs10RadiusAccClientPendingRequests2   			Unsigned32,
	    bgs10RadiusAccClientTimeouts2          			Unsigned32,
	    bgs10RadiusAccClientUnknownTypes2      			Unsigned32,
		bgs10RadiusAccClientPacketsDropped2    			Unsigned32,
	    bgs10RadiusAccServerIndex3             			Unsigned32,
	    bgs10RadiusAccServerAddress3           			IpAddress,
	    bgs10RadiusAccClientServerPortNumber3  			Unsigned32,
	    bgs10RadiusAccClientRoundTripTime3     			TimeTicks,
	    bgs10RadiusAccClientRequests3          			Unsigned32,
	    bgs10RadiusAccClientRetransmissions3   			Unsigned32,
	    bgs10RadiusAccClientResponses3         			Unsigned32,
	    bgs10RadiusAccClientMalformedResponses3			Unsigned32,
	    bgs10RadiusAccClientBadAuthenticators3 			Unsigned32,
	    bgs10RadiusAccClientPendingRequests3   			Unsigned32,
	    bgs10RadiusAccClientTimeouts3          			Unsigned32,
	    bgs10RadiusAccClientUnknownTypes3      			Unsigned32,
		bgs10RadiusAccClientPacketsDropped3    			Unsigned32,
	    bgs10RadiusAccServerIndex4             			Unsigned32,
	    bgs10RadiusAccServerAddress4           			IpAddress,
	    bgs10RadiusAccClientServerPortNumber4  			Unsigned32,
	    bgs10RadiusAccClientRoundTripTime4     			TimeTicks,
	    bgs10RadiusAccClientRequests4          			Unsigned32,
	    bgs10RadiusAccClientRetransmissions4   			Unsigned32,
	    bgs10RadiusAccClientResponses4         			Unsigned32,
	    bgs10RadiusAccClientMalformedResponses4			Unsigned32,
	    bgs10RadiusAccClientBadAuthenticators4 			Unsigned32,
	    bgs10RadiusAccClientPendingRequests4   			Unsigned32,
	    bgs10RadiusAccClientTimeouts4          			Unsigned32,
	    bgs10RadiusAccClientUnknownTypes4      			Unsigned32,
		bgs10RadiusAccClientPacketsDropped4    			Unsigned32,
	    bgs10RadiusAccServerIndex5             			Unsigned32,
	    bgs10RadiusAccServerAddress5           			IpAddress,
	    bgs10RadiusAccClientServerPortNumber5  			Unsigned32,
	    bgs10RadiusAccClientRoundTripTime5     			TimeTicks,
	    bgs10RadiusAccClientRequests5          			Unsigned32,
	    bgs10RadiusAccClientRetransmissions5   			Unsigned32,
	    bgs10RadiusAccClientResponses5         			Unsigned32,
	    bgs10RadiusAccClientMalformedResponses5			Unsigned32,
	    bgs10RadiusAccClientBadAuthenticators5 			Unsigned32,
	    bgs10RadiusAccClientPendingRequests5   			Unsigned32,
	    bgs10RadiusAccClientTimeouts5          			Unsigned32,
	    bgs10RadiusAccClientUnknownTypes5      			Unsigned32,
		bgs10RadiusAccClientPacketsDropped5    			Unsigned32,
		bgs10RadiusAccClientModule		    			UCHAR,
		bgs10RadiusClinetIspScrtNew1					OCTET STRING(SIZE(35)),
		bgs10RadiusClinetIspScrtNew2					OCTET STRING(SIZE(30))				
}                    
                                                     
bgs10RadiusClinetRowStatus OBJECT-TYPE
	SYNTAX	RowStatus
	MAX-ACCESS	read-write
	STATUS	current
	DESCRIPTION
		"."
	::= { bgs10RadiusClientEntry 1 }

bgs10RadiusClinetIspName OBJECT-TYPE
	SYNTAX	OCTET STRING(SIZE(33))
	MAX-ACCESS	read-write
	STATUS	current
	DESCRIPTION
		"."
	::= { bgs10RadiusClientEntry 2 }

bgs10RadiusClinetIspDscpt1 OBJECT-TYPE
	SYNTAX	OCTET STRING(SIZE(40))
	MAX-ACCESS	read-write
	STATUS	current
	DESCRIPTION
		"."
	::= { bgs10RadiusClientEntry 3 }

bgs10RadiusClinetIspDscpt2 OBJECT-TYPE
	SYNTAX	OCTET STRING(SIZE(40))
	MAX-ACCESS	read-write
	STATUS	current
	DESCRIPTION
		"."
	::= { bgs10RadiusClientEntry 4 }

bgs10RadiusClinetIspDscpt3 OBJECT-TYPE
	SYNTAX	OCTET STRING(SIZE(21))
	MAX-ACCESS	read-write
	STATUS	current
	DESCRIPTION
		"."
	::= { bgs10RadiusClientEntry 5 }

bgs10RadiusClinetIspScrt OBJECT-TYPE
	SYNTAX	OCTET STRING(SIZE(17))
	MAX-ACCESS	read-write
	STATUS	current
	DESCRIPTION
		"."
	::= { bgs10RadiusClientEntry 6 }

bgs10RadiusClinetIspType OBJECT-TYPE
	SYNTAX	UCHAR
	MAX-ACCESS	read-write
	STATUS	current
	DESCRIPTION
		"."
	::= { bgs10RadiusClientEntry 7 }

bgs10RadiusClinetClientAddr OBJECT-TYPE
	SYNTAX	Unsigned32
	MAX-ACCESS	read-write
	STATUS	current
	DESCRIPTION
		"."
	::= { bgs10RadiusClientEntry 8 }

bgs10RadiusClinetDNS1stAddr OBJECT-TYPE
	SYNTAX	Unsigned32
	MAX-ACCESS	read-write
	STATUS	current
	DESCRIPTION
		"."
	::= { bgs10RadiusClientEntry 9 }

bgs10RadiusClinetDNS2ndAddr OBJECT-TYPE
	SYNTAX	Unsigned32
	MAX-ACCESS	read-write
	STATUS	current
	DESCRIPTION
		"."
	::= { bgs10RadiusClientEntry 10 }

bgs10RadiusAuthClientInvalidServerAddresses OBJECT-TYPE
	SYNTAX	Unsigned32
	MAX-ACCESS	read-write
	STATUS	current
	DESCRIPTION
		"."
	::= { bgs10RadiusClientEntry 11 }

bgs10RadiusAuthClientIdentifier OBJECT-TYPE
	SYNTAX	OCTET STRING(SIZE(32))
	MAX-ACCESS	read-write
	STATUS	current
	DESCRIPTION
		"."
	::= { bgs10RadiusClientEntry 12 }

bgs10RadiusAuthServerIndex1 OBJECT-TYPE
	SYNTAX	Unsigned32
	MAX-ACCESS	read-write
	STATUS	current
	DESCRIPTION
		"."
	::= { bgs10RadiusClientEntry 13 }

bgs10RadiusAuthServerAddress1 OBJECT-TYPE
	SYNTAX	IpAddress
	MAX-ACCESS	read-write
	STATUS	current
	DESCRIPTION
		"."
	::= { bgs10RadiusClientEntry 14 }

bgs10RadiusAuthClientServerPortNumber1 OBJECT-TYPE
	SYNTAX	Unsigned32
	MAX-ACCESS	read-write
	STATUS	current
	DESCRIPTION
		"."
	::= { bgs10RadiusClientEntry 15 }

bgs10RadiusAuthClientRoundTripTime1 OBJECT-TYPE
	SYNTAX	TimeTicks
	MAX-ACCESS	read-write
	STATUS	current
	DESCRIPTION
		"."
	::= { bgs10RadiusClientEntry 16 }

bgs10RadiusAuthClientAccessRequests1 OBJECT-TYPE
	SYNTAX		Unsigned32
	MAX-ACCESS	read-write
	STATUS	current
	DESCRIPTION
		"."
	::= { bgs10RadiusClientEntry 17 }

bgs10RadiusAuthClientAccessRetransmissions1 OBJECT-TYPE
	SYNTAX		Unsigned32
	MAX-ACCESS	read-write
	STATUS	current
	DESCRIPTION
		"."
	::= { bgs10RadiusClientEntry 18 }

bgs10RadiusAuthClientAccessAccepts1 OBJECT-TYPE
	SYNTAX		Unsigned32
	MAX-ACCESS	read-write
	STATUS	current
	DESCRIPTION
		"."
	::= { bgs10RadiusClientEntry 19 }

bgs10RadiusAuthClientAccessRejects1 OBJECT-TYPE
	SYNTAX		Unsigned32
	MAX-ACCESS	read-write
	STATUS	current
	DESCRIPTION
		"."
	::= { bgs10RadiusClientEntry 20 }

bgs10RadiusAuthClientAccessChallenges1 OBJECT-TYPE
	SYNTAX		Unsigned32
	MAX-ACCESS	read-write
	STATUS	current
	DESCRIPTION
		"."
	::= { bgs10RadiusClientEntry 21 }

bgs10RadiusAuthClientMalformedAccessResponses1 OBJECT-TYPE
	SYNTAX		Unsigned32
	MAX-ACCESS	read-write
	STATUS	current
	DESCRIPTION
		"."
	::= { bgs10RadiusClientEntry 22 }

bgs10RadiusAuthClientBadAuthenticatorss1 OBJECT-TYPE
	SYNTAX		Unsigned32
	MAX-ACCESS	read-write
	STATUS	current
	DESCRIPTION
		"."
	::= { bgs10RadiusClientEntry 23 }

bgs10RadiusAuthClientPendingRequests1 OBJECT-TYPE
	SYNTAX		Unsigned32
	MAX-ACCESS	read-write
	STATUS	current
	DESCRIPTION
		"."
	::= { bgs10RadiusClientEntry 24 }

bgs10RadiusAuthClientTimeouts1 OBJECT-TYPE
	SYNTAX		Unsigned32
	MAX-ACCESS	read-write
	STATUS	current
	DESCRIPTION
		"."
	::= { bgs10RadiusClientEntry 25 }

bgs10RadiusAuthClientUnknownTypes1 OBJECT-TYPE
	SYNTAX		Unsigned32
	MAX-ACCESS	read-write
	STATUS	current
	DESCRIPTION
		"."
	::= { bgs10RadiusClientEntry 26 }

bgs10RadiusAuthClientPacketsDropped1 OBJECT-TYPE
	SYNTAX		Unsigned32
	MAX-ACCESS	read-write
	STATUS	current
	DESCRIPTION
		"."
	::= { bgs10RadiusClientEntry 27 }

bgs10RadiusAuthServerIndex2 OBJECT-TYPE
	SYNTAX	Unsigned32
	MAX-ACCESS	read-write
	STATUS	current
	DESCRIPTION
		"."
	::= { bgs10RadiusClientEntry 28 }

bgs10RadiusAuthServerAddress2 OBJECT-TYPE
	SYNTAX	IpAddress
	MAX-ACCESS	read-write
	STATUS	current
	DESCRIPTION
		"."
	::= { bgs10RadiusClientEntry 29 }

bgs10RadiusAuthClientServerPortNumber2 OBJECT-TYPE
	SYNTAX	Unsigned32
	MAX-ACCESS	read-write
	STATUS	current
	DESCRIPTION
		"."
	::= { bgs10RadiusClientEntry 30 }

bgs10RadiusAuthClientRoundTripTime2 OBJECT-TYPE
	SYNTAX	TimeTicks
	MAX-ACCESS	read-write
	STATUS	current
	DESCRIPTION
		"."
	::= { bgs10RadiusClientEntry 31 }

bgs10RadiusAuthClientAccessRequests2 OBJECT-TYPE
	SYNTAX		Unsigned32
	MAX-ACCESS	read-write
	STATUS	current
	DESCRIPTION
		"."
	::= { bgs10RadiusClientEntry 32 }

bgs10RadiusAuthClientAccessRetransmissions2 OBJECT-TYPE
	SYNTAX		Unsigned32
	MAX-ACCESS	read-write
	STATUS	current
	DESCRIPTION
		"."
	::= { bgs10RadiusClientEntry 33 }

bgs10RadiusAuthClientAccessAccepts2 OBJECT-TYPE
	SYNTAX		Unsigned32
	MAX-ACCESS	read-write
	STATUS	current
	DESCRIPTION
		"."
	::= { bgs10RadiusClientEntry 34 }

bgs10RadiusAuthClientAccessRejects2 OBJECT-TYPE
	SYNTAX		Unsigned32
	MAX-ACCESS	read-write
	STATUS	current
	DESCRIPTION
		"."
	::= { bgs10RadiusClientEntry 35 }

bgs10RadiusAuthClientAccessChallenges2 OBJECT-TYPE
	SYNTAX		Unsigned32
	MAX-ACCESS	read-write
	STATUS	current
	DESCRIPTION
		"."
	::= { bgs10RadiusClientEntry 36 }

bgs10RadiusAuthClientMalformedAccessResponses2 OBJECT-TYPE
	SYNTAX		Unsigned32
	MAX-ACCESS	read-write
	STATUS	current
	DESCRIPTION
		"."
	::= { bgs10RadiusClientEntry 37 }

bgs10RadiusAuthClientBadAuthenticatorss2 OBJECT-TYPE
	SYNTAX		Unsigned32
	MAX-ACCESS	read-write
	STATUS	current
	DESCRIPTION
		"."
	::= { bgs10RadiusClientEntry 38 }

bgs10RadiusAuthClientPendingRequests2 OBJECT-TYPE
	SYNTAX		Unsigned32
	MAX-ACCESS	read-write
	STATUS	current
	DESCRIPTION
		"."
	::= { bgs10RadiusClientEntry 39 }

bgs10RadiusAuthClientTimeouts2 OBJECT-TYPE
	SYNTAX		Unsigned32
	MAX-ACCESS	read-write
	STATUS	current
	DESCRIPTION
		"."
	::= { bgs10RadiusClientEntry 40 }

bgs10RadiusAuthClientUnknownTypes2 OBJECT-TYPE
	SYNTAX		Unsigned32
	MAX-ACCESS	read-write
	STATUS	current
	DESCRIPTION
		"."
	::= { bgs10RadiusClientEntry 41 }

bgs10RadiusAuthClientPacketsDropped2 OBJECT-TYPE
	SYNTAX		Unsigned32
	MAX-ACCESS	read-write
	STATUS	current
	DESCRIPTION
		"."
	::= { bgs10RadiusClientEntry 42 }

bgs10RadiusAuthServerIndex3 OBJECT-TYPE
	SYNTAX	Unsigned32
	MAX-ACCESS	read-write
	STATUS	current
	DESCRIPTION
		"."
	::= { bgs10RadiusClientEntry 43 }

bgs10RadiusAuthServerAddress3 OBJECT-TYPE
	SYNTAX	IpAddress
	MAX-ACCESS	read-write
	STATUS	current
	DESCRIPTION
		"."
	::= { bgs10RadiusClientEntry 44 }

bgs10RadiusAuthClientServerPortNumber3 OBJECT-TYPE
	SYNTAX	Unsigned32
	MAX-ACCESS	read-write
	STATUS	current
	DESCRIPTION
		"."
	::= { bgs10RadiusClientEntry 45 }

bgs10RadiusAuthClientRoundTripTime3 OBJECT-TYPE
	SYNTAX	TimeTicks
	MAX-ACCESS	read-write
	STATUS	current
	DESCRIPTION
		"."
	::= { bgs10RadiusClientEntry 46 }

bgs10RadiusAuthClientAccessRequests3 OBJECT-TYPE
	SYNTAX		Unsigned32
	MAX-ACCESS	read-write
	STATUS	current
	DESCRIPTION
		"."
	::= { bgs10RadiusClientEntry 47 }

bgs10RadiusAuthClientAccessRetransmissions3 OBJECT-TYPE
	SYNTAX		Unsigned32
	MAX-ACCESS	read-write
	STATUS	current
	DESCRIPTION
		"."
	::= { bgs10RadiusClientEntry 48 }

bgs10RadiusAuthClientAccessAccepts3 OBJECT-TYPE
	SYNTAX		Unsigned32
	MAX-ACCESS	read-write
	STATUS	current
	DESCRIPTION
		"."
	::= { bgs10RadiusClientEntry 49 }

bgs10RadiusAuthClientAccessRejects3 OBJECT-TYPE
	SYNTAX		Unsigned32
	MAX-ACCESS	read-write
	STATUS	current
	DESCRIPTION
		"."
	::= { bgs10RadiusClientEntry 50 }

bgs10RadiusAuthClientAccessChallenges3 OBJECT-TYPE
	SYNTAX		Unsigned32
	MAX-ACCESS	read-write
	STATUS	current
	DESCRIPTION
		"."
	::= { bgs10RadiusClientEntry 51 }

bgs10RadiusAuthClientMalformedAccessResponses3 OBJECT-TYPE
	SYNTAX		Unsigned32
	MAX-ACCESS	read-write
	STATUS	current
	DESCRIPTION
		"."
	::= { bgs10RadiusClientEntry 52 }

bgs10RadiusAuthClientBadAuthenticatorss3 OBJECT-TYPE
	SYNTAX		Unsigned32
	MAX-ACCESS	read-write
	STATUS	current
	DESCRIPTION
		"."
	::= { bgs10RadiusClientEntry 53 }

bgs10RadiusAuthClientPendingRequests3 OBJECT-TYPE
	SYNTAX		Unsigned32
	MAX-ACCESS	read-write
	STATUS	current
	DESCRIPTION
		"."
	::= { bgs10RadiusClientEntry 54 }

bgs10RadiusAuthClientTimeouts3 OBJECT-TYPE
	SYNTAX		Unsigned32
	MAX-ACCESS	read-write
	STATUS	current
	DESCRIPTION
		"."
	::= { bgs10RadiusClientEntry 55 }

bgs10RadiusAuthClientUnknownTypes3 OBJECT-TYPE
	SYNTAX		Unsigned32
	MAX-ACCESS	read-write
	STATUS	current
	DESCRIPTION
		"."
	::= { bgs10RadiusClientEntry 56 }

bgs10RadiusAuthClientPacketsDropped3 OBJECT-TYPE
	SYNTAX		Unsigned32
	MAX-ACCESS	read-write
	STATUS	current
	DESCRIPTION
		"."
	::= { bgs10RadiusClientEntry 57 }

bgs10RadiusAuthServerIndex4 OBJECT-TYPE
	SYNTAX	Unsigned32
	MAX-ACCESS	read-write
	STATUS	current
	DESCRIPTION
		"."
	::= { bgs10RadiusClientEntry 58 }

bgs10RadiusAuthServerAddress4 OBJECT-TYPE
	SYNTAX	IpAddress
	MAX-ACCESS	read-write
	STATUS	current
	DESCRIPTION
		"."
	::= { bgs10RadiusClientEntry 59 }

bgs10RadiusAuthClientServerPortNumber4 OBJECT-TYPE
	SYNTAX	Unsigned32
	MAX-ACCESS	read-write
	STATUS	current
	DESCRIPTION
		"."
	::= { bgs10RadiusClientEntry 60 }

bgs10RadiusAuthClientRoundTripTime4 OBJECT-TYPE
	SYNTAX	TimeTicks
	MAX-ACCESS	read-write
	STATUS	current
	DESCRIPTION
		"."
	::= { bgs10RadiusClientEntry 61 }

bgs10RadiusAuthClientAccessRequests4 OBJECT-TYPE
	SYNTAX		Unsigned32
	MAX-ACCESS	read-write
	STATUS	current
	DESCRIPTION
		"."
	::= { bgs10RadiusClientEntry 62 }

bgs10RadiusAuthClientAccessRetransmissions4 OBJECT-TYPE
	SYNTAX		Unsigned32
	MAX-ACCESS	read-write
	STATUS	current
	DESCRIPTION
		"."
	::= { bgs10RadiusClientEntry 63 }

bgs10RadiusAuthClientAccessAccepts4 OBJECT-TYPE
	SYNTAX		Unsigned32
	MAX-ACCESS	read-write
	STATUS	current
	DESCRIPTION
		"."
	::= { bgs10RadiusClientEntry 64 }

bgs10RadiusAuthClientAccessRejects4 OBJECT-TYPE
	SYNTAX		Unsigned32
	MAX-ACCESS	read-write
	STATUS	current
	DESCRIPTION
		"."
	::= { bgs10RadiusClientEntry 65 }

bgs10RadiusAuthClientAccessChallenges4 OBJECT-TYPE
	SYNTAX		Unsigned32
	MAX-ACCESS	read-write
	STATUS	current
	DESCRIPTION
		"."
	::= { bgs10RadiusClientEntry 66 }

bgs10RadiusAuthClientMalformedAccessResponses4 OBJECT-TYPE
	SYNTAX		Unsigned32
	MAX-ACCESS	read-write
	STATUS	current
	DESCRIPTION
		"."
	::= { bgs10RadiusClientEntry 67 }

bgs10RadiusAuthClientBadAuthenticatorss4 OBJECT-TYPE
	SYNTAX		Unsigned32
	MAX-ACCESS	read-write
	STATUS	current
	DESCRIPTION
		"."
	::= { bgs10RadiusClientEntry 68 }

bgs10RadiusAuthClientPendingRequests4 OBJECT-TYPE
	SYNTAX		Unsigned32
	MAX-ACCESS	read-write
	STATUS	current
	DESCRIPTION
		"."
	::= { bgs10RadiusClientEntry 69 }

bgs10RadiusAuthClientTimeouts4 OBJECT-TYPE
	SYNTAX		Unsigned32
	MAX-ACCESS	read-write
	STATUS	current
	DESCRIPTION
		"."
	::= { bgs10RadiusClientEntry 70 }

bgs10RadiusAuthClientUnknownTypes4 OBJECT-TYPE
	SYNTAX		Unsigned32
	MAX-ACCESS	read-write
	STATUS	current
	DESCRIPTION
		"."
	::= { bgs10RadiusClientEntry 71 }

bgs10RadiusAuthClientPacketsDropped4 OBJECT-TYPE
	SYNTAX		Unsigned32
	MAX-ACCESS	read-write
	STATUS	current
	DESCRIPTION
		"."
	::= { bgs10RadiusClientEntry 72 }

bgs10RadiusAuthServerIndex5 OBJECT-TYPE
	SYNTAX	Unsigned32
	MAX-ACCESS	read-write
	STATUS	current
	DESCRIPTION
		"."
	::= { bgs10RadiusClientEntry 73 }

bgs10RadiusAuthServerAddress5 OBJECT-TYPE
	SYNTAX	IpAddress
	MAX-ACCESS	read-write
	STATUS	current
	DESCRIPTION
		"."
	::= { bgs10RadiusClientEntry 74 }

bgs10RadiusAuthClientServerPortNumber5 OBJECT-TYPE
	SYNTAX	Unsigned32
	MAX-ACCESS	read-write
	STATUS	current
	DESCRIPTION
		"."
	::= { bgs10RadiusClientEntry 75 }

bgs10RadiusAuthClientRoundTripTime5 OBJECT-TYPE
	SYNTAX	TimeTicks
	MAX-ACCESS	read-write
	STATUS	current
	DESCRIPTION
		"."
	::= { bgs10RadiusClientEntry 76 }

bgs10RadiusAuthClientAccessRequests5 OBJECT-TYPE
	SYNTAX		Unsigned32
	MAX-ACCESS	read-write
	STATUS	current
	DESCRIPTION
		"."
	::= { bgs10RadiusClientEntry 77 }

bgs10RadiusAuthClientAccessRetransmissions5 OBJECT-TYPE
	SYNTAX		Unsigned32
	MAX-ACCESS	read-write
	STATUS	current
	DESCRIPTION
		"."
	::= { bgs10RadiusClientEntry 78 }

bgs10RadiusAuthClientAccessAccepts5 OBJECT-TYPE
	SYNTAX		Unsigned32
	MAX-ACCESS	read-write
	STATUS	current
	DESCRIPTION
		"."
	::= { bgs10RadiusClientEntry 79 }

bgs10RadiusAuthClientAccessRejects5 OBJECT-TYPE
	SYNTAX		Unsigned32
	MAX-ACCESS	read-write
	STATUS	current
	DESCRIPTION
		"."
	::= { bgs10RadiusClientEntry 80 }

bgs10RadiusAuthClientAccessChallenges5 OBJECT-TYPE
	SYNTAX		Unsigned32
	MAX-ACCESS	read-write
	STATUS	current
	DESCRIPTION
		"."
	::= { bgs10RadiusClientEntry 81 }

bgs10RadiusAuthClientMalformedAccessResponses5 OBJECT-TYPE
	SYNTAX		Unsigned32
	MAX-ACCESS	read-write
	STATUS	current
	DESCRIPTION
		"."
	::= { bgs10RadiusClientEntry 82 }

bgs10RadiusAuthClientBadAuthenticatorss5 OBJECT-TYPE
	SYNTAX		Unsigned32
	MAX-ACCESS	read-write
	STATUS	current
	DESCRIPTION
		"."
	::= { bgs10RadiusClientEntry 83 }

bgs10RadiusAuthClientPendingRequests5 OBJECT-TYPE
	SYNTAX		Unsigned32
	MAX-ACCESS	read-write
	STATUS	current
	DESCRIPTION
		"."
	::= { bgs10RadiusClientEntry 84 }

bgs10RadiusAuthClientTimeouts5 OBJECT-TYPE
	SYNTAX		Unsigned32
	MAX-ACCESS	read-write
	STATUS	current
	DESCRIPTION
		"."
	::= { bgs10RadiusClientEntry 85 }

bgs10RadiusAuthClientUnknownTypes5 OBJECT-TYPE
	SYNTAX		Unsigned32
	MAX-ACCESS	read-write
	STATUS	current
	DESCRIPTION
		"."
	::= { bgs10RadiusClientEntry 86 }

bgs10RadiusAuthClientPacketsDropped5 OBJECT-TYPE
	SYNTAX		Unsigned32
	MAX-ACCESS	read-write
	STATUS	current
	DESCRIPTION
		"."
	::= { bgs10RadiusClientEntry 87 }

bgs10RadiusAccClientInvalidServerAddresses OBJECT-TYPE
	SYNTAX		Unsigned32
	MAX-ACCESS	read-write
	STATUS	current
	DESCRIPTION
		"."
	::= { bgs10RadiusClientEntry 88 }

bgs10RadiusAccClientIdentifier OBJECT-TYPE
	SYNTAX		OCTET STRING(SIZE(32))
	MAX-ACCESS	read-write
	STATUS	current
	DESCRIPTION
		"."
	::= { bgs10RadiusClientEntry 89 }

bgs10RadiusAccServerIndex1 OBJECT-TYPE
	SYNTAX		Unsigned32
	MAX-ACCESS	read-write
	STATUS	current
	DESCRIPTION
		"."
	::= { bgs10RadiusClientEntry 90 }

bgs10RadiusAccServerAddress1 OBJECT-TYPE
	SYNTAX		IpAddress
	MAX-ACCESS	read-write
	STATUS	current
	DESCRIPTION
		"."
	::= { bgs10RadiusClientEntry 91 }

bgs10RadiusAccClientServerPortNumber1 OBJECT-TYPE
	SYNTAX		Unsigned32
	MAX-ACCESS	read-write
	STATUS	current
	DESCRIPTION
		"."
	::= { bgs10RadiusClientEntry 92 }

bgs10RadiusAccClientRoundTripTime1 OBJECT-TYPE
	SYNTAX		TimeTicks
	MAX-ACCESS	read-write
	STATUS	current
	DESCRIPTION
		"."
	::= { bgs10RadiusClientEntry 93 }

bgs10RadiusAccClientRequests1 OBJECT-TYPE
	SYNTAX		Unsigned32
	MAX-ACCESS	read-write
	STATUS	current
	DESCRIPTION
		"."
	::= { bgs10RadiusClientEntry 94 }

bgs10RadiusAccClientRetransmissions1 OBJECT-TYPE
	SYNTAX		Unsigned32
	MAX-ACCESS	read-write
	STATUS	current
	DESCRIPTION
		"."
	::= { bgs10RadiusClientEntry 95 }

bgs10RadiusAccClientResponses1 OBJECT-TYPE
	SYNTAX		Unsigned32
	MAX-ACCESS	read-write
	STATUS	current
	DESCRIPTION
		"."
	::= { bgs10RadiusClientEntry 96 }

bgs10RadiusAccClientMalformedResponses1 OBJECT-TYPE
	SYNTAX		Unsigned32
	MAX-ACCESS	read-write
	STATUS	current
	DESCRIPTION
		"."
	::= { bgs10RadiusClientEntry 97 }

bgs10RadiusAccClientBadAuthenticators1 OBJECT-TYPE
	SYNTAX		Unsigned32
	MAX-ACCESS	read-write
	STATUS	current
	DESCRIPTION
		"."
	::= { bgs10RadiusClientEntry 98 }

bgs10RadiusAccClientPendingRequests1 OBJECT-TYPE
	SYNTAX		Unsigned32
	MAX-ACCESS	read-write
	STATUS	current
	DESCRIPTION
		"."
	::= { bgs10RadiusClientEntry 99 }

bgs10RadiusAccClientTimeouts1 OBJECT-TYPE
	SYNTAX		Unsigned32
	MAX-ACCESS	read-write
	STATUS	current
	DESCRIPTION
		"."
	::= { bgs10RadiusClientEntry 100 }

bgs10RadiusAccClientUnknownTypes1 OBJECT-TYPE
	SYNTAX		Unsigned32
	MAX-ACCESS	read-write
	STATUS	current
	DESCRIPTION
		"."
	::= { bgs10RadiusClientEntry 101 }

bgs10RadiusAccClientPacketsDropped1 OBJECT-TYPE
	SYNTAX		Unsigned32
	MAX-ACCESS	read-write
	STATUS	current
	DESCRIPTION
		"."
	::= { bgs10RadiusClientEntry 102 }

bgs10RadiusAccServerIndex2 OBJECT-TYPE
	SYNTAX		Unsigned32
	MAX-ACCESS	read-write
	STATUS	current
	DESCRIPTION
		"."
	::= { bgs10RadiusClientEntry 103 }

bgs10RadiusAccServerAddress2 OBJECT-TYPE
	SYNTAX		IpAddress
	MAX-ACCESS	read-write
	STATUS	current
	DESCRIPTION
		"."
	::= { bgs10RadiusClientEntry 104 }

bgs10RadiusAccClientServerPortNumber2 OBJECT-TYPE
	SYNTAX		Unsigned32
	MAX-ACCESS	read-write
	STATUS	current
	DESCRIPTION
		"."
	::= { bgs10RadiusClientEntry 105 }

bgs10RadiusAccClientRoundTripTime2 OBJECT-TYPE
	SYNTAX		TimeTicks
	MAX-ACCESS	read-write
	STATUS	current
	DESCRIPTION
		"."
	::= { bgs10RadiusClientEntry 106 }

bgs10RadiusAccClientRequests2 OBJECT-TYPE
	SYNTAX		Unsigned32
	MAX-ACCESS	read-write
	STATUS	current
	DESCRIPTION
		"."
	::= { bgs10RadiusClientEntry 107 }

bgs10RadiusAccClientRetransmissions2 OBJECT-TYPE
	SYNTAX		Unsigned32
	MAX-ACCESS	read-write
	STATUS	current
	DESCRIPTION
		"."
	::= { bgs10RadiusClientEntry 108 }

bgs10RadiusAccClientResponses2 OBJECT-TYPE
	SYNTAX		Unsigned32
	MAX-ACCESS	read-write
	STATUS	current
	DESCRIPTION
		"."
	::= { bgs10RadiusClientEntry 109 }

bgs10RadiusAccClientMalformedResponses2 OBJECT-TYPE
	SYNTAX		Unsigned32
	MAX-ACCESS	read-write
	STATUS	current
	DESCRIPTION
		"."
	::= { bgs10RadiusClientEntry 110 }

bgs10RadiusAccClientBadAuthenticators2 OBJECT-TYPE
	SYNTAX		Unsigned32
	MAX-ACCESS	read-write
	STATUS	current
	DESCRIPTION
		"."
	::= { bgs10RadiusClientEntry 111 }

bgs10RadiusAccClientPendingRequests2 OBJECT-TYPE
	SYNTAX		Unsigned32
	MAX-ACCESS	read-write
	STATUS	current
	DESCRIPTION
		"."
	::= { bgs10RadiusClientEntry 112 }

bgs10RadiusAccClientTimeouts2 OBJECT-TYPE
	SYNTAX		Unsigned32
	MAX-ACCESS	read-write
	STATUS	current
	DESCRIPTION
		"."
	::= { bgs10RadiusClientEntry 113 }

bgs10RadiusAccClientUnknownTypes2 OBJECT-TYPE
	SYNTAX		Unsigned32
	MAX-ACCESS	read-write
	STATUS	current
	DESCRIPTION
		"."
	::= { bgs10RadiusClientEntry 114 }

bgs10RadiusAccClientPacketsDropped2 OBJECT-TYPE
	SYNTAX		Unsigned32
	MAX-ACCESS	read-write
	STATUS	current
	DESCRIPTION
		"."
	::= { bgs10RadiusClientEntry 115 }

bgs10RadiusAccServerIndex3 OBJECT-TYPE
	SYNTAX		Unsigned32
	MAX-ACCESS	read-write
	STATUS	current
	DESCRIPTION
		"."
	::= { bgs10RadiusClientEntry 116 }

bgs10RadiusAccServerAddress3 OBJECT-TYPE
	SYNTAX		IpAddress
	MAX-ACCESS	read-write
	STATUS	current
	DESCRIPTION
		"."
	::= { bgs10RadiusClientEntry 117 }

bgs10RadiusAccClientServerPortNumber3 OBJECT-TYPE
	SYNTAX		Unsigned32
	MAX-ACCESS	read-write
	STATUS	current
	DESCRIPTION
		"."
	::= { bgs10RadiusClientEntry 118 }

bgs10RadiusAccClientRoundTripTime3 OBJECT-TYPE
	SYNTAX		TimeTicks
	MAX-ACCESS	read-write
	STATUS	current
	DESCRIPTION
		"."
	::= { bgs10RadiusClientEntry 119 }

bgs10RadiusAccClientRequests3 OBJECT-TYPE
	SYNTAX		Unsigned32
	MAX-ACCESS	read-write
	STATUS	current
	DESCRIPTION
		"."
	::= { bgs10RadiusClientEntry 120 }

bgs10RadiusAccClientRetransmissions3 OBJECT-TYPE
	SYNTAX		Unsigned32
	MAX-ACCESS	read-write
	STATUS	current
	DESCRIPTION
		"."
	::= { bgs10RadiusClientEntry 121 }

bgs10RadiusAccClientResponses3 OBJECT-TYPE
	SYNTAX		Unsigned32
	MAX-ACCESS	read-write
	STATUS	current
	DESCRIPTION
		"."
	::= { bgs10RadiusClientEntry 122 }

bgs10RadiusAccClientMalformedResponses3 OBJECT-TYPE
	SYNTAX		Unsigned32
	MAX-ACCESS	read-write
	STATUS	current
	DESCRIPTION
		"."
	::= { bgs10RadiusClientEntry 123 }

bgs10RadiusAccClientBadAuthenticators3 OBJECT-TYPE
	SYNTAX		Unsigned32
	MAX-ACCESS	read-write
	STATUS	current
	DESCRIPTION
		"."
	::= { bgs10RadiusClientEntry 124 }

bgs10RadiusAccClientPendingRequests3 OBJECT-TYPE
	SYNTAX		Unsigned32
	MAX-ACCESS	read-write
	STATUS	current
	DESCRIPTION
		"."
	::= { bgs10RadiusClientEntry 125 }

bgs10RadiusAccClientTimeouts3 OBJECT-TYPE
	SYNTAX		Unsigned32
	MAX-ACCESS	read-write
	STATUS	current
	DESCRIPTION
		"."
	::= { bgs10RadiusClientEntry 126 }

bgs10RadiusAccClientUnknownTypes3 OBJECT-TYPE
	SYNTAX		Unsigned32
	MAX-ACCESS	read-write
	STATUS	current
	DESCRIPTION
		"."
	::= { bgs10RadiusClientEntry 127 }

bgs10RadiusAccClientPacketsDropped3 OBJECT-TYPE
	SYNTAX		Unsigned32
	MAX-ACCESS	read-write
	STATUS	current
	DESCRIPTION
		"."
	::= { bgs10RadiusClientEntry 128 }

bgs10RadiusAccServerIndex4 OBJECT-TYPE
	SYNTAX		Unsigned32
	MAX-ACCESS	read-write
	STATUS	current
	DESCRIPTION
		"."
	::= { bgs10RadiusClientEntry 129 }

bgs10RadiusAccServerAddress4 OBJECT-TYPE
	SYNTAX		IpAddress
	MAX-ACCESS	read-write
	STATUS	current
	DESCRIPTION
		"."
	::= { bgs10RadiusClientEntry 130 }

bgs10RadiusAccClientServerPortNumber4 OBJECT-TYPE
	SYNTAX		Unsigned32
	MAX-ACCESS	read-write
	STATUS	current
	DESCRIPTION
		"."
	::= { bgs10RadiusClientEntry 131 }

bgs10RadiusAccClientRoundTripTime4 OBJECT-TYPE
	SYNTAX		TimeTicks
	MAX-ACCESS	read-write
	STATUS	current
	DESCRIPTION
		"."
	::= { bgs10RadiusClientEntry 132 }

bgs10RadiusAccClientRequests4 OBJECT-TYPE
	SYNTAX		Unsigned32
	MAX-ACCESS	read-write
	STATUS	current
	DESCRIPTION
		"."
	::= { bgs10RadiusClientEntry 133 }

bgs10RadiusAccClientRetransmissions4 OBJECT-TYPE
	SYNTAX		Unsigned32
	MAX-ACCESS	read-write
	STATUS	current
	DESCRIPTION
		"."
	::= { bgs10RadiusClientEntry 134 }

bgs10RadiusAccClientResponses4 OBJECT-TYPE
	SYNTAX		Unsigned32
	MAX-ACCESS	read-write
	STATUS	current
	DESCRIPTION
		"."
	::= { bgs10RadiusClientEntry 135 }

bgs10RadiusAccClientMalformedResponses4 OBJECT-TYPE
	SYNTAX		Unsigned32
	MAX-ACCESS	read-write
	STATUS	current
	DESCRIPTION
		"."
	::= { bgs10RadiusClientEntry 136 }

bgs10RadiusAccClientBadAuthenticators4 OBJECT-TYPE
	SYNTAX		Unsigned32
	MAX-ACCESS	read-write
	STATUS	current
	DESCRIPTION
		"."
	::= { bgs10RadiusClientEntry 137 }

bgs10RadiusAccClientPendingRequests4 OBJECT-TYPE
	SYNTAX		Unsigned32
	MAX-ACCESS	read-write
	STATUS	current
	DESCRIPTION
		"."
	::= { bgs10RadiusClientEntry 138 }

bgs10RadiusAccClientTimeouts4 OBJECT-TYPE
	SYNTAX		Unsigned32
	MAX-ACCESS	read-write
	STATUS	current
	DESCRIPTION
		"."
	::= { bgs10RadiusClientEntry 139 }

bgs10RadiusAccClientUnknownTypes4 OBJECT-TYPE
	SYNTAX		Unsigned32
	MAX-ACCESS	read-write
	STATUS	current
	DESCRIPTION
		"."
	::= { bgs10RadiusClientEntry 140 }

bgs10RadiusAccClientPacketsDropped4 OBJECT-TYPE
	SYNTAX		Unsigned32
	MAX-ACCESS	read-write
	STATUS	current
	DESCRIPTION
		"."
	::= { bgs10RadiusClientEntry 141 }

bgs10RadiusAccServerIndex5 OBJECT-TYPE
	SYNTAX		Unsigned32
	MAX-ACCESS	read-write
	STATUS	current
	DESCRIPTION
		"."
	::= { bgs10RadiusClientEntry 142 }

bgs10RadiusAccServerAddress5 OBJECT-TYPE
	SYNTAX		IpAddress
	MAX-ACCESS	read-write
	STATUS	current
	DESCRIPTION
		"."
	::= { bgs10RadiusClientEntry 143 }

bgs10RadiusAccClientServerPortNumber5 OBJECT-TYPE
	SYNTAX		Unsigned32
	MAX-ACCESS	read-write
	STATUS	current
	DESCRIPTION
		"."
	::= { bgs10RadiusClientEntry 144 }

bgs10RadiusAccClientRoundTripTime5 OBJECT-TYPE
	SYNTAX		TimeTicks
	MAX-ACCESS	read-write
	STATUS	current
	DESCRIPTION
		"."
	::= { bgs10RadiusClientEntry 145 }

bgs10RadiusAccClientRequests5 OBJECT-TYPE
	SYNTAX		Unsigned32
	MAX-ACCESS	read-write
	STATUS	current
	DESCRIPTION
		"."
	::= { bgs10RadiusClientEntry 146 }

bgs10RadiusAccClientRetransmissions5 OBJECT-TYPE
	SYNTAX		Unsigned32
	MAX-ACCESS	read-write
	STATUS	current
	DESCRIPTION
		"."
	::= { bgs10RadiusClientEntry 147 }

bgs10RadiusAccClientResponses5 OBJECT-TYPE
	SYNTAX		Unsigned32
	MAX-ACCESS	read-write
	STATUS	current
	DESCRIPTION
		"."
	::= { bgs10RadiusClientEntry 148 }

bgs10RadiusAccClientMalformedResponses5 OBJECT-TYPE
	SYNTAX		Unsigned32
	MAX-ACCESS	read-write
	STATUS	current
	DESCRIPTION
		"."
	::= { bgs10RadiusClientEntry 149 }

bgs10RadiusAccClientBadAuthenticators5 OBJECT-TYPE
	SYNTAX		Unsigned32
	MAX-ACCESS	read-write
	STATUS	current
	DESCRIPTION
		"."
	::= { bgs10RadiusClientEntry 150 }

bgs10RadiusAccClientPendingRequests5 OBJECT-TYPE
	SYNTAX		Unsigned32
	MAX-ACCESS	read-write
	STATUS	current
	DESCRIPTION
		"."
	::= { bgs10RadiusClientEntry 151 }

bgs10RadiusAccClientTimeouts5 OBJECT-TYPE
	SYNTAX		Unsigned32
	MAX-ACCESS	read-write
	STATUS	current
	DESCRIPTION
		"."
	::= { bgs10RadiusClientEntry 152 }

bgs10RadiusAccClientUnknownTypes5 OBJECT-TYPE
	SYNTAX		Unsigned32
	MAX-ACCESS	read-write
	STATUS	current
	DESCRIPTION
		"."
	::= { bgs10RadiusClientEntry 153 }

bgs10RadiusAccClientPacketsDropped5 OBJECT-TYPE
	SYNTAX		Unsigned32
	MAX-ACCESS	read-write
	STATUS	current
	DESCRIPTION
		"."
	::= { bgs10RadiusClientEntry 154 }

bgs10RadiusAccClientModule OBJECT-TYPE
	SYNTAX		UCHAR
	MAX-ACCESS	read-write
	STATUS	current
	DESCRIPTION
		"."
	::= { bgs10RadiusClientEntry 155 }

bgs10RadiusClinetIspScrtNew1 OBJECT-TYPE
	SYNTAX		OCTET STRING(SIZE(35))
	MAX-ACCESS	read-write
	STATUS	current
	DESCRIPTION
		"."
	::= { bgs10RadiusClientEntry 156 }

bgs10RadiusClinetIspScrtNew2 OBJECT-TYPE
	SYNTAX		OCTET STRING(SIZE(30))
	MAX-ACCESS	read-write
	STATUS	current
	DESCRIPTION
		"."
	::= { bgs10RadiusClientEntry 157 }

-- bgs10radIpAddr
bgs10radIpAddr OBJECT-TYPE
	SYNTAX	SEQUENCE OF BGS10radIpAddrEntry
	MAX-ACCESS	not-accessible
	STATUS	current
	DESCRIPTION
		""
	::= { zxbgs10mib 74 }

bgs10radIpAddrEntry OBJECT-TYPE
	SYNTAX	BGS10radIpAddrEntry
	MAX-ACCESS	not-accessible
	STATUS	current
	DESCRIPTION
		"."
	INDEX {
		bgs10RadiusClinetIspType
		}
	::= { bgs10radIpAddr 1 }
	
BGS10radIpAddrEntry ::=
	SEQUENCE {
		bgs10radIpAddrRowStatus			RowStatus,
		bgs10radIpAddrState				UCHAR,
		bgs10radIpAddrIpAddr			Unsigned32,
		bgs10radIpAddrIspTypeIpPoolNo	UShort
}                    
                                                     
bgs10radIpAddrRowStatus OBJECT-TYPE
	SYNTAX	RowStatus
	MAX-ACCESS	read-write
	STATUS	current
	DESCRIPTION
		"."
	::= { bgs10radIpAddrEntry 1 }

bgs10radIpAddrState OBJECT-TYPE
	SYNTAX	UCHAR
	MAX-ACCESS	read-write
	STATUS	current
	DESCRIPTION
		"."
	::= { bgs10radIpAddrEntry 2 }

bgs10radIpAddrIpAddr OBJECT-TYPE
	SYNTAX	Unsigned32
	MAX-ACCESS	read-write
	STATUS	current
	DESCRIPTION
		"."
	::= { bgs10radIpAddrEntry 3 }

bgs10radIpAddrIspTypeIpPoolNo OBJECT-TYPE
	SYNTAX	UShort
	MAX-ACCESS	read-write
	STATUS	current
	DESCRIPTION
		"."
	::= { bgs10radIpAddrEntry 4 }

-- bgs10PPPFilter
bgs10PPPFilter OBJECT-TYPE
	SYNTAX	SEQUENCE OF BGS10PPPFilterEntry
	MAX-ACCESS	not-accessible
	STATUS	current
	DESCRIPTION
		""
	::= { zxbgs10mib 75 }

bgs10PPPFilterEntry OBJECT-TYPE
	SYNTAX	BGS10PPPFilterEntry
	MAX-ACCESS	not-accessible
	STATUS	current
	DESCRIPTION
		"."
	INDEX {
		bgs10PPPFilterKeyword
		}
	::= { bgs10PPPFilter 1 }
	
BGS10PPPFilterEntry ::=
	SEQUENCE {
		bgs10PPPFilterRowStatus			RowStatus,
		bgs10PPPFilterName				OCTET STRING(SIZE(33)),
		bgs10PPPFilterKeyword			UShort,
		bgs10PPPFilterRuleNum			UShort,
		bgs10PPPFilterPass				UShort
}                    
                                                     
bgs10PPPFilterRowStatus OBJECT-TYPE
	SYNTAX	RowStatus
	MAX-ACCESS	read-write
	STATUS	current
	DESCRIPTION
		"."
	::= { bgs10PPPFilterEntry 1 }

bgs10PPPFilterName OBJECT-TYPE
	SYNTAX	OCTET STRING(SIZE(33))
	MAX-ACCESS	read-write
	STATUS	current
	DESCRIPTION
		"."
	::= { bgs10PPPFilterEntry 2 }

bgs10PPPFilterKeyword OBJECT-TYPE
	SYNTAX	UShort
	MAX-ACCESS	read-write
	STATUS	current
	DESCRIPTION
		"."
	::= { bgs10PPPFilterEntry 3 }

bgs10PPPFilterRuleNum OBJECT-TYPE
	SYNTAX	UShort
	MAX-ACCESS	read-write
	STATUS	current
	DESCRIPTION
		"."
	::= { bgs10PPPFilterEntry 4 }

bgs10PPPFilterPass OBJECT-TYPE
	SYNTAX	UShort
	MAX-ACCESS	read-write
	STATUS	current
	DESCRIPTION
		"."
	::= { bgs10PPPFilterEntry 5 }


-- bgs10FilterRule
bgs10FilterRule OBJECT-TYPE
	SYNTAX	SEQUENCE OF BGS10FilterRuleEntry
	MAX-ACCESS	not-accessible
	STATUS	current
	DESCRIPTION
		""
	::= { zxbgs10mib 76 }

bgs10FilterRuleEntry OBJECT-TYPE
	SYNTAX	BGS10FilterRuleEntry
	MAX-ACCESS	not-accessible
	STATUS	current
	DESCRIPTION
		"."
	INDEX {
		bgs10FilterRuleRuleNo
		}
	::= { bgs10FilterRule 1 }
	
BGS10FilterRuleEntry ::=
	SEQUENCE {
		bgs10FilterRuleRowStatus			RowStatus,
		bgs10FilterRuleRuleNo				UShort,
		bgs10FilterRuleForward				UShort,
		bgs10FilterRuleIPAddress			Unsigned32,
		bgs10FilterRuleIPAddressMask		Unsigned32,
		bgs10FilterRulePort					UShort,
		bgs10FilterRulePortCmp				UShort,
		bgs10FilterRuleProtocol				UShort
}                    
                                                     
bgs10FilterRuleRowStatus OBJECT-TYPE
	SYNTAX	RowStatus
	MAX-ACCESS	read-write
	STATUS	current
	DESCRIPTION
		"."
	::= { bgs10FilterRuleEntry 1 }

bgs10FilterRuleRuleNo OBJECT-TYPE
	SYNTAX	UShort
	MAX-ACCESS	read-write
	STATUS	current
	DESCRIPTION
		"."
	::= { bgs10FilterRuleEntry 2 }

bgs10FilterRuleForward OBJECT-TYPE
	SYNTAX	UShort
	MAX-ACCESS	read-write
	STATUS	current
	DESCRIPTION
		"."
	::= { bgs10FilterRuleEntry 3 }

bgs10FilterRuleIPAddress OBJECT-TYPE
	SYNTAX	Unsigned32
	MAX-ACCESS	read-write
	STATUS	current
	DESCRIPTION
		"."
	::= { bgs10FilterRuleEntry 4 }

bgs10FilterRuleIPAddressMask OBJECT-TYPE
	SYNTAX	Unsigned32
	MAX-ACCESS	read-write
	STATUS	current
	DESCRIPTION
		"."
	::= { bgs10FilterRuleEntry 5 }


bgs10FilterRulePort OBJECT-TYPE
	SYNTAX	UShort
	MAX-ACCESS	read-write
	STATUS	current
	DESCRIPTION
		"."
	::= { bgs10FilterRuleEntry 6 }

bgs10FilterRulePortCmp OBJECT-TYPE
	SYNTAX	UShort
	MAX-ACCESS	read-write
	STATUS	current
	DESCRIPTION
		"."
	::= { bgs10FilterRuleEntry 7 }

bgs10FilterRuleProtocol OBJECT-TYPE
	SYNTAX	UShort
	MAX-ACCESS	read-write
	STATUS	current
	DESCRIPTION
		"."
	::= { bgs10FilterRuleEntry 8 }

--the bgs10POS61195 table 
bgs10POS61195			OBJECT IDENTIFIER	::= { zxbgs10mib 77}

-- struct_PosICConfigTable
bgs10PosICConfig		OBJECT IDENTIFIER	::= { bgs10POS61195 1}
                                                     
bgs10PosICConfigRowStatus OBJECT-TYPE
	SYNTAX	RowStatus
	MAX-ACCESS	read-write
	STATUS	current
	DESCRIPTION
		"."
	::= { bgs10PosICConfig 1 }

bgs10PosICConfigInterfacemode OBJECT-TYPE
	SYNTAX	UCHAR
	MAX-ACCESS	read-write
	STATUS	current
	DESCRIPTION
		"."
	::= { bgs10PosICConfig 2 }

bgs10PosICConfigAUpointer OBJECT-TYPE
	SYNTAX	UCHAR
	MAX-ACCESS	read-write
	STATUS	current
	DESCRIPTION
		"."
	::= { bgs10PosICConfig 3 }

bgs10PosICConfigC2 OBJECT-TYPE
	SYNTAX	UCHAR
	MAX-ACCESS	read-write
	STATUS	current
	DESCRIPTION
		"."
	::= { bgs10PosICConfig 4 }

bgs10PosICConfigRMcfg OBJECT-TYPE
	SYNTAX	UCHAR
	MAX-ACCESS	read-write
	STATUS	current
	DESCRIPTION
		"."
	::= { bgs10PosICConfig 5 }


bgs10PosICConfigPos7EMode OBJECT-TYPE
	SYNTAX	UCHAR
	MAX-ACCESS	read-write
	STATUS	current
	DESCRIPTION
		"."
	::= { bgs10PosICConfig 6 }
	
bgs10PosICConfigCRCmode OBJECT-TYPE
	SYNTAX	UCHAR
	MAX-ACCESS	read-write
	STATUS	current
	DESCRIPTION
		"."
	::= { bgs10PosICConfig 7 }

bgs10PosICConfigHeaderLocation OBJECT-TYPE
	SYNTAX	UCHAR
	MAX-ACCESS	read-write
	STATUS	current
	DESCRIPTION
		"."
	::= { bgs10PosICConfig 8 }

bgs10PosICConfigMinlen OBJECT-TYPE
	SYNTAX	UShort
	MAX-ACCESS	read-write
	STATUS	current
	DESCRIPTION
		"."
	::= { bgs10PosICConfig 9 }

bgs10PosICConfigMinlenMaxlen OBJECT-TYPE
	SYNTAX	UShort
	MAX-ACCESS	read-write
	STATUS	current
	DESCRIPTION
		"."
	::= { bgs10PosICConfig 10 }

bgs10PosICConfigPrintNum OBJECT-TYPE
	SYNTAX	UShort
	MAX-ACCESS	read-write
	STATUS	current
	DESCRIPTION
		"."
	::= { bgs10PosICConfig 11 }
	
bgs10PosICConfigModule OBJECT-TYPE
	SYNTAX	UCHAR
	MAX-ACCESS	read-write
	STATUS	current
	DESCRIPTION
		"."
	::= { bgs10PosICConfig 12 }

--the struct_PosRoutConf table 
bgs10PosRoutConf		OBJECT IDENTIFIER	::= { bgs10POS61195 2}
                                                     
bgs10PosRoutConfRowStatus OBJECT-TYPE
	SYNTAX	RowStatus
	MAX-ACCESS	read-write
	STATUS	current
	DESCRIPTION
		"."
	::= { bgs10PosRoutConf 1 }

bgs10PosRoutConfModeType OBJECT-TYPE
	SYNTAX	UCHAR
	MAX-ACCESS	read-write
	STATUS	current
	DESCRIPTION
		"."
	::= { bgs10PosRoutConf 2 }

bgs10PosRoutConfForward OBJECT-TYPE
	SYNTAX	UCHAR
	MAX-ACCESS	read-write
	STATUS	current
	DESCRIPTION
		"."
	::= { bgs10PosRoutConf 3 }

bgs10PosRoutConfMailPort1 OBJECT-TYPE
	SYNTAX	OCTET STRING(SIZE(20))
	MAX-ACCESS	read-write
	STATUS	current
	DESCRIPTION
		"."
	::= { bgs10PosRoutConf 4 }

bgs10PosRoutConfMailPort2 OBJECT-TYPE
	SYNTAX	OCTET STRING(SIZE(20))
	MAX-ACCESS	read-write
	STATUS	current
	DESCRIPTION
		"."
	::= { bgs10PosRoutConf 5 }


bgs10PosRoutConfHttpPort1 OBJECT-TYPE
	SYNTAX	OCTET STRING(SIZE(20))
	MAX-ACCESS	read-write
	STATUS	current
	DESCRIPTION
		"."
	::= { bgs10PosRoutConf 6 }

bgs10PosRoutConfHttpPort2 OBJECT-TYPE
	SYNTAX	OCTET STRING(SIZE(20))
	MAX-ACCESS	read-write
	STATUS	current
	DESCRIPTION
		"."
	::= { bgs10PosRoutConf 7 }


bgs10PosRoutConfSrcMac1 OBJECT-TYPE
	SYNTAX	OCTET STRING(SIZE(6))
	MAX-ACCESS	read-write
	STATUS	current
	DESCRIPTION
		"."
	::= { bgs10PosRoutConf 8 }

bgs10PosRoutConfSrcMac2 OBJECT-TYPE
	SYNTAX	OCTET STRING(SIZE(6))
	MAX-ACCESS	read-write
	STATUS	current
	DESCRIPTION
		"."
	::= { bgs10PosRoutConf 9 }

bgs10PosRoutConfSrcMac3 OBJECT-TYPE
	SYNTAX	OCTET STRING(SIZE(6))
	MAX-ACCESS	read-write
	STATUS	current
	DESCRIPTION
		"."
	::= { bgs10PosRoutConf 10 }

bgs10PosRoutConfSrcMac4 OBJECT-TYPE
	SYNTAX	OCTET STRING(SIZE(6))
	MAX-ACCESS	read-write
	STATUS	current
	DESCRIPTION
		"."
	::= { bgs10PosRoutConf 11 }

bgs10PosRoutConfSrcMac5 OBJECT-TYPE
	SYNTAX	OCTET STRING(SIZE(6))
	MAX-ACCESS	read-write
	STATUS	current
	DESCRIPTION
		"."
	::= { bgs10PosRoutConf 12 }

bgs10PosRoutConfSrcMac6 OBJECT-TYPE
	SYNTAX	OCTET STRING(SIZE(6))
	MAX-ACCESS	read-write
	STATUS	current
	DESCRIPTION
		"."
	::= { bgs10PosRoutConf 13 }

bgs10PosRoutConfSrcMac7 OBJECT-TYPE
	SYNTAX	OCTET STRING(SIZE(6))
	MAX-ACCESS	read-write
	STATUS	current
	DESCRIPTION
		"."
	::= { bgs10PosRoutConf 14 }



bgs10PosRoutConfSrcMac8 OBJECT-TYPE
	SYNTAX	OCTET STRING(SIZE(6))
	MAX-ACCESS	read-write
	STATUS	current
	DESCRIPTION
		"."
	::= { bgs10PosRoutConf 15 }

bgs10PosRoutConfDstMac1 OBJECT-TYPE
	SYNTAX	OCTET STRING(SIZE(6))
	MAX-ACCESS	read-write
	STATUS	current
	DESCRIPTION
		"."
	::= { bgs10PosRoutConf 16 }

bgs10PosRoutConfDstMac2 OBJECT-TYPE
	SYNTAX	OCTET STRING(SIZE(6))
	MAX-ACCESS	read-write
	STATUS	current
	DESCRIPTION
		"."
	::= { bgs10PosRoutConf 17 }

bgs10PosRoutConfDstMac3 OBJECT-TYPE
	SYNTAX	OCTET STRING(SIZE(6))
	MAX-ACCESS	read-write
	STATUS	current
	DESCRIPTION
		"."
	::= { bgs10PosRoutConf 18 }

bgs10PosRoutConfDstMac4 OBJECT-TYPE
	SYNTAX	OCTET STRING(SIZE(6))
	MAX-ACCESS	read-write
	STATUS	current
	DESCRIPTION
		"."
	::= { bgs10PosRoutConf 19 }

bgs10PosRoutConfDstMac5 OBJECT-TYPE
	SYNTAX	OCTET STRING(SIZE(6))
	MAX-ACCESS	read-write
	STATUS	current
	DESCRIPTION
		"."
	::= { bgs10PosRoutConf 20 }

bgs10PosRoutConfDstMac6 OBJECT-TYPE
	SYNTAX	OCTET STRING(SIZE(6))
	MAX-ACCESS	read-write
	STATUS	current
	DESCRIPTION
		"."
	::= { bgs10PosRoutConf 21 }

bgs10PosRoutConfDstMac7 OBJECT-TYPE
	SYNTAX	OCTET STRING(SIZE(6))
	MAX-ACCESS	read-write
	STATUS	current
	DESCRIPTION
		"."
	::= { bgs10PosRoutConf 22 }

bgs10PosRoutConfDstMac8 OBJECT-TYPE
	SYNTAX	OCTET STRING(SIZE(6))
	MAX-ACCESS	read-write
	STATUS	current
	DESCRIPTION
		"."
	::= { bgs10PosRoutConf 23 }

bgs10PosRoutConfModule OBJECT-TYPE
	SYNTAX	UCHAR
	MAX-ACCESS	read-write
	STATUS	current
	DESCRIPTION
		"."
	::= { bgs10PosRoutConf 24 }
	
-- bgs10PMPTable
bgs10PMPTable OBJECT-TYPE
	SYNTAX	SEQUENCE OF BGS10PMPTableEntry
	MAX-ACCESS	not-accessible
	STATUS	current
	DESCRIPTION
		""
	::= { zxbgs10mib 78 }

bgs10PMPTableEntry OBJECT-TYPE
	SYNTAX	BGS10PMPTableEntry
	MAX-ACCESS	not-accessible
	STATUS	current
	DESCRIPTION
		"."
	INDEX {
		bgs10PMPTableLModule,
		bgs10PMPTableLPort,
		bgs10PMPTableLVPI, 
		bgs10PMPTableLVCI,	
		bgs10PMPTableWMODULE,
		bgs10PMPTableWPORT,
		bgs10PMPTableWVPI, 
		bgs10PMPTableWVCI	
	}                    
	::= { bgs10PMPTable 1 }  
	                         
BGS10PMPTableEntry ::=
	SEQUENCE {
		bgs10PMPTableRowStatus				RowStatus,
		bgs10PMPTableLModule				UCHAR,
		bgs10PMPTableLPort					UCHAR,		
		bgs10PMPTableLVPI     				UShort,		
		bgs10PMPTableLVCI	  		        UShort, 		
		bgs10PMPTableLCPType  		        UCHAR,
		bgs10PMPTableLATMAddress 	        AtmAddr,
		bgs10PMPTableWMODULE  		        UCHAR,
		bgs10PMPTableWPORT    		        UCHAR,		
		bgs10PMPTableWVPI     		        UShort,		
		bgs10PMPTableWVCI	  		        UShort,		
		bgs10PMPTableWCPType  		        UCHAR,	
		bgs10PMPTableWConnTag 		        UShort,		
		bgs10PMPTableWCCID	  		        UShort,	
		bgs10PMPTableWATMAddress 	        AtmAddr,
		bgs10PMPTablePMODULE  	            UCHAR,
		bgs10PMPTablePPORT    		        UCHAR,		
		bgs10PMPTablePVPI     		        UShort,		
		bgs10PMPTablePVCI	  		        UShort,		
		bgs10PMPTablePCPType  		        UCHAR,	
		bgs10PMPTablePConnTag 		        UShort,		
		bgs10PMPTablePCCID    		        UShort,	
		bgs10PMPTablePATMAddress 	        AtmAddr,
		bgs10PMPTableW2LtrafficDescrType	UCHAR,
  		bgs10PMPTableW2LtrafficDescrParam1	Unsigned32,		
  		bgs10PMPTableW2LtrafficDescrParam2	Unsigned32,    	
  		bgs10PMPTableW2LtrafficDescrParam3	Unsigned32,    	
  		bgs10PMPTableW2LtrafficDescrParam4	Unsigned32,    	
  		bgs10PMPTableW2LtrafficDescrParam5	Unsigned32,    	
  		bgs10PMPTableW2LtrafficQosClass		UCHAR,    	    	                                    	        
  		bgs10PMPTableL2WtrafficDescrType	UCHAR,    	
  		bgs10PMPTableL2WtrafficDescrParam1	Unsigned32,		
  		bgs10PMPTableL2WtrafficDescrParam2	Unsigned32,    	
  		bgs10PMPTableL2WtrafficDescrParam3	Unsigned32,    	
  		bgs10PMPTableL2WtrafficDescrParam4	Unsigned32,    	
  		bgs10PMPTableL2WtrafficDescrParam5	Unsigned32,    	
  		bgs10PMPTableL2WtrafficQosClass		UCHAR,    			                                    	        
		bgs10PMPTableCatchRM  			    UCHAR,		
		bgs10PMPTableAllowEFC 			    UCHAR,	 	
		bgs10PMPTableEPDFlag				UCHAR,	 	
		bgs10PMPTableFeeGleanFlag 		    UCHAR,	 	
		bgs10PMPTablePolicing     		    UCHAR,	 			                                            
		bgs10PMPTablePacketType  		    UCHAR,	 	
		bgs10PMPTableFCSInd				    UCHAR,	 	
		bgs10PMPTableSpecialIndex 		    UShort,  	    	                                            
		bgs10PMPTableuse 				    UCHAR,	
		bgs10PMPTableConnectType  		    UCHAR,		
		bgs10PMPTableConnectStruct 	        UCHAR,		
		bgs10PMPTableServiceCategory		UCHAR,		
		bgs10PMPTablePVCType	 			UCHAR,		    	                                            
		bgs10PMPTableWOperStatus		    UCHAR,		
		bgs10PMPTablePOperStatus		    UCHAR,				                                            
		bgs10PMPTableManualControl 		    UCHAR,		
		bgs10PMPTablePSwitchType   		    UCHAR,		
		bgs10PMPTableOperatingMode 		    UCHAR,				                                            
		bgs10PMPTableGroupId 			    UShort,
		bgs10PMPTableAlarmStatus            UCHAR   	
}                    
                                                     
bgs10PMPTableRowStatus OBJECT-TYPE
	SYNTAX	RowStatus
	MAX-ACCESS	read-write
	STATUS	current
	DESCRIPTION
		"."
	::= { bgs10PMPTableEntry 1 }

bgs10PMPTableLModule OBJECT-TYPE
	SYNTAX	UCHAR
	MAX-ACCESS	read-write
	STATUS	current
	DESCRIPTION
		"."
	::= { bgs10PMPTableEntry 2 }

bgs10PMPTableLPort OBJECT-TYPE
	SYNTAX	UCHAR
	MAX-ACCESS	read-write
	STATUS	current
	DESCRIPTION
		"."
	::= { bgs10PMPTableEntry 3 }

bgs10PMPTableLVPI OBJECT-TYPE
	SYNTAX	UShort
	MAX-ACCESS	read-write
	STATUS	current
	DESCRIPTION
		"."
	::= { bgs10PMPTableEntry 4 }

bgs10PMPTableLVCI OBJECT-TYPE
	SYNTAX	UShort
	MAX-ACCESS	read-write
	STATUS	current
	DESCRIPTION
		"."
	::= { bgs10PMPTableEntry 5 }

bgs10PMPTableLCPType OBJECT-TYPE
	SYNTAX	UCHAR
	MAX-ACCESS	read-write
	STATUS	current
	DESCRIPTION
		"."
	::= { bgs10PMPTableEntry 6 }

bgs10PMPTableLATMAddress OBJECT-TYPE
	SYNTAX	AtmAddr
	MAX-ACCESS	read-write
	STATUS	current
	DESCRIPTION
		"."
	::= { bgs10PMPTableEntry 7 }

bgs10PMPTableWMODULE OBJECT-TYPE
	SYNTAX	UCHAR
	MAX-ACCESS	read-write
	STATUS	current
	DESCRIPTION
		"."
	::= { bgs10PMPTableEntry 8 }

bgs10PMPTableWPORT OBJECT-TYPE
	SYNTAX	UCHAR
	MAX-ACCESS	read-write
	STATUS	current
	DESCRIPTION
		"."
	::= { bgs10PMPTableEntry 9 }

bgs10PMPTableWVPI OBJECT-TYPE
	SYNTAX	UShort
	MAX-ACCESS	read-write
	STATUS	current
	DESCRIPTION
		"."
	::= { bgs10PMPTableEntry 10 }

bgs10PMPTableWVCI OBJECT-TYPE
	SYNTAX	UShort
	MAX-ACCESS	read-write
	STATUS	current
	DESCRIPTION
		"."
	::= { bgs10PMPTableEntry 11 }

bgs10PMPTableWCPType OBJECT-TYPE
	SYNTAX	UCHAR
	MAX-ACCESS	read-write
	STATUS	current
	DESCRIPTION
		"."
	::= { bgs10PMPTableEntry 12 }

bgs10PMPTableWConnTag OBJECT-TYPE
	SYNTAX	UShort
	MAX-ACCESS	read-write
	STATUS	current
	DESCRIPTION
		"."
	::= { bgs10PMPTableEntry 13 }

bgs10PMPTableWCCID OBJECT-TYPE
	SYNTAX	UShort
	MAX-ACCESS	read-write
	STATUS	current
	DESCRIPTION
		"."
	::= { bgs10PMPTableEntry 14 }

bgs10PMPTableWATMAddress OBJECT-TYPE
	SYNTAX	AtmAddr
	MAX-ACCESS	read-write
	STATUS	current
	DESCRIPTION
		"."
	::= { bgs10PMPTableEntry 15 }

bgs10PMPTablePMODULE OBJECT-TYPE
	SYNTAX	UCHAR
	MAX-ACCESS	read-write
	STATUS	current
	DESCRIPTION
		"."
	::= { bgs10PMPTableEntry 16 }

bgs10PMPTablePPORT OBJECT-TYPE
	SYNTAX	UCHAR
	MAX-ACCESS	read-write
	STATUS	current
	DESCRIPTION
		"."
	::= { bgs10PMPTableEntry 17 }

bgs10PMPTablePVPI OBJECT-TYPE
	SYNTAX	UShort
	MAX-ACCESS	read-write
	STATUS	current
	DESCRIPTION
		"."
	::= { bgs10PMPTableEntry 18 }

bgs10PMPTablePVCI OBJECT-TYPE
	SYNTAX	UShort
	MAX-ACCESS	read-write
	STATUS	current
	DESCRIPTION
		"."
	::= { bgs10PMPTableEntry 19 }

bgs10PMPTablePCPType OBJECT-TYPE
	SYNTAX	UCHAR
	MAX-ACCESS	read-write
	STATUS	current
	DESCRIPTION
		"."
	::= { bgs10PMPTableEntry 20 }

bgs10PMPTablePConnTag OBJECT-TYPE
	SYNTAX	UShort
	MAX-ACCESS	read-write
	STATUS	current
	DESCRIPTION
		"."
	::= { bgs10PMPTableEntry 21 }

bgs10PMPTablePCCID OBJECT-TYPE
	SYNTAX	UShort
	MAX-ACCESS	read-write
	STATUS	current
	DESCRIPTION
		"."
	::= { bgs10PMPTableEntry 22 }

bgs10PMPTablePATMAddress OBJECT-TYPE
	SYNTAX	AtmAddr
	MAX-ACCESS	read-write
	STATUS	current
	DESCRIPTION
		"."
	::= { bgs10PMPTableEntry 23 }

bgs10PMPTableW2LtrafficDescrType OBJECT-TYPE
	SYNTAX	UCHAR
	MAX-ACCESS	read-write
	STATUS	current
	DESCRIPTION
		"."
	::= { bgs10PMPTableEntry 24 }

bgs10PMPTableW2LtrafficDescrParam1 OBJECT-TYPE
	SYNTAX	Unsigned32
	MAX-ACCESS	read-write
	STATUS	current
	DESCRIPTION
		"."
	::= { bgs10PMPTableEntry 25 }

bgs10PMPTableW2LtrafficDescrParam2 OBJECT-TYPE
	SYNTAX	Unsigned32
	MAX-ACCESS	read-write
	STATUS	current
	DESCRIPTION
		"."
	::= { bgs10PMPTableEntry 26 }

bgs10PMPTableW2LtrafficDescrParam3 OBJECT-TYPE
	SYNTAX	Unsigned32
	MAX-ACCESS	read-write
	STATUS	current
	DESCRIPTION
		"."
	::= { bgs10PMPTableEntry 27 }

bgs10PMPTableW2LtrafficDescrParam4 OBJECT-TYPE
	SYNTAX	Unsigned32
	MAX-ACCESS	read-write
	STATUS	current
	DESCRIPTION
		"."
	::= { bgs10PMPTableEntry 28 }

bgs10PMPTableW2LtrafficDescrParam5 OBJECT-TYPE
	SYNTAX	Unsigned32
	MAX-ACCESS	read-write
	STATUS	current
	DESCRIPTION
		"."
	::= { bgs10PMPTableEntry 29 }

bgs10PMPTableW2LtrafficQosClass OBJECT-TYPE
	SYNTAX	UCHAR
	MAX-ACCESS	read-write
	STATUS	current
	DESCRIPTION
		"."
	::= { bgs10PMPTableEntry 30 }

bgs10PMPTableL2WtrafficDescrType OBJECT-TYPE
	SYNTAX	UCHAR
	MAX-ACCESS	read-write
	STATUS	current
	DESCRIPTION
		"."
	::= { bgs10PMPTableEntry 31 }

bgs10PMPTableL2WtrafficDescrParam1 OBJECT-TYPE
	SYNTAX	Unsigned32
	MAX-ACCESS	read-write
	STATUS	current
	DESCRIPTION
		"."
	::= { bgs10PMPTableEntry 32 }

bgs10PMPTableL2WtrafficDescrParam2 OBJECT-TYPE
	SYNTAX	Unsigned32
	MAX-ACCESS	read-write
	STATUS	current
	DESCRIPTION
		"."
	::= { bgs10PMPTableEntry 33 }

bgs10PMPTableL2WtrafficDescrParam3 OBJECT-TYPE
	SYNTAX	Unsigned32
	MAX-ACCESS	read-write
	STATUS	current
	DESCRIPTION
		"."
	::= { bgs10PMPTableEntry 34 }

bgs10PMPTableL2WtrafficDescrParam4 OBJECT-TYPE
	SYNTAX	Unsigned32
	MAX-ACCESS	read-write
	STATUS	current
	DESCRIPTION
		"."
	::= { bgs10PMPTableEntry 35 }

bgs10PMPTableL2WtrafficDescrParam5 OBJECT-TYPE
	SYNTAX	Unsigned32
	MAX-ACCESS	read-write
	STATUS	current
	DESCRIPTION
		"."
	::= { bgs10PMPTableEntry 36 }

bgs10PMPTableL2WtrafficQosClass OBJECT-TYPE
	SYNTAX	UCHAR
	MAX-ACCESS	read-write
	STATUS	current
	DESCRIPTION
		"."
	::= { bgs10PMPTableEntry 37 }

bgs10PMPTableCatchRM OBJECT-TYPE
	SYNTAX	UCHAR
	MAX-ACCESS	read-write
	STATUS	current
	DESCRIPTION
		"."
	::= { bgs10PMPTableEntry 38 }

bgs10PMPTableAllowEFC OBJECT-TYPE
	SYNTAX	UCHAR
	MAX-ACCESS	read-write
	STATUS	current
	DESCRIPTION
		"."
	::= { bgs10PMPTableEntry 39 }

bgs10PMPTableEPDFlag OBJECT-TYPE
	SYNTAX	UCHAR
	MAX-ACCESS	read-write
	STATUS	current
	DESCRIPTION
		"."
	::= { bgs10PMPTableEntry 40 }

bgs10PMPTableFeeGleanFlag OBJECT-TYPE
	SYNTAX	UCHAR
	MAX-ACCESS	read-write
	STATUS	current
	DESCRIPTION
		"."
	::= { bgs10PMPTableEntry 41 }

bgs10PMPTablePolicing OBJECT-TYPE
	SYNTAX	UCHAR
	MAX-ACCESS	read-write
	STATUS	current
	DESCRIPTION
		"."
	::= { bgs10PMPTableEntry 42 }

bgs10PMPTablePacketType OBJECT-TYPE
	SYNTAX	UCHAR
	MAX-ACCESS	read-write
	STATUS	current
	DESCRIPTION
		"."
	::= { bgs10PMPTableEntry 43 }

bgs10PMPTableFCSInd OBJECT-TYPE
	SYNTAX	UCHAR
	MAX-ACCESS	read-write
	STATUS	current
	DESCRIPTION
		"."
	::= { bgs10PMPTableEntry 44 }

bgs10PMPTableSpecialIndex OBJECT-TYPE
	SYNTAX	UShort
	MAX-ACCESS	read-write
	STATUS	current
	DESCRIPTION
		"."
	::= { bgs10PMPTableEntry 45 }

bgs10PMPTableuse OBJECT-TYPE
	SYNTAX	UCHAR
	MAX-ACCESS	read-write
	STATUS	current
	DESCRIPTION
		"."
	::= { bgs10PMPTableEntry 46 }

bgs10PMPTableConnectType OBJECT-TYPE
	SYNTAX	UCHAR
	MAX-ACCESS	read-write
	STATUS	current
	DESCRIPTION
		"."
	::= { bgs10PMPTableEntry 47 }

bgs10PMPTableConnectStruct OBJECT-TYPE
	SYNTAX	UCHAR
	MAX-ACCESS	read-write
	STATUS	current
	DESCRIPTION
		"."
	::= { bgs10PMPTableEntry 48 }

bgs10PMPTableServiceCategory OBJECT-TYPE
	SYNTAX	UCHAR
	MAX-ACCESS	read-write
	STATUS	current
	DESCRIPTION
		"."
	::= { bgs10PMPTableEntry 49 }

bgs10PMPTablePVCType OBJECT-TYPE
	SYNTAX	UCHAR
	MAX-ACCESS	read-write
	STATUS	current
	DESCRIPTION
		"."
	::= { bgs10PMPTableEntry 50 }

bgs10PMPTableWOperStatus OBJECT-TYPE
	SYNTAX	UCHAR
	MAX-ACCESS	read-write
	STATUS	current
	DESCRIPTION
		"."
	::= { bgs10PMPTableEntry 51 }

bgs10PMPTablePOperStatus OBJECT-TYPE
	SYNTAX	UCHAR
	MAX-ACCESS	read-write
	STATUS	current
	DESCRIPTION
		"."
	::= { bgs10PMPTableEntry 52 }

bgs10PMPTableManualControl OBJECT-TYPE
	SYNTAX	UCHAR
	MAX-ACCESS	read-write
	STATUS	current
	DESCRIPTION
		"."
	::= { bgs10PMPTableEntry 53 }

bgs10PMPTablePSwitchType OBJECT-TYPE
	SYNTAX	UCHAR
	MAX-ACCESS	read-write
	STATUS	current
	DESCRIPTION
		"."
	::= { bgs10PMPTableEntry 54 }

bgs10PMPTableOperatingMode OBJECT-TYPE
	SYNTAX	UCHAR
	MAX-ACCESS	read-write
	STATUS	current
	DESCRIPTION
		"."
	::= { bgs10PMPTableEntry 55 }

bgs10PMPTableGroupId OBJECT-TYPE
	SYNTAX	UShort
	MAX-ACCESS	read-write
	STATUS	current
	DESCRIPTION
		"."
	::= { bgs10PMPTableEntry 56 }

bgs10PMPTableAlarmStatus OBJECT-TYPE
	SYNTAX	UCHAR
	MAX-ACCESS	read-write
	STATUS	current
	DESCRIPTION
		"."
	::= { bgs10PMPTableEntry 57 }


--The Traps for ZXB10 and its successors.
	  
--The phyical Hardware Unit Alarm
				
--The Alarms of the power Board of 25-G and 5-G ATM switchers quotes
--ATM FORUM af-nm-0095.001:'atmM4HwFanFailAlarm'(atmfM4MIBTrapPrefix.41)
		
--The Alarm of power voltage (+5,-48)of 25-G and 5-G ATM switchers
--referenced ATM FORUM af-nm-0095.001:'atmfM4HwPowerAlarm'(
--atmfM4MIBTrapPrefix.25).the folowing are the supplyment to it.

zxbgs10PowerBoardTrap		OBJECT IDENTIFIER	::= { zxbgs10Traps 1 }
zxbgs10PowerBoardTrapPrefix	OBJECT IDENTIFIER	::= { zxbgs10PowerBoardTrap 0 }
	
bgs10PowerChannel1V5Alarm	NOTIFICATION-TYPE
	OBJECTS	{	atmfM4PlugInUnitOperStatus,
				atmfM4TrapAlarmSeverity
			}
	STATUS	current
	DESCRIPTION
		"indicates the Alarm of +5 power at Channel No.1."
	::= { zxbgs10PowerBoardTrapPrefix 1 }

bgs10PowerChannel1V3Alarm NOTIFICATION-TYPE
	OBJECTS	{	atmfM4PlugInUnitOperStatus,
				atmfM4TrapAlarmSeverity
			}
	STATUS	current
	DESCRIPTION
		"indicaes the Alarm of V3.3 power at Channel No.1."
	::= { zxbgs10PowerBoardTrapPrefix 2 }
	
bgs10PowerChannel2V5Alarm	NOTIFICATION-TYPE
	OBJECTS	{	atmfM4PlugInUnitOperStatus,
				atmfM4TrapAlarmSeverity
			}
	STATUS	current
	DESCRIPTION
		"indicates the Alarm of +5 power at Channel No.2."
	::= { zxbgs10PowerBoardTrapPrefix 3 }

bgs10PowerChannel2V3Alarm NOTIFICATION-TYPE
	OBJECTS	{	atmfM4PlugInUnitOperStatus,
				atmfM4TrapAlarmSeverity
			}
	STATUS	current
	DESCRIPTION
		"indicaes the Alarm of V3.3 power at Channel No.2."
	::= { zxbgs10PowerBoardTrapPrefix 4 }
	
bgs10PowerChannel3V5Alarm	NOTIFICATION-TYPE
	OBJECTS	{	atmfM4PlugInUnitOperStatus,
				atmfM4TrapAlarmSeverity
			}
	STATUS	current
	DESCRIPTION
		"indicates the Alarm of +5 power at Channel No.3."
	::= { zxbgs10PowerBoardTrapPrefix 5 }

bgs10PowerChannel3V3Alarm NOTIFICATION-TYPE
	OBJECTS	{	atmfM4PlugInUnitOperStatus,
				atmfM4TrapAlarmSeverity
			}
	STATUS	current
	DESCRIPTION
		"indicaes the Alarm of V3.3 power at Channel No.3."
	::= { zxbgs10PowerBoardTrapPrefix 6 }
	
bgs10PowerChannel4V5Alarm	NOTIFICATION-TYPE
	OBJECTS	{	atmfM4PlugInUnitOperStatus,
				atmfM4TrapAlarmSeverity
			}
	STATUS	current
	DESCRIPTION
		"indicates the Alarm of +5 power at Channel No.4."
	::= { zxbgs10PowerBoardTrapPrefix 7 }

bgs10PowerChannel4V3Alarm NOTIFICATION-TYPE
	OBJECTS	{	atmfM4PlugInUnitOperStatus,
				atmfM4TrapAlarmSeverity
			}
	STATUS	current
	DESCRIPTION
		"indicaes the Alarm of V3.3 power at Channel No.4."
	::= { zxbgs10PowerBoardTrapPrefix 8 }
	
bgs10PowerChannel1OfflineAlarm NOTIFICATION-TYPE
	OBJECTS	{	atmfM4PlugInUnitOperStatus,
				atmfM4TrapAlarmSeverity
			}
	STATUS	current
	DESCRIPTION
		"indicaes the off-line Alarm of Channel No.1."
	::= { zxbgs10PowerBoardTrapPrefix 9 }
		
bgs10PowerChannel2OfflineAlarm NOTIFICATION-TYPE
	OBJECTS	{	atmfM4PlugInUnitOperStatus,
				atmfM4TrapAlarmSeverity
			}
	STATUS	current
	DESCRIPTION
		"indicaes the off-line Alarm of Channel No.2."
	::= { zxbgs10PowerBoardTrapPrefix 10 }
	
bgs10PowerChannel3OfflineAlarm NOTIFICATION-TYPE
	OBJECTS	{	atmfM4PlugInUnitOperStatus,
				atmfM4TrapAlarmSeverity
			}
	STATUS	current
	DESCRIPTION
		"indicaes the off-line Alarm of Channel No.3."
	::= { zxbgs10PowerBoardTrapPrefix 11 }
	
bgs10PowerChannel4OfflineAlarm NOTIFICATION-TYPE
	OBJECTS	{	atmfM4PlugInUnitOperStatus,
				atmfM4TrapAlarmSeverity
			}
	STATUS	current
	DESCRIPTION
		"indicaes the off-line Alarm of Channel No.4."
	::= { zxbgs10PowerBoardTrapPrefix 12 }
	
--The Alarm of Clock board references ATM FORUM af-nm-0095.001:
--atmfM4HwTimingProbAlarm .and the following  is that ZXB10 system 
--supplies the Alarm to it.

bgs10ClkBoardTrap		OBJECT IDENTIFIER	::= { zxbgs10Traps 2 }
bgs10ClkBoardTrapPrefix	OBJECT IDENTIFIER	::= { bgs10ClkBoardTrap 0}

bgs10ClkChannel1BenchAlarm NOTIFICATION-TYPE
	OBJECTS	{	entPhysicalContainedIn,
				entPhysicalParentRelPos,
				entPhysicalClass,
				atmfM4TrapAlarmSeverity
			}
	STATUS	current
	DESCRIPTION
		"Indicates the Alarm of clock board's Channel No.1."
	::= { bgs10ClkBoardTrapPrefix 1 } 

bgs10ClkChannel2BenchAlarm NOTIFICATION-TYPE
	OBJECTS	{	entPhysicalContainedIn,
				entPhysicalParentRelPos,
				entPhysicalClass,
				atmfM4TrapAlarmSeverity
			}
	STATUS	current
	DESCRIPTION
		"Indicates the Alarm of clock board's Channel No.2."
	::= { bgs10ClkBoardTrapPrefix 2 } 
	
bgs10ClkChannel3BenchAlarm NOTIFICATION-TYPE
	OBJECTS	{	entPhysicalContainedIn,
				entPhysicalParentRelPos,
				entPhysicalClass,
				atmfM4TrapAlarmSeverity
			}
	STATUS	current
	DESCRIPTION
		"Indicates the Alarm of clock board's Channel No.3."
	::= { bgs10ClkBoardTrapPrefix 3 } 
	
bgs10ClkChannel4BenchAlarm NOTIFICATION-TYPE
	OBJECTS	{	entPhysicalContainedIn,
				entPhysicalParentRelPos,
				entPhysicalClass,
				atmfM4TrapAlarmSeverity
			}
	STATUS	current
	DESCRIPTION
		"Indicates the Alarm of clock board's Channel No.4."
	::= { bgs10ClkBoardTrapPrefix 4 } 
	
bgs10ClkChannel5BenchAlarm NOTIFICATION-TYPE
	OBJECTS	{	entPhysicalContainedIn,
				entPhysicalParentRelPos,
				entPhysicalClass,
				atmfM4TrapAlarmSeverity
			}
	STATUS	current
	DESCRIPTION
		"Indicates the Alarm of clock board's Channel No.5."
	::= {	bgs10ClkBoardTrapPrefix 5 } 
	
bgs10ClkChannel6BenchAlarm NOTIFICATION-TYPE
	OBJECTS	{	entPhysicalContainedIn,
				entPhysicalParentRelPos,
				entPhysicalClass,
				atmfM4TrapAlarmSeverity
			}
	STATUS	current
	DESCRIPTION
		"Indicates the Alarm of clock board's Channel No.6."
	::= { bgs10ClkBoardTrapPrefix 6 }
	
bgs10ClkCrystalStopAlarm	NOTIFICATION-TYPE
	OBJECTS	{	entPhysicalContainedIn,
				entPhysicalParentRelPos,
				entPhysicalClass,
				atmfM4TrapAlarmSeverity
			}
	STATUS	current
	DESCRIPTION
		"Indicates that the crystal stop working."
	::= { bgs10ClkBoardTrapPrefix 7 }
	
bgs10ClkRamBadAlarm	NOTIFICATION-TYPE
	OBJECTS	{	entPhysicalContainedIn,
				entPhysicalParentRelPos,
				entPhysicalClass,
				atmfM4TrapAlarmSeverity
			}
	STATUS	current
	DESCRIPTION
		"Indicates that the ram is bad 
		worse."
	::= { bgs10ClkBoardTrapPrefix 8 }
	
bgs10ClkChannel1BenchOfflineAlarm	NOTIFICATION-TYPE
	OBJECTS	{	entPhysicalContainedIn,
				entPhysicalParentRelPos,
				entPhysicalClass,
				atmfM4TrapAlarmSeverity
			}
	STATUS	current
	DESCRIPTION
		"Indicates that the bench No.1 of clock board is off-line."
	::= {	bgs10ClkBoardTrapPrefix 9 } 
	
bgs10ClkChannel2BenchOfflineAlarm	NOTIFICATION-TYPE
	OBJECTS	{	entPhysicalContainedIn,
				entPhysicalParentRelPos,
				entPhysicalClass,
				atmfM4TrapAlarmSeverity
			}
	STATUS	current
	DESCRIPTION
		"Indicates that the bench No.2 of clock board is off-line."
	::= { bgs10ClkBoardTrapPrefix 10 }
	
bgs10ClkChannel3BenchOfflineAlarm	NOTIFICATION-TYPE
	OBJECTS	{	entPhysicalContainedIn,
				entPhysicalParentRelPos,
				entPhysicalClass,
				atmfM4TrapAlarmSeverity
			}
	STATUS	current
	DESCRIPTION
		"Indicates that the bench No.3 of clock board is off-line."
	::= { bgs10ClkBoardTrapPrefix 11 }
	
bgs10ClkChannel4BenchOfflineAlarm	NOTIFICATION-TYPE
	OBJECTS	{	entPhysicalContainedIn,
				entPhysicalParentRelPos,
				entPhysicalClass,
				atmfM4TrapAlarmSeverity
			}
	STATUS	current
	DESCRIPTION
		"Indicates that the bench No.4 of clock board is off-line."
	::= { bgs10ClkBoardTrapPrefix 12 }

bgs10ClkChannel5BenchOfflineAlarm	NOTIFICATION-TYPE
	OBJECTS	{	entPhysicalContainedIn,
				entPhysicalParentRelPos,
				entPhysicalClass,
				atmfM4TrapAlarmSeverity
			}
	STATUS	current
	DESCRIPTION
		"Indicates that the bench No.5 of clock board is off-line."
	::= {	bgs10ClkBoardTrapPrefix 13 } 
	
bgs10ClkChannel6BenchOfflineAlarm	NOTIFICATION-TYPE
	OBJECTS	{	entPhysicalContainedIn,
				entPhysicalParentRelPos,
				entPhysicalClass,
				atmfM4TrapAlarmSeverity
			}
	STATUS	current
	DESCRIPTION
		"Indicates that the bench No.6 of clock board is off-line."
	::= { bgs10ClkBoardTrapPrefix 14 }
	
bgs10ClkBoardOnLineStatus	NOTIFICATION-TYPE
	OBJECTS { 	bgs10PlugInUnitCardType,
				atmfM4PlugInUnitAvailStatus,
				bgs10PlugInUnitMasterStatus
			}
	STATUS	current
	DESCRIPTION
		"the Clock Card stats's notification ."
	::= { bgs10ClkBoardTrapPrefix 29 }
	

-- The Alarm of Net board.The following are defined for ZXB10 and its 
--successors.

bgs10NetCardTraps		OBJECT IDENTIFIER	::= { zxbgs10Traps 3 }
bgs10NetCardTrapsPrefix	OBJECT IDENTIFIER	::= { bgs10NetCardTraps 0}

bgs10NetCardASXIdleAddrCounterZeroAlarm	NOTIFICATION-TYPE
	OBJECTS	{	entPhysicalContainedIn,
				entPhysicalParentRelPos,
				entPhysicalClass,
				atmfM4TrapAlarmSeverity
			}
	STATUS	current
	DESCRIPTION
		"Indicates that the idle address counter of the ASX clip becomes 
		zero."
	::= { bgs10NetCardTrapsPrefix 1 }
	
bgs10NetCardASXLinkListErrAlarm	NOTIFICATION-TYPE
	OBJECTS	{	entPhysicalContainedIn,
				entPhysicalParentRelPos,
				entPhysicalClass,
				atmfM4TrapAlarmSeverity
			}
	STATUS	current
	DESCRIPTION
		"Indicates that the LInk list of the ASX clip is wrong."
	::= { bgs10NetCardTrapsPrefix 2 }
	
bgs10NetCardASXInputClkStatusChangeAlarm	NOTIFICATION-TYPE
	OBJECTS	{	entPhysicalContainedIn,
				entPhysicalParentRelPos,
				entPhysicalClass,
				atmfM4TrapAlarmSeverity
			}
	STATUS	current
	DESCRIPTION
		"Indicates that the status of the input clock of the ASX clip is
		changed."
	::= { bgs10NetCardTrapsPrefix 3 }
	
bgs10NetCardASXInPortOverSpeedAlarm	NOTIFICATION-TYPE
   OBJECTS	{	entPhysicalContainedIn,
				entPhysicalParentRelPos,
				entPhysicalClass,
				atmfM4TrapAlarmSeverity
			}
	STATUS	current
	DESCRIPTION
		"Indicates that the inport of the ASX clip is over speed."
	::= { bgs10NetCardTrapsPrefix 4 }

bgs10NetCardASXCRCCheckErrAlarm	NOTIFICATION-TYPE
	OBJECTS	{	entPhysicalContainedIn,
				entPhysicalParentRelPos,
				entPhysicalClass,
				atmfM4TrapAlarmSeverity
			}
	STATUS	current
	DESCRIPTION
		"Indicates that the CRC check occurs error."
	::= { bgs10NetCardTrapsPrefix 5 }
	
bgs10NetCardASXCheckoutErrAlarm	NOTIFICATION-TYPE
	OBJECTS	{	entPhysicalContainedIn,
				entPhysicalParentRelPos,
				entPhysicalClass,
				atmfM4TrapAlarmSeverity
			}
	STATUS	current
	DESCRIPTION
		"Indicates that the ASX clip's chekcout is error."
	::= { bgs10NetCardTrapsPrefix 6 }

bgs10NetCardACESumErrAlarm	NOTIFICATION-TYPE
	OBJECTS	{	entPhysicalContainedIn,
				entPhysicalParentRelPos,
				entPhysicalClass,
				atmfM4TrapAlarmSeverity
			}
	STATUS	current
	DESCRIPTION
		"Indicates that the ACE clip's sum is error."
	::= { bgs10NetCardTrapsPrefix 7 }
	
bgs10NetCardACEInputClkStatusChangeAlarm	NOTIFICATION-TYPE
	OBJECTS	{	entPhysicalContainedIn,
				entPhysicalParentRelPos,
				entPhysicalClass,
				atmfM4TrapAlarmSeverity
			}
	STATUS	current
	DESCRIPTION
		"Indicates that the input clock's status of the ACE clip is changed."
	::= { bgs10NetCardTrapsPrefix 8 }
	
bgs10NetCardACEInPortOverSpeedAlarm	NOTIFICATION-TYPE
	OBJECTS	{	entPhysicalContainedIn,
				entPhysicalParentRelPos,
				entPhysicalClass,
				atmfM4TrapAlarmSeverity
			}
	STATUS	current
	DESCRIPTION
		"indicates that in port of the ACE clip is over speed."
	::= { bgs10NetCardTrapsPrefix 9 }

bgs10NetCardACECheckErrAlarm	NOTIFICATION-TYPE
	OBJECTS	{	entPhysicalContainedIn,
				entPhysicalParentRelPos,
				entPhysicalClass,
				atmfM4TrapAlarmSeverity
			}
	STATUS	current
	DESCRIPTION
		"Indicates that the ACE clip's check is error."
	::= { bgs10NetCardTrapsPrefix 10 }

--The Alarm of the Line card.The trap defined in ATM FORUM af-nm-0095.001
--(atmfm4LineCardAlarm:atmfm4MIBTrapPrefix 23) indicates the producing the 
--Alarm line card's position. the following traps are defined for detail 
--descroiption to every trap,and only for ZXB10 and its successors.

bgs10LICTraps		OBJECT IDENTIFIER ::= { zxbgs10Traps 4 }
bgs10LICTrapsPrefix	OBJECT IDENTIFIER ::= { bgs10LICTraps 0 }

bgs10LICECapFSyncErAlarm	NOTIFICATION-TYPE
	OBJECTS	{	entPhysicalContainedIn,
				entPhysicalParentRelPos,
				entPhysicalClass,
				atmfM4TrapAlarmSeverity
			}
	STATUS	current
	DESCRIPTION
		"Indicates that egress captured FIFO cells synchronization error occurrs."
	::= { bgs10LICTrapsPrefix 1 }
	
bgs10LICICapFSyncErAlarm	NOTIFICATION-TYPE
	OBJECTS	{	entPhysicalContainedIn,
				entPhysicalParentRelPos,
				entPhysicalClass,
				atmfM4TrapAlarmSeverity
			}
	STATUS	current
	DESCRIPTION
		"Indicates that the ingress captured FIFO cells synchronization error occurs."
	::= { bgs10LICTrapsPrefix 2 }

bgs10LICInsertFSyncErAlarm	NOTIFICATION-TYPE
	OBJECTS	{	entPhysicalContainedIn,
				entPhysicalParentRelPos,
				entPhysicalClass,
				atmfM4TrapAlarmSeverity
			}
	STATUS	current
	DESCRIPTION
		"Indicates that the insert FIFO cells synchronization error occurs."
	::= { bgs10LICTrapsPrefix 3 }
	
bgs10LICEmipErAlarm	NOTIFICATION-TYPE
	OBJECTS	{	entPhysicalContainedIn,
				entPhysicalParentRelPos,
				entPhysicalClass,
				atmfM4TrapAlarmSeverity
			}
	STATUS	current
	DESCRIPTION
		"Indicates that external memory interface parity error occurs."
	::= { bgs10LICTrapsPrefix 4 }

bgs10LICIRxPErAlarm	NOTIFICATION-TYPE
	OBJECTS	{	entPhysicalContainedIn,
				entPhysicalParentRelPos,
				entPhysicalClass,
				atmfM4TrapAlarmSeverity
			}
	STATUS	current
	DESCRIPTION
		"Indicates that the ingress parity error on UTOPIA recieve bus error occurs."
	::= { bgs10LICTrapsPrefix 5 }
	
bgs10LICERxPErAlarm	NOTIFICATION-TYPE
	OBJECTS	{	entPhysicalContainedIn,
				entPhysicalParentRelPos,
				entPhysicalClass,
				atmfM4TrapAlarmSeverity
			}
	STATUS	current
	DESCRIPTION
		"Indicates that the parity error on recieved egress cells error occurs."
	::= { bgs10LICTrapsPrefix 6 }
	
bgs10LICUSyncErAlarm	NOTIFICATION-TYPE
	OBJECTS	{	entPhysicalContainedIn,
				entPhysicalParentRelPos,
				entPhysicalClass,
				atmfM4TrapAlarmSeverity
			}
	STATUS	current
	DESCRIPTION
		"Indicates that the synchronization error takes place."
	::= { bgs10LICTrapsPrefix 7 }
	
bgs10LICPETErrAlarm	NOTIFICATION-TYPE
	OBJECTS	{	entPhysicalContainedIn,
				entPhysicalParentRelPos,
				entPhysicalClass,
				atmfM4TrapAlarmSeverity
			}
	STATUS	current
	DESCRIPTION
		"Indicates that the policing E update time out error."
	::= { bgs10LICTrapsPrefix 8 }

bgs10LICVCISzErAlarm	NOTIFICATION-TYPE
	OBJECTS	{	entPhysicalContainedIn,
				entPhysicalParentRelPos,
				entPhysicalClass,
				atmfM4TrapAlarmSeverity
			}
	STATUS	current
	DESCRIPTION
		"Indicates that the VCI size error occurs."
	::= { bgs10LICTrapsPrefix 9 }
	
bgs10LICVPISzErAlarm	NOTIFICATION-TYPE
	OBJECTS	{	entPhysicalContainedIn,
				entPhysicalParentRelPos,
				entPhysicalClass,
				atmfM4TrapAlarmSeverity
			}
	STATUS	current
	DESCRIPTION
		"Indicates that the VPI szie error occurs."
	::= { bgs10LICTrapsPrefix 10 }
	
bgs10LICMPHYOvrnAlarm	NOTIFICATION-TYPE
	OBJECTS	{	entPhysicalContainedIn,
				entPhysicalParentRelPos,
				entPhysicalClass,
				atmfM4TrapAlarmSeverity
			}
	STATUS	current
	DESCRIPTION
		"Indicates that MPHY port overrun condition has occured."
	::= { bgs10LICTrapsPrefix 11 }
	
bgs10LICInFiFLAlarm	NOTIFICATION-TYPE
	OBJECTS	{	entPhysicalContainedIn,
				entPhysicalParentRelPos,
				entPhysicalClass,
				atmfM4TrapAlarmSeverity
			}
	STATUS	current
	DESCRIPTION
		"Indicates that ingress FIFO full condition takes place."
	::= { bgs10LICTrapsPrefix 12 }
	
bgs10LICIERRSAlarm	NOTIFICATION-TYPE
	OBJECTS	{	entPhysicalContainedIn,
				entPhysicalParentRelPos,
				entPhysicalClass,
				atmfM4TrapAlarmSeverity
			}
	STATUS	current
	DESCRIPTION
		"Indicates that the sequencing error in ingress linked lists takes place."
	::= { bgs10LICTrapsPrefix 13 }
	
bgs10LICVERRPAlarm	NOTIFICATION-TYPE
	OBJECTS	{	entPhysicalContainedIn,
				entPhysicalParentRelPos,
				entPhysicalClass,
				atmfM4TrapAlarmSeverity
			}
	STATUS	current
	DESCRIPTION
		"Inidcates that the parity error in incoming egress cell takes place."
	::= { bgs10LICTrapsPrefix 14 }
	
bgs10LICEsErrAlarm	NOTIFICATION-TYPE
	OBJECTS	{	entPhysicalContainedIn,
				entPhysicalParentRelPos,
				entPhysicalClass,
				atmfM4TrapAlarmSeverity
			}
	STATUS	current
	DESCRIPTION
		"Inidcates that sequencing error in egress linked lists."
	::= { bgs10LICTrapsPrefix 15 }
	
bgs10LICIpRtyErrAlarm	NOTIFICATION-TYPE
	OBJECTS	{	entPhysicalContainedIn,
				entPhysicalParentRelPos,
				entPhysicalClass,
				atmfM4TrapAlarmSeverity
			}
	STATUS	current
	DESCRIPTION
		"Indicates that parity error in stored ingress cells takes place."
	::= { bgs10LICTrapsPrefix 16 }
	
bgs10LICEprtyErrAlarm	NOTIFICATION-TYPE
	OBJECTS	{	entPhysicalContainedIn,
				entPhysicalParentRelPos,
				entPhysicalClass,
				atmfM4TrapAlarmSeverity
			}
	STATUS	current
	DESCRIPTION
		"Indicates that parity error in stored egress cells takes palce."
	::= { bgs10LICTrapsPrefix 17 }
	
bgs10LICIbpOvrExcAlarm	NOTIFICATION-TYPE
	OBJECTS	{	entPhysicalContainedIn,
				entPhysicalParentRelPos,
				entPhysicalClass,
				atmfM4TrapAlarmSeverity
			}
	STATUS	current
	DESCRIPTION
		"Indicates that the backpressure override threshold exceeded takes place."
	::= { bgs10LICTrapsPrefix 18 }
	
bgs10LICPpErrAlarm	NOTIFICATION-TYPE
	OBJECTS	{	entPhysicalContainedIn,
				entPhysicalParentRelPos,
				entPhysicalClass,
				atmfM4TrapAlarmSeverity
			}
	STATUS	current
	DESCRIPTION
		"Indicates that parity error from pointer RAM has occured."
	::= { bgs10LICTrapsPrefix 19 }
	
bgs10LICPillErrAlarm	NOTIFICATION-TYPE
	OBJECTS	{	entPhysicalContainedIn,
				entPhysicalParentRelPos,
				entPhysicalClass,
				atmfM4TrapAlarmSeverity
			}
	STATUS	current
	DESCRIPTION
		"Indicates that ingress free list exhaustion error has occured."
	::= { bgs10LICTrapsPrefix 20 }
	
bgs10LICPellErrAlarm	NOTIFICATION-TYPE
	OBJECTS	{	entPhysicalContainedIn,
				entPhysicalParentRelPos,
				entPhysicalClass,
				atmfM4TrapAlarmSeverity
			}
	STATUS	current
	DESCRIPTION
		"Indicates that egress free list exhaustion error has occrued."
	::= { bgs10LICTrapsPrefix 21 }
	
bgs10LICPeIpErrAlarm	NOTIFICATION-TYPE
	OBJECTS	{	entPhysicalContainedIn,
				entPhysicalParentRelPos,
				entPhysicalClass,
				atmfM4TrapAlarmSeverity
			}
	STATUS	current
	DESCRIPTION
		"indicates that the egress index pair(IP) free list exhaustion error has 
		occured."
	::= { bgs10LICTrapsPrefix 22 }

bgs10LICUSyncErrAlarm	NOTIFICATION-TYPE
	OBJECTS	{	entPhysicalContainedIn,
				entPhysicalParentRelPos,
				entPhysicalClass,
				atmfM4TrapAlarmSeverity
			}
	STATUS	current
	DESCRIPTION
		"Indicates that the ingress synchronization error has occured."
	::= { bgs10LICTrapsPrefix 23 }
	
bgs10LICUegSyncErrPAlarm	NOTIFICATION-TYPE
	OBJECTS {	entPhysicalContainedIn,
				entPhysicalParentRelPos,
				entPhysicalClass,
				atmfM4TrapAlarmSeverity
			}
	STATUS	current
	DESCRIPTION
		"Indicates that the egress synchronization error has occured."
	::= { bgs10LICTrapsPrefix 24 }

--The Communication Alarm(SDH)
--The following traps are for ZXB10 and its successors.

bgs10CommSDHTraps			OBJECT IDENTIFIER ::= { zxbgs10Traps 5 }
bgs10CommSDHTrapsPrefix		OBJECT IDENTIFIER ::= { bgs10CommSDHTraps 0 }

--The LCD Alarm has defined in ATM Forum af-nm-0095.001:atmf4IfLcdAlarm
--(atmfM4MIBTrapPrefix 2 },so it isn't necessary to redefine it.

bgs10CommSDHTroolAlarm	NOTIFICATION-TYPE
	OBJECTS	{	ifOperStatus,
				atmfM4TrapAlarmSeverity
			}
	STATUS	current
	DESCRIPTION
		"indicates that transmitting reference out of lock(Abbr:TROOL) has
		occurred (PM5346 clip)."
	::= { bgs10CommSDHTrapsPrefix 1 }
	
bgs10CommSDHRdoolAlarm	NOTIFICATION-TYPE
	OBJECTS	{	ifOperStatus,
				atmfM4TrapAlarmSeverity
			}
	STATUS	current
	DESCRIPTION
		"Indicates that recieving data out of lock (Abbr:RDOOL) has
		occurred (PM5346 clip)."
	::= { bgs10CommSDHTrapsPrefix 2 }

bgs10CommSDHOofAlarm		NOTIFICATION-TYPE
	OBJECTS	{	ifOperStatus,
				atmfM4TrapAlarmSeverity
			}
	STATUS	current
	DESCRIPTION
		"Indicates that an OOFD Alarm condition has occurred(created by 
		PM5346 clip)."
	::= { bgs10CommSDHTrapsPrefix 3 }

--The LOF Alarm has been defined by ATM Forum af-nm-0095.001:atmfM4LofAlarm
--(atmfM4MIBTrapPrefix 3).Here should not redefine it.
 
--The LOS Alarm has been defined by ATM Forum af-nm-0095.001:atmfM4LosAlarm
--(atmfM4MIBTrapPrefix 5).Here should not redefine it.

--The RDI Alarm has been defined in ATM Forum af-nm-0095.001:atmfM4RdiAlarm
--(atmfM4MIBTrapPrefix 9), Here define two Alarms sbout it: one for line,
--another for path.

bgs10CommSDHLRdiAlarm	NOTIFICATION-TYPE
	OBJECTS	{	ifOperStatus,
				atmfM4TrapAlarmSeverity
			}
	STATUS	current
	DESCRIPTION
		"Indicates that an line RDI Alarm condition has occurred(created
		by PM5346 clip)."
	::= { bgs10CommSDHTrapsPrefix 4 }
	
bgs10CommSDHPRdiAlarm	NOTIFICATION-TYPE
	OBJECTS	{	ifOperStatus,
				atmfM4TrapAlarmSeverity
			}
	STATUS	current
	DESCRIPTION
		"indicates that a path RDT Alarm condition has occurred(created
		by PM5346 clip)."
	::= { bgs10CommSDHTrapsPrefix 5  }
  
--The AIS Alarm has been defined in ATM Forum af-nm-0095.001:atmfM4AisAlarm
--(atmfM4MIBTrapPrefix 9), Here define two Alarms sbout it: one for line,
--another for path.
bgs10CommSDHLAisAlarm	NOTIFICATION-TYPE
	OBJECTS	{	ifOperStatus,
				atmfM4TrapAlarmSeverity
			}
	STATUS	current
	DESCRIPTION
		"Indicates that a line Ais Alarm condition has occurred(created 
		by PM5346 clip)."
	::= { bgs10CommSDHTrapsPrefix 6 }
	
bgs10CommSDHPAisAlarm	NOTIFICATION-TYPE
	OBJECTS	{	ifOperStatus,
				atmfM4TrapAlarmSeverity
			}
	STATUS	current
	DESCRIPTION
		"Indicates that a path AIS Alarm condition has occurred(created
		by PM5346 clip)."
	::= { bgs10CommSDHTrapsPrefix 7 }

bgs10CommSDHRroolAlarm	NOTIFICATION-TYPE
	OBJECTS	{	ifOperStatus,
				atmfM4TrapAlarmSeverity
			}
	STATUS	current
	DESCRIPTION
		"Indicates that the recieving reference clock is out of lock(created
		PM5346)."
	::= { bgs10CommSDHTrapsPrefix 8 }
	
--the atmfM4IfLopAlarm has defined LOP Alarm in ATM Forum af-nm-0095.001
--So here don't redefine it.

--the ATM Alarm has defined in ATM Forum af-nm-0095.001. So here should not
--redefine them.

--the Frame Realg E1 Traps
bgs10FrfE1Traps			OBJECT IDENTIFIER 	::= { zxbgs10Traps 6 }
bgs10FrfE1TrapsPrefix	OBJECT IDENTIFIER	::= { bgs10FrfE1Traps 0 }

bgs10FrfE1CRCS1Alarm	NOTIFICATION-TYPE
	OBJECTS {	entPhysicalContainedIn,
				entPhysicalParentRelPos,
				entPhysicalClass,
				atmfM4TrapAlarmSeverity
			}
	STATUS	current
	DESCRIPTION
		"the CRC S1 Alarm of the FR/ATM  IWF Board E1 Physical  Port."
	::= { bgs10FrfE1TrapsPrefix 1 }
	
bgs10FrfE1CRCS2Alarm	NOTIFICATION-TYPE
	OBJECTS {	entPhysicalContainedIn,
				entPhysicalParentRelPos,
				entPhysicalClass,
				atmfM4TrapAlarmSeverity
			}
	STATUS	current
	DESCRIPTION
		"the CRC S2 Alarm of the FR/ATM  IWF Board E1 Physical  Port."
	::= { bgs10FrfE1TrapsPrefix 2 }
	
bgs10frfRfAil		NOTIFICATION-TYPE
	OBJECTS {	entPhysicalContainedIn,
				entPhysicalParentRelPos,
				entPhysicalClass,
				atmfM4TrapAlarmSeverity
			}
	STATUS	current
	DESCRIPTION
		"the RFAIL Alarm of the FR/ATM  IWF Board E1 Physical  Port."
	::= { bgs10FrfE1TrapsPrefix 3 }
	
bgs10FrfLossAlarm	NOTIFICATION-TYPE
	OBJECTS {	entPhysicalContainedIn,
				entPhysicalParentRelPos,
				entPhysicalClass,
				atmfM4TrapAlarmSeverity
			}
	STATUS	current
	DESCRIPTION
		"the loss Alarm of the FR/ATM  IWF Board E1 Physical  Port."
	::= { bgs10FrfE1TrapsPrefix 4 }
	
bgs10FrfAis16Alarm	NOTIFICATION-TYPE
	OBJECTS {	entPhysicalContainedIn,
				entPhysicalParentRelPos,
				entPhysicalClass,
				atmfM4TrapAlarmSeverity
			}
	STATUS	current
	DESCRIPTION
		"the AIS-16 Alarm of the FR/ATM  IWF Board E1 Physical  Port."
	::= { bgs10FrfE1TrapsPrefix 5 }
	
bgs10FrfAissAlarm	NOTIFICATION-TYPE
	OBJECTS {	entPhysicalContainedIn,
				entPhysicalParentRelPos,
				entPhysicalClass,
				atmfM4TrapAlarmSeverity
			}
	STATUS	current
	DESCRIPTION
		"the CRC S1 Alarm of the FR/ATM  IWF Board E1 Physical  Port."
	::= { bgs10FrfE1TrapsPrefix 6 }

bgs10FrfRaisAlarm	NOTIFICATION-TYPE
	OBJECTS {	entPhysicalContainedIn,
				entPhysicalParentRelPos,
				entPhysicalClass,
				atmfM4TrapAlarmSeverity
			}
	STATUS	current
	DESCRIPTION
		"the RAIS Alarm of the FR/ATM  IWF Board E1 Physical  Port."
	::= { bgs10FrfE1TrapsPrefix 7 }
	
bgs10FrfRcrsAlarm	NOTIFICATION-TYPE
	OBJECTS {	entPhysicalContainedIn,
				entPhysicalParentRelPos,
				entPhysicalClass,
				atmfM4TrapAlarmSeverity
			}
	STATUS	current
	DESCRIPTION
		"the RCRS Alarm of the FR/ATM  IWF Board E1 Physical  Port."
	::= { bgs10FrfE1TrapsPrefix 8 }
	
bgs10FrfE1LCDAlarm	NOTIFICATION-TYPE
	OBJECTS {	entPhysicalContainedIn,
				entPhysicalParentRelPos,
				entPhysicalClass,
				atmfM4TrapAlarmSeverity
			}
	STATUS	current
	DESCRIPTION
		"the LCD Alarm of the FR/ATM  IWF Board E1 Physical  Port."
	::= { bgs10FrfE1TrapsPrefix 9 }
	
bgs10FrfFrTraps			OBJECT IDENTIFIER 	::= { zxbgs10Traps 7 }
bgs10FrfFrTrapsPrefix	OBJECT IDENTIFIER 	::= { bgs10FrfFrTraps 0 }

bgs10FrfFrLogicalPortAlarm	NOTIFICATION-TYPE
	OBJECTS {	entPhysicalContainedIn,
				entPhysicalParentRelPos,
				entPhysicalClass,
				atmfM4TrapAlarmSeverity
			}
	STATUS	current
	DESCRIPTION
		"the  Alarm of the FR/ATM  IWF Board Logical Port."
	::= { bgs10FrfFrTrapsPrefix 1 }
	
bgs10FrfFrPvcAlarm	NOTIFICATION-TYPE
	OBJECTS {	entPhysicalContainedIn,
				entPhysicalParentRelPos,
				entPhysicalClass,
				atmfM4TrapAlarmSeverity
			}
	STATUS	current
	DESCRIPTION
		"the Alarm of the FR/ATM  IWF Board PVC Port."
	::= { bgs10FrfFrTrapsPrefix 2 }
	
bgs10Cardtraps			OBJECT IDENTIFIER	::= { zxbgs10Traps 8 }
bgs10CardTrapsPrefix	OBJECT IDENTIFIER	::= { bgs10Cardtraps 0 }

bgs10CardOnLineStatus			NOTIFICATION-TYPE
	OBJECTS { 	bgs10PlugInUnitCardType,
				atmfM4PlugInUnitAvailStatus,
				bgs10PlugInUnitMasterStatus
			}
	STATUS	current
	DESCRIPTION
		"the card stats's notification ."
	::= { bgs10CardTrapsPrefix 1 }
	
bgs10PerfTraps			OBJECT IDENTIFIER	::= { zxbgs10Traps 9 }
bgs10PerfTrapsPrefix	OBJECT IDENTIFIER	::= { bgs10PerfTraps 0 }

bgs10PerfPortDiscardHECViolCell		NOTIFICATION-TYPE
	OBJECTS {	alarmValue,
				alarmRisingThreshold,
				alarmFallingThreshold,
				atmfM4TrapAlarmSeverity
			}
	STATUS	current
	DESCRIPTION
		"the discard violate cells ."
	::= { bgs10PerfTrapsPrefix 1 }
	
bgs10UpcNpcDisagreementCell				NOTIFICATION-TYPE
	OBJECTS {	alarmValue,
				alarmRisingThreshold,
				atmfM4TrapAlarmSeverity
			}
	STATUS	current
	DESCRIPTION
		"the UPC/NPC disagreement cells ."
	::= { bgs10PerfTrapsPrefix 2 }
	
bgs10OAMLoopback	NOTIFICATION-TYPE
	OBJECTS {	bgs10PmLoopBackTestIndex,
				bgs10PmLoopBackTestResult
			}
	STATUS	current
	DESCRIPTION
		"the OAM loop-back test notification ."
	::= { bgs10PerfTrapsPrefix 3 }
	
bgs10OAMLoopbackTestOver NOTIFICATION-TYPE
	OBJECTS {	bgs10PmLoopBackTestIndex,
				bgs10PmLoopBackTestResult
			}
	STATUS	current
	DESCRIPTION
		"the OAM loop-back test notification ."
	::= { bgs10PerfTrapsPrefix 4 }

bgs10E1CellsTraps		OBJECT IDENTIFIER	::= { zxbgs10Traps 10 }
bgs10E1CellsTrapsPrefix	OBJECT IDENTIFIER	::= { bgs10E1CellsTraps 0 }	

bgs10E1CellsYellowAlarm	NOTIFICATION-TYPE
	OBJECTS {	bgs10E1LinkOperStatus,
				atmfM4TrapAlarmSeverity
			}
	STATUS	current
	DESCRIPTION
		"the E1 yellow Alarm notification ."
	::= { bgs10E1CellsTrapsPrefix 1 }
	
bgs10E1CellsLofAlarm	NOTIFICATION-TYPE
	OBJECTS {	bgs10E1LinkOperStatus,
				atmfM4TrapAlarmSeverity
			}
	STATUS	current
	DESCRIPTION
		"the E1 LOF Alarm notification ."
	::= { bgs10E1CellsTrapsPrefix 2 }
	
bgs10E1CellsLosAlarm	NOTIFICATION-TYPE
	OBJECTS {	bgs10E1LinkOperStatus,
				atmfM4TrapAlarmSeverity
			}
	STATUS	current
	DESCRIPTION
		"the E1 LOS Alarm notification ."
	::= { bgs10E1CellsTrapsPrefix 3 }
	
bgs10E1CellsAisAlarm	NOTIFICATION-TYPE
	OBJECTS {	bgs10E1LinkOperStatus,
				atmfM4TrapAlarmSeverity
			}
	STATUS	current
	DESCRIPTION
		"the E1 AIS Alarm notification ."
	::= { bgs10E1CellsTrapsPrefix 4 }
	
bgs10E1CellsCrcAlarm	NOTIFICATION-TYPE
	OBJECTS {	bgs10E1LinkOperStatus,
				atmfM4TrapAlarmSeverity
			}
	STATUS	current
	DESCRIPTION
		"the E1 CRC Alarm notification ."
	::= { bgs10E1CellsTrapsPrefix 5 }
	
bgs10E1CellsAtmLcdAlarm	NOTIFICATION-TYPE
	OBJECTS {	bgs10E1LinkOperStatus,
				atmfM4TrapAlarmSeverity
			}
	STATUS	current
	DESCRIPTION
		"the E1 ATM LCD Alarm notification ."
	::= { bgs10E1CellsTrapsPrefix 6 }

--The Fans' Alarm, different from ATM Forum

bgs10FanTraps				OBJECT IDENTIFIER	::= { zxbgs10Traps 11 }
bgs10FanTrapsPrefix			OBJECT IDENTIFIER	::= { bgs10FanTraps 0 }

bgs10Fan1Alarm			NOTIFICATION-TYPE
	OBJECTS {	atmfM4TrapAlarmSeverity
			}
	STATUS	current
	DESCRIPTION
		"The Alarm of Fan No.1"
	::= { bgs10FanTrapsPrefix 1}
	
bgs10Fan2Alarm			NOTIFICATION-TYPE
	OBJECTS {	atmfM4TrapAlarmSeverity
			}
	STATUS	current
	DESCRIPTION
		"The Alarm of Fan No.2"
	::= { bgs10FanTrapsPrefix 2}
	
	
bgs10Fan3Alarm			NOTIFICATION-TYPE
	OBJECTS {	atmfM4TrapAlarmSeverity
			}
	STATUS	current
	DESCRIPTION
		"The Alarm of Fan No.3"
	::= { bgs10FanTrapsPrefix 3}


bgs10Fan4Alarm			NOTIFICATION-TYPE
	OBJECTS {	atmfM4TrapAlarmSeverity
			}
	STATUS	current
	DESCRIPTION
		"The Alarm of Fan No.4"
	::= { bgs10FanTrapsPrefix 4}

--The Software' Alarm, different from ATM Forum

bgs10SoftwareTraps				OBJECT IDENTIFIER	::= { zxbgs10Traps 12 }
bgs10SoftwareTrapsPrefix		OBJECT IDENTIFIER	::= { bgs10SoftwareTraps 0 }

bgs10SoftwareCommAlarm			NOTIFICATION-TYPE
	OBJECTS {	
				zxb10SoftSpecialAlarmParam1,
				zxb10SoftSpecialAlarmParam2,
				zxb10SoftSpecialAlarmParam3,
				zxb10SoftSpecialAlarmParam4,
				zxb10SoftSpecialAlarmParam5,
				zxb10SoftSpecialAlarmParam6,
				zxb10SoftSpecialAlarmParam7,
			   	atmfM4TrapAlarmSeverity
			}
	STATUS	current
	DESCRIPTION
		"The Comm Alarm of Software Alarm"
	::= { bgs10SoftwareTrapsPrefix 1}

bgs10SoftwareSSCOPConnAlarm			NOTIFICATION-TYPE
	OBJECTS {	
				zxb10SoftSpecialAlarmParam1,
				zxb10SoftSpecialAlarmParam2,
				zxb10SoftSpecialAlarmParam3,
				zxb10SoftSpecialAlarmParam4,
				zxb10SoftSpecialAlarmParam5
			}
	STATUS	current
	DESCRIPTION
		"The SSCOP Connection Alarm of Software Alarm"
	::= { bgs10SoftwareTrapsPrefix 2}

bgs10SoftwareSSCOPErrorIndication			NOTIFICATION-TYPE
	OBJECTS {	
				zxb10SoftSpecialAlarmParam1,
				zxb10SoftSpecialAlarmParam2,
				zxb10SoftSpecialAlarmParam3,
				zxb10SoftSpecialAlarmParam4,
				zxb10SoftSpecialAlarmParam5,
				zxb10SoftSpecialAlarmParam6
			}
	STATUS	current
	DESCRIPTION
		"The SSCOP Error Indication of Software Alarm"
	::= { bgs10SoftwareTrapsPrefix 3}

bgs10SoftwareLdpSigIndication			NOTIFICATION-TYPE
	OBJECTS {	
				zxb10SoftSpecialAlarmParam1,
				zxb10SoftSpecialAlarmParam2,
				zxb10SoftSpecialAlarmParam3
			}
	STATUS	current
	DESCRIPTION
		"The LDP Signal Indication of Software Alarm"
	::= { bgs10SoftwareTrapsPrefix 4}

bgs10SoftwareSPVCVcStatus			NOTIFICATION-TYPE
	OBJECTS {	
				zxb10SoftSpecialAlarmParam1,
				zxb10SoftSpecialAlarmParam2,
				zxb10SoftSpecialAlarmParam3,
				zxb10SoftSpecialAlarmParam4,
				zxb10SoftSpecialAlarmParam5,
				zxb10SoftSpecialAlarmParam8
			}
	STATUS	current
	DESCRIPTION
		"The SPVC VC Status Indication of Software Alarm"
	::= { bgs10SoftwareTrapsPrefix 5}

bgs10SoftwareSPVCVpStatus			NOTIFICATION-TYPE
	OBJECTS {	
				zxb10SoftSpecialAlarmParam1,
				zxb10SoftSpecialAlarmParam2,
				zxb10SoftSpecialAlarmParam3,
				zxb10SoftSpecialAlarmParam4,
				zxb10SoftSpecialAlarmParam8
			}
	STATUS	current
	DESCRIPTION
		"The SPVC VP Status Indication of Software Alarm"
	::= { bgs10SoftwareTrapsPrefix 6}

bgs10SoftwareSPVCFrStatus			NOTIFICATION-TYPE
	OBJECTS {	
				zxb10SoftSpecialAlarmParam1,
				zxb10SoftSpecialAlarmParam2,
				zxb10SoftSpecialAlarmParam3,
				zxb10SoftSpecialAlarmParam4,
				zxb10SoftSpecialAlarmParam8
			}
	STATUS	current
	DESCRIPTION
		"The SPVC FR Status Indication of Software Alarm"
	::= { bgs10SoftwareTrapsPrefix 7}

bgs10SoftwareSPVCCesStatus			NOTIFICATION-TYPE
	OBJECTS {	
				zxb10SoftSpecialAlarmParam1,
				zxb10SoftSpecialAlarmParam2,
				zxb10SoftSpecialAlarmParam8
			}
	STATUS	current
	DESCRIPTION
		"The SPVC CES Status Indication of Software Alarm"
	::= { bgs10SoftwareTrapsPrefix 8}

bgs10SoftwareILMIAlarm			NOTIFICATION-TYPE
	OBJECTS {	
				zxb10SoftSpecialAlarmParam1,
				zxb10SoftSpecialAlarmParam2,
				zxb10SoftSpecialAlarmParam8
			}
	STATUS	current
	DESCRIPTION
		"The SPVC CES Status Indication of Software Alarm"
	::= { bgs10SoftwareTrapsPrefix 9}

bgs10SoftwareIMAConnectivityAlarm			NOTIFICATION-TYPE
	OBJECTS {	
				zxb10SoftSpecialAlarmParam1,
				zxb10SoftSpecialAlarmParam2,
				zxb10SoftSpecialAlarmParam8
			}
	STATUS	current
	DESCRIPTION
		"The IMA Connectivity Alarm"
	::= { bgs10SoftwareTrapsPrefix 10}

bgs10SoftwareMFUM2SFailedAlarm		NOTIFICATION-TYPE
	OBJECTS {	
				zxb10SoftSpecialAlarmParam1,
				zxb10SoftSpecialAlarmParam2,
				zxb10SoftSpecialAlarmParam8
			}
	STATUS	current
	DESCRIPTION
		"The MFU Master to Slave CES Status Indication of Software Alarm"
	::= { bgs10SoftwareTrapsPrefix 11}

--The X.25 Alarm
bgs10X25Traps			OBJECT IDENTIFIER	::= { zxbgs10Traps 13 }
bgs10X25TrapsPrefix		OBJECT IDENTIFIER	::= { bgs10X25Traps 0 }

bgs10X25RestartAlarm			NOTIFICATION-TYPE
	OBJECTS {	
				bgs10X25OperRestart,
				bgs10X25LapbOperRealmodule,
				bgs10X25LapbOperRealport							
			}
	STATUS	current
	DESCRIPTION
		"The Restart Alarm of X25 Alarm"
	::= { bgs10X25TrapsPrefix 1}

bgs10X25ProtocolStateAlarm			NOTIFICATION-TYPE
	OBJECTS {	
				bgs10X25LapbOperState,
				bgs10X25LapbOperRealmodule,
				bgs10X25LapbOperRealport			
			}
	STATUS	current
	DESCRIPTION
		"The Link Alarm of X25 Alarm"
	::= { bgs10X25TrapsPrefix 2}
	
bgs10X25PhyPortDSRAlarm		NOTIFICATION-TYPE
	OBJECTS {	
				bgs10X25Rs232PortDSRAlarm,
			   	atmfM4TrapAlarmSeverity
			}
	STATUS	current
	DESCRIPTION
		"The Phy Port DSR Alarm of X25 Alarm"
	::= { bgs10X25TrapsPrefix 3}
	
bgs10X25PhyPortDTRAlarm		NOTIFICATION-TYPE
	OBJECTS {	
				bgs10X25Rs232PortDTRAlarm,
			   	atmfM4TrapAlarmSeverity
			}
	STATUS	current
	DESCRIPTION
		"The Phy Port DTR Alarm of X25 Alarm"
	::= { bgs10X25TrapsPrefix 4}

--The Ima Alarm
bgs10ImaTraps			OBJECT IDENTIFIER	::= { zxbgs10Traps 14 }
bgs10ImaTrapsPrefix		OBJECT IDENTIFIER	::= { bgs10ImaTraps 0 }

bgs10ImaGroupLinkAlarm			NOTIFICATION-TYPE
	OBJECTS {	
				bgs10ImaAlarmType,
				bgs10ImaLinkFlag,
				atmfM4TrapAlarmSeverity
			}
	STATUS	current
	DESCRIPTION
		"The Group and Link Alarm of Ima Alarm"
	::= { bgs10ImaTrapsPrefix 1}

--the Rs232 Traps
bgs10Rs232Traps			OBJECT IDENTIFIER 	::= { zxbgs10Traps 15 }
bgs10Rs232TrapsPrefix	OBJECT IDENTIFIER	::= { bgs10Rs232Traps 0 }

bgs10Rs232DCDAlarm	NOTIFICATION-TYPE
	OBJECTS {	entPhysicalContainedIn,
				entPhysicalParentRelPos,
				entPhysicalClass,
				atmfM4TrapAlarmSeverity
			}
	STATUS	current
	DESCRIPTION
		"the DCD Alarm of the Rs232 Physical  Port."
	::= { bgs10Rs232TrapsPrefix 1 }
	
bgs10Rs232DTRAlarm	NOTIFICATION-TYPE
	OBJECTS {	entPhysicalContainedIn,
				entPhysicalParentRelPos,
				entPhysicalClass,
				atmfM4TrapAlarmSeverity
			}
	STATUS	current
	DESCRIPTION
		"the DTR Alarm of the Rs232 Physical  Port."
	::= { bgs10Rs232TrapsPrefix 2 }
	
bgs10Rs232DSRAlarm	NOTIFICATION-TYPE
	OBJECTS {	entPhysicalContainedIn,
				entPhysicalParentRelPos,
				entPhysicalClass,
				atmfM4TrapAlarmSeverity
			}
	STATUS	current
	DESCRIPTION
		"the DSR Alarm of the Rs232 Physical  Port."
	::= { bgs10Rs232TrapsPrefix 3 }

bgs10Rs232CTSAlarm	NOTIFICATION-TYPE
	OBJECTS {	entPhysicalContainedIn,
				entPhysicalParentRelPos,
				entPhysicalClass,
				atmfM4TrapAlarmSeverity
			}
	STATUS	current
	DESCRIPTION
		"the CTS Alarm of the Rs232 Physical  Port."
	::= { bgs10Rs232TrapsPrefix 4 }
	
bgs10Rs232RTSAlarm	NOTIFICATION-TYPE
	OBJECTS {	entPhysicalContainedIn,
				entPhysicalParentRelPos,
				entPhysicalClass,
				atmfM4TrapAlarmSeverity
			}
	STATUS	current
	DESCRIPTION
		"the RTS Alarm of the Rs232 Physical  Port."
	::= { bgs10Rs232TrapsPrefix 5 }

--the E3 Traps
bgs10E3Traps			OBJECT IDENTIFIER 	::= { zxbgs10Traps 16 }
bgs10E3TrapsPrefix		OBJECT IDENTIFIER	::= { bgs10E3Traps 0 }

bgs10E3RAIAlarm	NOTIFICATION-TYPE
	OBJECTS {	entPhysicalContainedIn,
				entPhysicalParentRelPos,
				entPhysicalClass,
				atmfM4TrapAlarmSeverity
			}
	STATUS	current
	DESCRIPTION
		"the RAI Alarm of the E3 Physical  Port."
	::= { bgs10E3TrapsPrefix 1 }
	
bgs10E3LOFAlarm	NOTIFICATION-TYPE
	OBJECTS {	entPhysicalContainedIn,
				entPhysicalParentRelPos,
				entPhysicalClass,
				atmfM4TrapAlarmSeverity
			}
	STATUS	current
	DESCRIPTION
		"the LOF Alarm of the E3 Physical  Port."
	::= { bgs10E3TrapsPrefix 2 }
	
bgs10E3LOSAlarm	NOTIFICATION-TYPE
	OBJECTS {	entPhysicalContainedIn,
				entPhysicalParentRelPos,
				entPhysicalClass,
				atmfM4TrapAlarmSeverity
			}
	STATUS	current
	DESCRIPTION
		"the LOS Alarm of the E3 Physical  Port."
	::= { bgs10E3TrapsPrefix 3 }

bgs10E3AISAlarm	NOTIFICATION-TYPE
	OBJECTS {	entPhysicalContainedIn,
				entPhysicalParentRelPos,
				entPhysicalClass,
				atmfM4TrapAlarmSeverity
			}
	STATUS	current
	DESCRIPTION
		"the AIS Alarm of the E3 Physical  Port."
	::= { bgs10E3TrapsPrefix 4 }
	
bgs10E3FERFAlarm	NOTIFICATION-TYPE
	OBJECTS {	entPhysicalContainedIn,
				entPhysicalParentRelPos,
				entPhysicalClass,
				atmfM4TrapAlarmSeverity
			}
	STATUS	current
	DESCRIPTION
		"the FERF Alarm of the E3 Physical  Port."
	::= { bgs10E3TrapsPrefix 5 }

bgs10E3LCDAlarm	NOTIFICATION-TYPE
	OBJECTS {	entPhysicalContainedIn,
				entPhysicalParentRelPos,
				entPhysicalClass,
				atmfM4TrapAlarmSeverity
			}
	STATUS	current
	DESCRIPTION
		"the LCD Alarm of the E3 Physical  Port."
	::= { bgs10E3TrapsPrefix 6 }

--end of zhongxing mib.
END
