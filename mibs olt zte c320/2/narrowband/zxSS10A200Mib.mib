--Msag MIB Definition

ZXSS10-A200-MIB DEFINITIONS ::= BEGIN

    IMPORTS
        MODULE-IDENTITY, OBJECT-TYPE, enterprises,IpAddress,Counter32,
        Counter64, Unsigned32 FROM SNMPv2-SMI
        TEXTUAL-CONVENTION,MacAddress,DateAndTime,RowStatus,DisplayString
        FROM SNMPv2-TC;
         
    zte   OBJECT IDENTIFIER ::= { enterprises 3902 }
    ss-gateway OBJECT IDENTIFIER ::= { zte 701 }
    a200 OBJECT IDENTIFIER ::= { ss-gateway 1 }
    
    a200-mib MODULE-IDENTITY
    LAST-UPDATED "0202280830Z"
    ORGANIZATION "Nanjing Research Institute of ZhongXin Telecommunication Co.limited"
    CONTACT-INFO "  data group of Wire-Network department           
                    tel:    86-25-2871502
                     E-mail: yuan.yue@mail.zte.com.cn
                 "
    DESCRIPTION  "This module defined Access Gateway AG200 MIB for snmp"
    REVISION     "0110150200Z"    
    DESCRIPTION
                 "version 1.0"
    ::={a200 1}

-- MODULE DESCRIPTION END 
--------------------------------------------------------

--NEXT TEXT CONVENTION DEFINITION    
   A200RackTypes::= TEXTUAL-CONVENTION
        STATUS      current
        DESCRIPTION
            "Rack type used by ZXSS10-A200.
             ZXA200NOMAL: ZXA200 normal rack;
             ZXA200EXTRN: ZXA200 extern rack."
        SYNTAX      INTEGER
        {
            zxA200NOMAL(1)
        }
             
   A200ShelfTypes::= TEXTUAL-CONVENTION
        STATUS      current
        DESCRIPTION
            "Shelf type used by ZXSS10-A200.
             dBCONBSTBASE :  control shelf;
             dBCONBSTBASE1:  extern control shelf;
             dBCONBSTSLC  :  subscriber line circuit shelf;
             dBCONBSTSLC1 :  extern subscriber line circuit shelf."
        SYNTAX      INTEGER
        {
            dBCONBSTBASE(1),
            dBCONBSTBASE1(2),
            dBCONBSTSLC(3),
            dBCONBSTSLC1(4),
            dBCONBSTMSAGEX(5),
            dBCONBSTMSAGCTL(6),
            onu100(8),
            out50C(9),
            out50D(10),
            mbsl_CTL(11),
            mbsl_EX(12),
            tpu_EX(13),
            pp_EX(14),
            doublePP_EX(15)
        }

   A200BoardTypes::= TEXTUAL-CONVENTION
        STATUS      current
        DESCRIPTION
            "Board type used by ZXSS10-A200.
             dBCONWBTASCL  :  simulation board;
             dBCONWBTAMTT  :  multi-function test board;
             dBCONWBTMFP   :  multi-function main processing module;
             dBCONWBTAPR   :  packet processing and resource card;
             dBCONWBTAMSNIC:  network interface card;
             dBCONWBTASP   :  subscriber unit driver card;
             dBCONWBTASPI  :  subscriber unit driver interface card;
             dBCONWBTAPOW  :  access gateway power card;
             dBCONWBTAPOWP :  access gateway power card;
             dBCONWBTAFAN  :  access gateway fan card;"
        SYNTAX      INTEGER
        {
            dBCONWBTASCL(1),
            dBCONWBTAMTT(2),
            dBCONWBTMFP(3),
            dBCONWBTAPR(4),
            dBCONWBTAMSNIC(5),
            dBCONWBTASP(6),
            dBCONWBTASPI(7),
            dBCONWBTAPOW(8),
            dBCONWBTAPOWP(9),
            dBCONWBTAFAN(10)
        }
                
--TEXT CONVENTION END
------------------------------------------------------------------

--NEXT DEFINE TABLES IN THIS MIB
--mgcfg table definition begin
   a200mgcfgTable OBJECT-TYPE
        SYNTAX        SEQUENCE OF A200MgcfgEntry
        MAX-ACCESS    not-accessible
        STATUS        current
        DESCRIPTION   
            "Media gateway table."
        ::={a200-mib 1}

   a200mgcfgentry OBJECT-TYPE
        SYNTAX        A200MgcfgEntry
        MAX-ACCESS    not-accessible
        STATUS        current
        DESCRIPTION   
            "colunms and index of mgccfg table"
        INDEX {a200mgid}
        ::={a200mgcfgTable 1}
    
    A200MgcfgEntry ::= SEQUENCE
        {
            a200seckey                        Integer32,    
            a200tranidmax                     Unsigned32,
            a200tranidmin                     Unsigned32,    
            a200mgport                        Integer32,
            a200tractnum                      Integer32,
            a200sdpcho                        Integer32,
            a200retranmin                     Integer32,
            a200lkpttime                      Integer32,
            a200pendtime                      Integer32,
            a200pendcount                     Integer32,
            a200kprestime                     Integer32,
            a200mgid                          Integer32,
            a200mgcid                         Integer32,
            a200protype                       INTEGER,
            a200version                       Integer32,
            a200encodetp                      INTEGER,
            a200translay                      INTEGER,
            a200transpro                      INTEGER,
            a200secmet                        Integer32,
            a200retrannum                     Integer32,
            a200resdelay                      INTEGER,
            a200mgip                          IpAddress,
            a200mgmask                        IpAddress,
            a200mgRowStatus                   RowStatus,
            a200mgPSTNMediaVoiceTos           INTEGER,
            a200mgPSTNMediaFaxTos             INTEGER,  
            a200mgPSTNMediaModemTos           INTEGER,
            a200mgPSTNMediaDataTos            INTEGER,            
            a200mgSigTos                      INTEGER,
            a200mgISTNMediaVoiceTos           INTEGER,
            a200mgISTNMediaFaxTos             INTEGER,  
            a200mgISTNMediaModemTos           INTEGER,
            a200mgISTNMediaDataTos            INTEGER,
            a200mgDomainName                  DisplayString,
            a200mgInfo                        INTEGER,
            a200mgcid2                        Integer32,
            a200mgcid3                        Integer32,
            a200mgcid4                        Integer32,
            a200rtpFaxPri1                    INTEGER,
            a200rtpFaxPri2                    INTEGER,
            a200rtpFaxPri3                    INTEGER,
            a200rtpFaxPri4                    INTEGER,
            a200rtp2833Type                   INTEGER,
            a200callParaFo                    Integer32,
            a200callNumRcv                    Integer32,
            a200softPara                      Integer32,
            a200ipsThreshold                  Integer32,
            a200selfexchange                  INTEGER, 
            a200protectcall                   INTEGER,
            a200calllimit                     INTEGER,
            a200callmatchtype                 INTEGER,
            a200FAX_CNG_TONE                  INTEGER,
            a200V21_FLAGS_TONE                INTEGER,
            a200T38_FAX_END                   INTEGER,
            a200ANSamWI_TONE                  INTEGER,
            a200ANSamWO_TONE                  INTEGER,
            a200ANSWI_TONE                    INTEGER,
            a200ANSWO_TONE                    INTEGER,
            a200disasterprot                  INTEGER,
            a200currentmgcid                  Integer32,
            
            a200MgReversePolarityControlMode  INTEGER,
            a200MgCongestionToneTimeOut       Integer32
        }

    a200seckey    OBJECT-TYPE
        SYNTAX       Integer32
        MAX-ACCESS   read-create
        STATUS       current
        DESCRIPTION  
            "Security key."
        ::={a200mgcfgentry 1}
    
    a200tranidmax     OBJECT-TYPE
        SYNTAX       Unsigned32
        MAX-ACCESS   read-create
        STATUS       current
        DESCRIPTION  
            "Maximum value of transactionID. It should be less than 0xffffffff."
        ::={a200mgcfgentry 2}

    a200tranidmin      OBJECT-TYPE
        SYNTAX       Unsigned32
        MAX-ACCESS   read-create
        STATUS       current
        DESCRIPTION  
            "Minimum value of transactionID. It should not be less than 0."
        ::={a200mgcfgentry 3}

    a200mgport  OBJECT-TYPE
        SYNTAX       Integer32
        MAX-ACCESS   read-create
        STATUS       current
        DESCRIPTION  
            "UDP port number of MG."
        ::={a200mgcfgentry 4}

    a200tractnum  OBJECT-TYPE
        SYNTAX       Integer32(5000..7000)
        MAX-ACCESS   read-create
        STATUS       current
        DESCRIPTION  
            "Session number of MG."
        ::={a200mgcfgentry 5}

    a200sdpcho  OBJECT-TYPE
        SYNTAX       Integer32
        MAX-ACCESS   read-create
        STATUS       current
        DESCRIPTION  
            "Command category that SDP supports."
        ::={a200mgcfgentry 6}

    a200retranmin OBJECT-TYPE
        SYNTAX       Integer32(300..1500)
        UNITS        "ms"
        MAX-ACCESS   read-create
        STATUS       current
        DESCRIPTION  
            "Minimum re-transmission timer."
        ::={a200mgcfgentry 7}

    a200lkpttime  OBJECT-TYPE
        SYNTAX       Integer32
        MAX-ACCESS   read-create
        STATUS       current
        DESCRIPTION    
            "Link checking message sent interval. The message should be sent
             two times in the interval."
        ::={a200mgcfgentry 8}

    a200pendtime  OBJECT-TYPE
        SYNTAX       Integer32(300..1000)
        UNITS        "ms"
        MAX-ACCESS   read-create
        STATUS       current
        DESCRIPTION  
            "Pend time."
        ::={a200mgcfgentry 9}

    a200pendcount  OBJECT-TYPE
        SYNTAX       Integer32(20..50)
        MAX-ACCESS   read-create
        STATUS       current
        DESCRIPTION    
            "Maximum pend counter."
        ::={a200mgcfgentry 10}

    a200kprestime  OBJECT-TYPE
        SYNTAX       Integer32(20..50)
        UNITS        "seconds"
        MAX-ACCESS   read-create
        STATUS       current
        DESCRIPTION  
            "The reserved time responsed to MGC."
        DEFVAL  { 30 }
        ::={a200mgcfgentry 11}

    a200mgid  OBJECT-TYPE
        SYNTAX       Integer32
        MAX-ACCESS   not-accessible
        STATUS       current
        DESCRIPTION  
            "MG ID"
        ::={a200mgcfgentry 12}

    a200mgcid  OBJECT-TYPE
        SYNTAX       Integer32(1..255)
        MAX-ACCESS   read-create
        STATUS       current
        DESCRIPTION  
            "MGC ID."
        ::={a200mgcfgentry 13}

    a200protype  OBJECT-TYPE
        SYNTAX       INTEGER
            {
                h248(1),
                mgcp(2)
            }
        MAX-ACCESS   read-create
        STATUS       current
        DESCRIPTION  
            "Protocol type."
        ::={a200mgcfgentry 14}

    a200version  OBJECT-TYPE
        SYNTAX       Integer32
        MAX-ACCESS   read-create
        STATUS       current
        DESCRIPTION  
            "Protocol version."
        ::={a200mgcfgentry 15}

    a200encodetp  OBJECT-TYPE
        SYNTAX       INTEGER
            {
                text(1),
                binary(2)
            }
        MAX-ACCESS   read-create
        STATUS       current
        DESCRIPTION    
            "Protocol encoding type."
        ::={a200mgcfgentry 16}

    a200translay  OBJECT-TYPE
        SYNTAX       INTEGER
            {
                ip(1),
                atm(2)
            }
        MAX-ACCESS   read-create
        STATUS       current
        DESCRIPTION  
            "Transmission type."
        ::={a200mgcfgentry 17}

    a200transpro  OBJECT-TYPE
        SYNTAX       INTEGER
            {
                udp(1),
                tcp(2)
            }
        MAX-ACCESS   read-create
        STATUS       current
        DESCRIPTION  
            "Transmission protocol type."
        ::={a200mgcfgentry 18}

    a200secmet  OBJECT-TYPE
        SYNTAX       Integer32
        MAX-ACCESS   read-create
        STATUS       current
        DESCRIPTION  
            " Encryption type."
        ::={a200mgcfgentry 19}

    a200retrannum  OBJECT-TYPE
        SYNTAX       Integer32(3..7)
        MAX-ACCESS   read-create
        STATUS       current
        DESCRIPTION  
            "Retransmission times."
        ::={a200mgcfgentry 20}

    a200resdelay  OBJECT-TYPE
        SYNTAX       Integer32(20..255)
        UNITS        "seconds"
        MAX-ACCESS   read-create
        STATUS       current
        DESCRIPTION  
            "MG restart delay time."
        ::={a200mgcfgentry 21}

    a200mgip  OBJECT-TYPE
        SYNTAX       IpAddress
        MAX-ACCESS   read-create
        STATUS       current
        DESCRIPTION  
            "MG IP address."
        ::={a200mgcfgentry 22}
    
    a200mgmask  OBJECT-TYPE
        SYNTAX       IpAddress
        MAX-ACCESS   read-create
        STATUS       current
        DESCRIPTION  
            "IP Address mask"
        ::={a200mgcfgentry 23}
    
    a200mgRowStatus  OBJECT-TYPE
        SYNTAX       RowStatus
        MAX-ACCESS   read-create
        STATUS       current
        DESCRIPTION  
            "Insert, delete, update"
        ::={a200mgcfgentry 24}
        
    a200mgPSTNMediaVoiceTos  OBJECT-TYPE
        SYNTAX       INTEGER
            {
                typeCommon(0),
                typeMinFee(1),
                typeMaxSecurity(2),
                typeMaxThruput(4),
                typeMinDelay(8)
            }
        MAX-ACCESS   read-create
        STATUS       current
        DESCRIPTION  
            "PSTN media voice ToS."
        ::={a200mgcfgentry 25}
        
    a200mgPSTNMediaFaxTos  OBJECT-TYPE
        SYNTAX       INTEGER
            {
                typeCommon(0),
                typeMinFee(1),
                typeMaxSecurity(2),
                typeMaxThruput(4),
                typeMinDelay(8)
            }
        MAX-ACCESS   read-create
        STATUS       current
        DESCRIPTION  
            "PSTN media fax ToS."
        ::={a200mgcfgentry 26}
        
    a200mgPSTNMediaModemTos  OBJECT-TYPE
        SYNTAX       INTEGER
            {
                typeCommon(0),
                typeMinFee(1),
                typeMaxSecurity(2),
                typeMaxThruput(4),
                typeMinDelay(8)
            }
        MAX-ACCESS   read-create
        STATUS       current
        DESCRIPTION  
            "PSTN media modem ToS."
        ::={a200mgcfgentry 27}
        
    a200mgPSTNMediaDataTos  OBJECT-TYPE
        SYNTAX       INTEGER
            {
                typeCommon(0),
                typeMinFee(1),
                typeMaxSecurity(2),
                typeMaxThruput(4),
                typeMinDelay(8)
            }
        MAX-ACCESS   read-create
        STATUS       current
        DESCRIPTION  
            "PSTN media data ToS."
        ::={a200mgcfgentry 28}
        
    a200mgSigTos  OBJECT-TYPE
        SYNTAX       INTEGER
            {
                typeCommon(0),
                typeMinFee(1),
                typeMaxSecurity(2),
                typeMaxThruput(4),
                typeMinDelay(8)
            }
        MAX-ACCESS   read-create
        STATUS       current
        DESCRIPTION  
            "Signal ToS."
        ::={a200mgcfgentry 29}
        
    a200mgISTNMediaVoiceTos  OBJECT-TYPE
        SYNTAX       INTEGER
            {
                typeCommon(0),
                typeMinFee(1),
                typeMaxSecurity(2),
                typeMaxThruput(4),
                typeMinDelay(8)
            }
        MAX-ACCESS   read-create
        STATUS       current
        DESCRIPTION  
            "ISTN media voice ToS."
        ::={a200mgcfgentry 30}
        
    a200mgISTNMediaFaxTos  OBJECT-TYPE
        SYNTAX       INTEGER
            {
                typeCommon(0),
                typeMinFee(1),
                typeMaxSecurity(2),
                typeMaxThruput(4),
                typeMinDelay(8)
            }
        MAX-ACCESS   read-create
        STATUS       current
        DESCRIPTION  
            "ISTN media fax ToS."
        ::={a200mgcfgentry 31}
        
    a200mgISTNMediaModemTos  OBJECT-TYPE
        SYNTAX       INTEGER
            {
                typeCommon(0),
                typeMinFee(1),
                typeMaxSecurity(2),
                typeMaxThruput(4),
                typeMinDelay(8)
            }
        MAX-ACCESS   read-create
        STATUS       current
        DESCRIPTION    
            "ISTN media modem ToS."
        ::={a200mgcfgentry 32}
        
    a200mgISTNMediaDataTos  OBJECT-TYPE
        SYNTAX       INTEGER
            {
                typeCommon(0),
                typeMinFee(1),
                typeMaxSecurity(2),
                typeMaxThruput(4),
                typeMinDelay(8)
            }
        MAX-ACCESS   read-create
        STATUS       current
        DESCRIPTION    
            "ISTN media data ToS."
        ::={a200mgcfgentry 33}
        
    a200mgDomainName  OBJECT-TYPE
        SYNTAX       DisplayString(SIZE(0..80))
        MAX-ACCESS   read-create
        STATUS       current
        DESCRIPTION   
            "Domain Name."
        ::={a200mgcfgentry 34}
        
    a200mgInfo  OBJECT-TYPE
        SYNTAX       INTEGER
            {
                useIp(0),
                useDomain(1),
                useMacAsDomain(2),
                ipsIdle(4),
                englishTone(128)
            }
        MAX-ACCESS   read-create
        STATUS       current
        DESCRIPTION    
            "MG information."
        ::={a200mgcfgentry 35}
        
    a200mgcid2      OBJECT-TYPE
        SYNTAX       Integer32(1..255)
        MAX-ACCESS   read-create
        STATUS       current
        DESCRIPTION  
            "MGC ID 2."
        ::={a200mgcfgentry 36}
        
    a200mgcid3      OBJECT-TYPE
        SYNTAX       Integer32(1..255)
        MAX-ACCESS   read-create
        STATUS       current
        DESCRIPTION    
            "MGC ID 3."
        ::={a200mgcfgentry 37}
        
    a200mgcid4      OBJECT-TYPE
        SYNTAX       Integer32(1..255)
        MAX-ACCESS   read-create
        STATUS       current
        DESCRIPTION  
            "MGC ID 4."
        ::={a200mgcfgentry 38}
        
    a200rtpFaxPri1  OBJECT-TYPE
        SYNTAX       INTEGER
            {
                vbd(1),
                t38(2)
            }
        MAX-ACCESS   read-create
        STATUS       current
        DESCRIPTION  
            "RTP fax priority 1."
        ::={a200mgcfgentry 39}
        
    a200rtpFaxPri2  OBJECT-TYPE
        SYNTAX       INTEGER
            {
                vbd(1),
                t38(2)
            }
        MAX-ACCESS   read-create
        STATUS       current
        DESCRIPTION  
            "RTP fax priority 2."
        ::={a200mgcfgentry 40}
        
    a200rtpFaxPri3  OBJECT-TYPE
        SYNTAX       INTEGER
            {
                vbd(1),
                t38(2)
            }
        MAX-ACCESS   read-create
        STATUS       current
        DESCRIPTION  
            "RTP fax priority 3."
        ::={a200mgcfgentry 41}
        
    a200rtpFaxPri4  OBJECT-TYPE
        SYNTAX       INTEGER
            {
                vbd(1),
                t38(2)
            }
        MAX-ACCESS   read-create
        STATUS       current
        DESCRIPTION  
            "RTP fax priority 3."
        ::={a200mgcfgentry 42}
        
    a200rtp2833Type  OBJECT-TYPE
        SYNTAX       INTEGER
            { 
                type2833Redun(1),
                typeRTP(2),
                type2833NoRedun(3) 
             }
        MAX-ACCESS   read-create
        STATUS       current
        DESCRIPTION    
            "RTP 2833 type."
        ::={a200mgcfgentry 43}
        
    a200callParaFo  OBJECT-TYPE
        SYNTAX       Integer32(0..1)
        MAX-ACCESS   read-create
        STATUS       current
        DESCRIPTION   
            "Call parameter forward."
        ::={a200mgcfgentry 44}
        
    a200callNumRcv  OBJECT-TYPE
        SYNTAX       Integer32(0..1)
        MAX-ACCESS   read-create
        STATUS       current
        DESCRIPTION    
            "Call parameter received."
        ::={a200mgcfgentry 45}
        
    a200softPara  OBJECT-TYPE
        SYNTAX       Integer32(0..255)
        MAX-ACCESS   read-create
        STATUS       current
        DESCRIPTION  
            "Soft parameter."
        ::={a200mgcfgentry 46}
        
    a200ipsThreshold  OBJECT-TYPE
        SYNTAX       Integer32(1..100)
        MAX-ACCESS   read-create
        STATUS       current
        DESCRIPTION  
            "IPS threshold."
        ::={a200mgcfgentry 47}
        
    a200selfexchange  OBJECT-TYPE
        SYNTAX       INTEGER
            {
                disable(0),
                enable(1)
            }
        MAX-ACCESS   read-create
        STATUS       current
        DESCRIPTION  
            "Enable/disable Self-exchange."
        ::={a200mgcfgentry 48}
            
    a200protectcall  OBJECT-TYPE
        SYNTAX       INTEGER
            {
                disable(0),
                enable(1)
            }
        MAX-ACCESS   read-create
        STATUS       current
        DESCRIPTION  
            "Enable/disable call protection."
        ::={a200mgcfgentry 49}
        
    a200calllimit  OBJECT-TYPE
        SYNTAX       INTEGER
            {
                disable(0),
                enable(1)
            }
        MAX-ACCESS   read-create
        STATUS       current
        DESCRIPTION    
            "Enable/disable call limit."
        ::={a200mgcfgentry 50}
        
    a200callmatchtype  OBJECT-TYPE
        SYNTAX       INTEGER
            {
                longmatch(1),
                shortmatch(2)
            }
        MAX-ACCESS   read-create
        STATUS       current
        DESCRIPTION    
            "Call match type."
        ::={a200mgcfgentry 51}
        
    a200FAX_CNG_TONE  OBJECT-TYPE
        SYNTAX       INTEGER
            {
                notreport(0),
                report(1)
            }
        MAX-ACCESS   read-create
        STATUS       current
        DESCRIPTION  
            "Fax tone."
        ::={a200mgcfgentry 52}
        
    a200V21_FLAGS_TONE  OBJECT-TYPE
        SYNTAX       INTEGER
            {
                notreport(0),
                report(1)
            }
        MAX-ACCESS   read-create
        STATUS       current
        DESCRIPTION    
            "Flags tone."
        ::={a200mgcfgentry 53}
        
    a200T38_FAX_END  OBJECT-TYPE
        SYNTAX       INTEGER
            {
                notreport(0),
                report(1)
            }
        MAX-ACCESS   read-create
        STATUS       current
        DESCRIPTION    
            "T38 fax end."
        ::={a200mgcfgentry 54}
        
    a200ANSamWI_TONE  OBJECT-TYPE
        SYNTAX       INTEGER
            {
                notreport(0),
                report(1)
            }
        MAX-ACCESS   read-create
        STATUS       current
        DESCRIPTION    
            ""
        ::={a200mgcfgentry 55}
        
    a200ANSamWO_TONE  OBJECT-TYPE
        SYNTAX       INTEGER
            {
                notreport(0),
                report(1)
            }
        MAX-ACCESS   read-create
        STATUS       current
        DESCRIPTION    ""
        ::={a200mgcfgentry 56}
        
    a200ANSWI_TONE  OBJECT-TYPE
        SYNTAX       INTEGER
            {
                notreport(0),
                report(1)
            }
        MAX-ACCESS   read-create
        STATUS       current
        DESCRIPTION    ""
        ::={a200mgcfgentry 57}
        
    a200ANSWO_TONE  OBJECT-TYPE
        SYNTAX       INTEGER
            {
                notreport(0),
                report(1)
            }
        MAX-ACCESS   read-create
        STATUS       current
        DESCRIPTION    ""
        ::={a200mgcfgentry 58}

    a200disasterprot  OBJECT-TYPE
        SYNTAX      INTEGER
            {
                disble(0),
                enable(1)
            }
        MAX-ACCESS  read-create
        STATUS      current
        DESCRIPTION 
            "Enable/disable disaster protection."
        ::={a200mgcfgentry 59}

    a200currentmgcid  OBJECT-TYPE
        SYNTAX      Integer32(0..4)
        MAX-ACCESS  read-create
        STATUS      current
        DESCRIPTION 
            "Current MGC ID."
        ::={a200mgcfgentry 60}
        
    a200MgReversePolarityControlMode  OBJECT-TYPE
        SYNTAX      INTEGER
            {
                bySs(1),
                byMg(2)
            }
        MAX-ACCESS  read-create
        STATUS      current
        DESCRIPTION 
            "Reverse polarity control mode."
        ::={a200mgcfgentry 61}
    
    a200MgCongestionToneTimeOut  OBJECT-TYPE
        SYNTAX      Integer32(10..20)
        UNITS       "seconds"
        MAX-ACCESS  read-create
        STATUS      current
        DESCRIPTION 
            "Congetstion tone time out."
        DEFVAL  { 10 }
        ::={a200mgcfgentry 62}

        
--end of mgcfg table

--mgccfg table definition begin
   a200mgccfgTable OBJECT-TYPE
        SYNTAX        SEQUENCE OF A200MgccfgEntry
        MAX-ACCESS    not-accessible
        STATUS      current
        DESCRIPTION    "\u5a92\u4f53\u7f51\u5173\u63a7\u5236\u5668\uff08MGC\uff09\u914d\u7f6e\u4fe1\u606f"
        ::={a200-mib 2}

   a200mgccfgentry OBJECT-TYPE
        SYNTAX        A200MgccfgEntry
        MAX-ACCESS    not-accessible
        STATUS      current
        DESCRIPTION    "colunms and index of mgcfg table"
        INDEX {a200mgcmgcid}
        ::={a200mgccfgTable 1}
    
    A200MgccfgEntry::=
        SEQUENCE{
            a200mgcmgcid         Integer32,
            a200mgcport1         Integer32,
            a200mgcport2         Integer32,
            a200mgcport3         Integer32,
            a200mgcport4         Integer32,
            a200mgcip1           IpAddress,
            a200mgcip2           IpAddress,
            a200mgcip3           IpAddress,
            a200mgcip4           IpAddress,            
            a200mgcRowStatus     RowStatus,
            a200mgcdomain1       DisplayString,
            a200mgcdomain2       DisplayString,
            a200mgcdomain3       DisplayString,
            a200mgcdomain4       DisplayString,
            a200mgctypeid        INTEGER,
            a200mgcMD5Info1      INTEGER,
            a200mgcMD5Info2      INTEGER,
            a200mgcMD5Info3      INTEGER,
            a200mgcMD5Info4      INTEGER,
            a200mgcinfo          INTEGER
            }


    a200mgcmgcid  OBJECT-TYPE
        SYNTAX        Integer32
        MAX-ACCESS    not-accessible
        STATUS        current
        DESCRIPTION   "MGC ID"
        ::={a200mgccfgentry 1}


    a200mgcport1  OBJECT-TYPE
        SYNTAX        Integer32
        MAX-ACCESS    read-create
        STATUS        current
        DESCRIPTION   
            "MGC port"
        ::={a200mgccfgentry 2}
       
    a200mgcport2   OBJECT-TYPE
        SYNTAX        Integer32
        MAX-ACCESS    not-accessible
        STATUS        current
        DESCRIPTION   
            "MGC port"
        ::={a200mgccfgentry 3}

    a200mgcport3   OBJECT-TYPE
        SYNTAX        Integer32
        MAX-ACCESS    not-accessible
        STATUS        current
        DESCRIPTION   
            "MGC port"
        ::={a200mgccfgentry 4}

    a200mgcport4   OBJECT-TYPE
        SYNTAX        Integer32
        MAX-ACCESS    not-accessible
        STATUS        current
        DESCRIPTION   
            "MGC port"
        ::={a200mgccfgentry 5}

    a200mgcip1   OBJECT-TYPE
        SYNTAX        IpAddress
        MAX-ACCESS    read-create
        STATUS        current
        DESCRIPTION  
            "MGC IP address"
        ::={a200mgccfgentry 6}
      
    a200mgcip2   OBJECT-TYPE
        SYNTAX        IpAddress
        MAX-ACCESS    not-accessible
        STATUS        current
        DESCRIPTION   
            "MGC IP address"
        ::={a200mgccfgentry 7}

    a200mgcip3   OBJECT-TYPE
        SYNTAX        IpAddress
        MAX-ACCESS    not-accessible
        STATUS        current
        DESCRIPTION   
            "MGC IP address"
        ::={a200mgccfgentry 8}

    a200mgcip4   OBJECT-TYPE
        SYNTAX        IpAddress
        MAX-ACCESS    not-accessible
        STATUS        current
        DESCRIPTION   
            "MGC IP address"
        ::={a200mgccfgentry 9}
        
    a200mgcRowStatus   OBJECT-TYPE
        SYNTAX        RowStatus
        MAX-ACCESS    read-create
        STATUS        current
        DESCRIPTION   
            "Insert, delete, update"
        ::={a200mgccfgentry 10}
        
    a200mgcdomain1   OBJECT-TYPE
        SYNTAX        DisplayString (SIZE (0..32))
        MAX-ACCESS    read-create
        STATUS        current
        DESCRIPTION   ""
        ::={a200mgccfgentry 11}
        
    a200mgcdomain2   OBJECT-TYPE
        SYNTAX        DisplayString (SIZE (0..32))
        MAX-ACCESS    not-accessible
        STATUS        current
        DESCRIPTION   ""
        ::={a200mgccfgentry 12}
        
    a200mgcdomain3   OBJECT-TYPE
        SYNTAX        DisplayString (SIZE (0..32))
        MAX-ACCESS    not-accessible
        STATUS        current
        DESCRIPTION   ""
        ::={a200mgccfgentry 13}
        
    a200mgcdomain4   OBJECT-TYPE
        SYNTAX        DisplayString (SIZE (0..32))
        MAX-ACCESS    not-accessible
        STATUS        current
        DESCRIPTION   ""
        ::={a200mgccfgentry 14}
        
    a200mgctypeid   OBJECT-TYPE
        SYNTAX        INTEGER
        {
            zte(1),
            hw(2),
            cisco(3),
            alcatel(4),
            nortel_mgcp(5),
            nortel_h248(6),
            ericsson(7)
        }
        MAX-ACCESS    read-create
        STATUS        current
        DESCRIPTION   
            "This object indicates the SS type."
        ::={a200mgccfgentry 15}
        
    a200mgcMD5Info1   OBJECT-TYPE
        SYNTAX        INTEGER(0..10)
        MAX-ACCESS    read-create
        STATUS        current
        DESCRIPTION   ""
        ::={a200mgccfgentry 16}
        
    a200mgcMD5Info2   OBJECT-TYPE
        SYNTAX        INTEGER(0..10)
        MAX-ACCESS    not-accessible
        STATUS        current
        DESCRIPTION   ""
        ::={a200mgccfgentry 17}
        
    a200mgcMD5Info3   OBJECT-TYPE
        SYNTAX        INTEGER(0..10)
        MAX-ACCESS    not-accessible
        STATUS        current
        DESCRIPTION   ""
        ::={a200mgccfgentry 18}
        
    a200mgcMD5Info4   OBJECT-TYPE
        SYNTAX        INTEGER(0..10)
        MAX-ACCESS    not-accessible
        STATUS        current
        DESCRIPTION   ""
        ::={a200mgccfgentry 19}
        
    a200mgcinfo   OBJECT-TYPE
        SYNTAX        INTEGER{use_ip(1),use_domain(2)}
        MAX-ACCESS    read-create
        STATUS        current
        DESCRIPTION   ""
        ::={a200mgccfgentry 20}
        
--end of mgccfg table

--Rack table definition begin
   a200rackTable OBJECT-TYPE
        SYNTAX        SEQUENCE OF A200RackEntry
        MAX-ACCESS    not-accessible
        STATUS      current
        DESCRIPTION    "\u673a\u67b6\u914d\u7f6e\u8868\uff0c\u63cf\u8ff0\u8bbe\u5907\u4e2d\u673a\u67b6\u914d\u7f6e\u4fe1\u606f"
        ::={a200-mib 3}

   a200rackentry OBJECT-TYPE
        SYNTAX        A200RackEntry
        MAX-ACCESS    not-accessible
        STATUS      current
        DESCRIPTION    "colunms and index of rack table"
        INDEX {a200rackno}
        ::={a200rackTable 1}
    
    A200RackEntry::=
        SEQUENCE{
            a200rackno          INTEGER, 
            a200racktype        INTEGER,
            a200rackmaxshelfnum INTEGER,
            a200rackRowStatus   RowStatus
            }

   a200rackno OBJECT-TYPE
        SYNTAX       INTEGER
        MAX-ACCESS   not-accessible
        STATUS       current
        DESCRIPTION    "\u673a\u67b6\u53f7"
        ::={a200rackentry 1}

   a200racktype OBJECT-TYPE
        SYNTAX        INTEGER
        MAX-ACCESS  read-write
        STATUS      current
        DESCRIPTION    "\u673a\u67b6\u7c7b\u578b"
        ::={a200rackentry 2}
        
    a200rackmaxshelfnum   OBJECT-TYPE
        SYNTAX        INTEGER
        MAX-ACCESS  read-only
        STATUS      current
        DESCRIPTION    "\u672c\u673a\u67b6\u4e2d\u6700\u5927\u53ef\u914d\u7f6e\u673a\u6846\u6570"
        ::={a200rackentry 3}

    a200rackRowStatus   OBJECT-TYPE
        SYNTAX        RowStatus
        MAX-ACCESS  read-create
        STATUS      current
        DESCRIPTION    "insert,delete"
        ::={a200rackentry 4}
--end of racktable

--shelf table begin
   a200shelfTable OBJECT-TYPE
        SYNTAX        SEQUENCE OF A200ShelfEntry
        MAX-ACCESS    not-accessible
        STATUS      current
        DESCRIPTION    "\u673a\u6846\u914d\u7f6e\u8868\uff0c\u63cf\u8ff0\u8bbe\u5907\u4e2d\u673a\u6846\u914d\u7f6e\u4fe1\u606f"
        ::={a200-mib 4}

   a200ShelfEntry OBJECT-TYPE
        SYNTAX        A200ShelfEntry
        MAX-ACCESS    not-accessible
        STATUS      current
        DESCRIPTION    "describe colunms and index in shelf table"
        INDEX {a200shelfrackno,a200shelfno}
        ::={a200shelfTable 1}
        
   A200ShelfEntry::=
           SEQUENCE{
               a200shelfrackno        INTEGER,
               a200shelfno            INTEGER,
               a200shelftype        A200ShelfTypes,
               a200shelfmaxslotnum         INTEGER,
               a200shelfRowStatus          RowStatus
             
               }
               
   a200shelfrackno    OBJECT-TYPE
        SYNTAX        INTEGER
        MAX-ACCESS  not-accessible
        STATUS      current
        DESCRIPTION    "\u673a\u6846\u6240\u5728\u7684\u673a\u67b6\u53f7"
        ::={a200ShelfEntry 1}        

   a200shelfno    OBJECT-TYPE
        SYNTAX        INTEGER
        MAX-ACCESS  not-accessible
        STATUS      current
        DESCRIPTION    "\u673a\u6846\u53f7"
        ::={a200ShelfEntry 2}        

   a200shelftype    OBJECT-TYPE
        SYNTAX        A200ShelfTypes
        MAX-ACCESS  read-create
        STATUS      current
        DESCRIPTION    "\u673a\u6846\u7c7b\u578b"
        ::={a200ShelfEntry 3}

   a200shelfmaxslotnum  OBJECT-TYPE
        SYNTAX        INTEGER
        MAX-ACCESS  read-only
        STATUS      current
        DESCRIPTION    "\u672c\u673a\u6846\u4e2d\u6700\u5927\u69fd\u4f4d\u6570"
        ::={a200ShelfEntry 4}        

   a200shelfRowStatus   OBJECT-TYPE
        SYNTAX        RowStatus
        MAX-ACCESS  read-create
        STATUS      current
        DESCRIPTION    "insert,delete"
        ::={a200ShelfEntry 5}
        
      
   

--end of shelf table
        
--board table begin    
   a200boardTable OBJECT-TYPE
        SYNTAX        SEQUENCE OF A200BoardEntry
        MAX-ACCESS    not-accessible
        STATUS      current
        DESCRIPTION    "\u7535\u8def\u677f\u914d\u7f6e\u8868\uff0c\u63cf\u8ff0\u8bbe\u5907\u4e2d\u914d\u7f6e\u7684\u7535\u8def\u677f\u4fe1\u606f"
        ::={a200-mib 5}

   a200boardentry OBJECT-TYPE
        SYNTAX        A200BoardEntry
        MAX-ACCESS    not-accessible
        STATUS      current
        DESCRIPTION    "describe colunms and index in board table"
        INDEX {a200boardrackno,a200boardshelfno,a200boardslotno}
        ::={a200boardTable 1}
        
   A200BoardEntry::=
       SEQUENCE{
           a200boardrackno       INTEGER,
           a200boardshelfno      INTEGER,
           a200boardslotno     INTEGER,
        a200boardline485     INTEGER,
        a200boardtype     A200BoardTypes,
        a200boardaddr485     INTEGER,
        a200boardstatus      INTEGER,
        a200boardnum         INTEGER,
        a200boardslcseqno    DisplayString
        }
        
    a200boardrackno  OBJECT-TYPE
        SYNTAX        INTEGER
        MAX-ACCESS  not-accessible
        STATUS      current
        DESCRIPTION    "\u7535\u8def\u677f\u6240\u5728\u673a\u67b6\u53f7"
        ::={a200boardentry 1}
        
    a200boardshelfno OBJECT-TYPE
        SYNTAX        INTEGER
        MAX-ACCESS  not-accessible
        STATUS      current
        DESCRIPTION    "\u7535\u8def\u677f\u6240\u5728\u673a\u6846\u53f7"
        ::={a200boardentry 2}

    a200boardslotno     OBJECT-TYPE
        SYNTAX        INTEGER
        MAX-ACCESS  not-accessible
        STATUS      current
        DESCRIPTION    "\u7535\u8def\u677f\u6240\u5728\u69fd\u4f4d\u53f7"
        ::={a200boardentry 3}

        a200boardline485  OBJECT-TYPE
        SYNTAX        INTEGER
        MAX-ACCESS  read-only
        STATUS      current
        DESCRIPTION    "RS485\u603b\u7ebf\u53f7"
        ::={a200boardentry 4}
        
    a200boardtype    OBJECT-TYPE
        SYNTAX        A200BoardTypes
        MAX-ACCESS  read-only
        STATUS      current
        DESCRIPTION    "\u7535\u8def\u677f\u7c7b\u578b"
        ::={a200boardentry 5}

      a200boardaddr485  OBJECT-TYPE
        SYNTAX        INTEGER
        MAX-ACCESS  read-only
        STATUS      current
        DESCRIPTION    "RS485\u5730\u5740"
        ::={a200boardentry 6}

      a200boardstatus   OBJECT-TYPE
        SYNTAX        INTEGER
        MAX-ACCESS  read-only
        STATUS      current
        DESCRIPTION    "\u7535\u8def\u677f\u72b6\u6001 =0\uff1a\u79bb\u7ebf
                      =1\uff1a\u4eba\u5de5\u95ed\u585e
                      =2\uff1a\u5907\u7528
                      =3\uff1a\u4e3b\u7528"
        ::={a200boardentry 7}

      a200boardnum  OBJECT-TYPE
        SYNTAX        INTEGER
        MAX-ACCESS  read-only
        STATUS      current
        DESCRIPTION    "\u5355\u677f\u6240\u5360\u69fd\u4f4d\u6570"
        ::={a200boardentry 8}
      a200boardslcseqno     OBJECT-TYPE
        SYNTAX        DisplayString(SIZE(0..12))
        MAX-ACCESS  read-write
        STATUS      current
        DESCRIPTION    ""
        ::={a200boardentry 9}
--end of board table 

--subdev table begin    
   a200subdevTable OBJECT-TYPE
        SYNTAX        SEQUENCE OF A200SubdevEntry
        MAX-ACCESS    not-accessible
        STATUS      current
        DESCRIPTION    "\u7535\u8def\u677f\u5185\u5b50\u8bbe\u5907\u63cf\u8ff0\u8868,\u63cf\u8ff0\u677f\u5185\u5b50\u8bbe\u5907\u7c7b\u578b\u3001\u72b6\u6001"
        ::={a200-mib 6}

   a200subdeventry OBJECT-TYPE
        SYNTAX        A200SubdevEntry
        MAX-ACCESS    not-accessible
        STATUS      current
        DESCRIPTION    "describe colunms and index in subdev table"
        INDEX {a200boardrackno,a200boardshelfno,a200boardslotno,a200subdevno}
        ::={a200subdevTable 1}
        
   A200SubdevEntry::=
        SEQUENCE{
        a200subdevno      INTEGER,
        a200subdevtype      INTEGER,
        a200subdevstatus      INTEGER
        }
        
    a200subdevno  OBJECT-TYPE
        SYNTAX        INTEGER
        MAX-ACCESS  not-accessible
        STATUS      current
        DESCRIPTION    "\u5b50\u8bbe\u5907\u5728\u7535\u8def\u677f\u5185\u7684\u5e8f\u53f7"
        ::={a200subdeventry 1}

    a200subdevtype  OBJECT-TYPE
        SYNTAX        INTEGER
        MAX-ACCESS  read-only
        STATUS      current
        DESCRIPTION    "\u5b50\u8bbe\u5907\u7c7b\u578b"
        ::={a200subdeventry 2}

    a200subdevstatus  OBJECT-TYPE
        SYNTAX        INTEGER
        MAX-ACCESS  read-only
        STATUS      current
        DESCRIPTION    "\u5b50\u8bbe\u5907\u72b6\u6001\uff0c\u6309\u4f4d\u53d6\u503c"
        ::={a200subdeventry 3}
--end of subdev table 

--netseg table begin    
   a200netsegTable OBJECT-TYPE
        SYNTAX        SEQUENCE OF A200NetsegEntry
        MAX-ACCESS    not-accessible
        STATUS      current
        DESCRIPTION    "\u7f51\u6bb5\u914d\u7f6e\u8868\uff0c\u63cf\u8ff0\u8bbe\u5907\u4e2d\u5404\u7f51\u6bb5\u7684\u7f51\u7edc\u5730\u5740\u548c\u5b50\u7f51\u63a9\u7801"
        ::={a200-mib 7}

   a200netsegentry OBJECT-TYPE
        SYNTAX        A200NetsegEntry
        MAX-ACCESS    not-accessible
        STATUS      current
        DESCRIPTION    "describe colunms and index in netseg table"
        INDEX {a200iptype}
        ::={a200netsegTable 1}

   A200NetsegEntry::=
           SEQUENCE{
            a200innet            IpAddress,
            a200inmask           IpAddress,
            a200iptype           INTEGER,
            a200netsegRowStatus  RowStatus
            }           

       a200innet  OBJECT-TYPE
        SYNTAX       IpAddress
        MAX-ACCESS   read-create
        STATUS       current
        DESCRIPTION    "\u672c\u7f51\u6bb5\u7684\u7f51\u7edc\u5730\u5740"
        ::={a200netsegentry 1}    
       
       a200inmask  OBJECT-TYPE
        SYNTAX        IpAddress
        MAX-ACCESS  read-create
        STATUS      current
        DESCRIPTION    "\u672c\u7f51\u6bb5\u7684\u5b50\u7f51\u63a9\u7801"
        ::={a200netsegentry 2}    

       
       a200iptype    OBJECT-TYPE
        SYNTAX       INTEGER
        MAX-ACCESS   not-accessible
        STATUS       current
        DESCRIPTION    "\u672c\u7f51\u6bb5\u7684\u529f\u80fd\u7c7b\u578b\uff1a
                    =1: MP\u3001PP\u4e4b\u95f4\u901a\u8baf 
                    =2: \u5a92\u4f53\u6d41\u4f20\u8f93
                    =3: \u5916\u90e8IP\u7f51\u6bb5\uff08\u65e0\u4e3b\u5907\u7aef\u53e3\u7528\uff09"
        ::={a200netsegentry 3}    
        
       a200netsegRowStatus  OBJECT-TYPE
        SYNTAX        RowStatus
        MAX-ACCESS  read-create
        STATUS      current
        DESCRIPTION    "insert,delete,update"
        ::={a200netsegentry 4}            
--end of netseg table 

--ippool table begin    
   a200ippoolTable OBJECT-TYPE
        SYNTAX        SEQUENCE OF A200IpPoolEntry
        MAX-ACCESS    not-accessible
        STATUS      current
        DESCRIPTION    "IP\u5730\u5740\u914d\u7f6e\u8868\uff0c\u63cf\u8ff0\u914d\u7f6e\u5728\u7535\u8def\u677f\u4e2a\u7aef\u53e3\u4e0a\u7684IP\u5730\u5740"
        ::={a200-mib 8}

   a200ippoolentry OBJECT-TYPE
        SYNTAX        A200IpPoolEntry
        MAX-ACCESS    not-accessible
        STATUS      current
        DESCRIPTION    "describe colunms and index in ippool table"
        INDEX { a200ippoolipaddr }
        ::={a200ippoolTable 1}

   A200IpPoolEntry::=
           SEQUENCE{
            a200ippoolipaddr      IpAddress,
            a200ippoolipmask      IpAddress,
            a200ippooliptype      INTEGER,
            a200ippoolrackno      INTEGER,
            a200ippoolshelfno     INTEGER,
            a200ippoolslotno      INTEGER,
            a200ippoolphyport     INTEGER,
            a200ippoolipno        INTEGER,
            a200ippoolisused      INTEGER,
            a200ippoolRowStatus   RowStatus
            }           

    a200ippoolipaddr  OBJECT-TYPE
        SYNTAX       IpAddress
        MAX-ACCESS   not-accessible
        STATUS       current
        DESCRIPTION    "ip\u5730\u5740"
        ::={a200ippoolentry 1}    
      
    a200ippoolipmask  OBJECT-TYPE
        SYNTAX        IpAddress
        MAX-ACCESS  read-create
        STATUS      current
        DESCRIPTION    "ip\u5730\u5740\u5bf9\u5e94\u7684\u5b50\u7f51\u63a9\u7801"
        ::={a200ippoolentry 2}    
      
    a200ippooliptype  OBJECT-TYPE
        SYNTAX        INTEGER
        MAX-ACCESS  read-create
        STATUS      current
        DESCRIPTION    "ip\u5730\u5740\u7c7b\u578b\uff0c\u53d6\u503c\u540ca200iptype"
        ::={a200ippoolentry 3}    
    
    a200ippoolrackno  OBJECT-TYPE
        SYNTAX        INTEGER
        MAX-ACCESS  read-only
        STATUS      current
        DESCRIPTION    "ip\u5730\u5740\u6240\u5728\u7684\u7535\u8def\u677f\u6240\u5c5e\u7684\u673a\u67b6\u53f7"
        ::={a200ippoolentry 4}    
    
    a200ippoolshelfno   OBJECT-TYPE
        SYNTAX        INTEGER
        MAX-ACCESS  read-only
        STATUS      current
        DESCRIPTION    "ip\u5730\u5740\u6240\u5728\u7684\u7535\u8def\u677f\u6240\u5c5e\u7684\u673a\u6846\u53f7"
        ::={a200ippoolentry 5}    
  
    a200ippoolslotno  OBJECT-TYPE
        SYNTAX        INTEGER
        MAX-ACCESS  read-only
        STATUS      current
        DESCRIPTION    "ip\u5730\u5740\u6240\u5728\u7684\u7535\u8def\u677f\u7684\u69fd\u4f4d\u53f7"
        ::={a200ippoolentry 6}    
    
    a200ippoolphyport  OBJECT-TYPE
        SYNTAX        INTEGER
        MAX-ACCESS  read-only
        STATUS      current
        DESCRIPTION    "ip\u5730\u5740\u6240\u5728\u7684\u7aef\u53e3\u53f7"
        ::={a200ippoolentry 7}    

    a200ippoolipno    OBJECT-TYPE
        SYNTAX        INTEGER
        MAX-ACCESS  read-only
        STATUS      current
        DESCRIPTION    "\u540c\u4e00\u7aef\u53e3\u7684ip\u5730\u5740\u5e8f\u53f7"
        ::={a200ippoolentry 8}    

    a200ippoolisused   OBJECT-TYPE
        SYNTAX        INTEGER
        MAX-ACCESS  read-only
        STATUS      current
        DESCRIPTION    "ip\u72b6\u6001:   =0: \u7a7a\u95f2\uff0c  =1: \u4f7f\u7528"
        ::={a200ippoolentry 9}    
        
    a200ippoolRowStatus   OBJECT-TYPE
        SYNTAX        RowStatus
        MAX-ACCESS  read-create
        STATUS      current
        DESCRIPTION    "insert,delete"
        ::={a200ippoolentry 10}            
--end of ippool table 

--macpool table begin    
   a200macpoolTable OBJECT-TYPE
        SYNTAX        SEQUENCE OF A200MacPoolEntry
        MAX-ACCESS    not-accessible
        STATUS      current
        DESCRIPTION    "Mac\u5730\u5740\u914d\u7f6e\u8868\uff0c\u63cf\u8ff0\u914d\u7f6e\u5728\u7535\u8def\u677f\u4e2a\u7aef\u53e3\u4e0a\u7684Mac\u5730\u5740"
        ::={a200-mib 9}

   a200macpoolentry OBJECT-TYPE
        SYNTAX        A200MacPoolEntry
        MAX-ACCESS    not-accessible
        STATUS      current
        DESCRIPTION    "describe colunms and index in macpool table"
        INDEX { a200macpoolmacaddr }
        ::={a200macpoolTable 1}

   A200MacPoolEntry::=
           SEQUENCE{
               a200macpoolmacaddr MacAddress, 
               a200macpoolrackno  INTEGER,
               a200macpoolshelfno INTEGER,
               a200macpoolslotno  INTEGER,
               a200macpoolphyport INTEGER,
               a200macpoolisused  INTEGER,
               a200macpoolRowStatus  RowStatus
            }           
   
       a200macpoolmacaddr OBJECT-TYPE
        SYNTAX        MacAddress
        MAX-ACCESS  read-only
        STATUS      current
        DESCRIPTION    "Mac\u5730\u5740"
        ::={a200macpoolentry 1}    
 
       a200macpoolrackno  OBJECT-TYPE
        SYNTAX        INTEGER
        MAX-ACCESS  read-only
        STATUS      current
        DESCRIPTION    "Mac\u5730\u5740\u6240\u5728\u7684\u7535\u8def\u677f\u6240\u5c5e\u7684\u673a\u67b6\u53f7"
        ::={a200macpoolentry 2}    

       a200macpoolshelfno OBJECT-TYPE
        SYNTAX        INTEGER
        MAX-ACCESS  read-only
        STATUS      current
        DESCRIPTION    "Mac\u5730\u5740\u6240\u5728\u7684\u7535\u8def\u677f\u6240\u5c5e\u7684\u673a\u6846\u53f7"
        ::={a200macpoolentry 3}    

       a200macpoolslotno  OBJECT-TYPE
        SYNTAX        INTEGER
        MAX-ACCESS  read-only
        STATUS      current
        DESCRIPTION    "Mac\u5730\u5740\u6240\u5728\u7684\u7535\u8def\u677f\u7684\u69fd\u4f4d\u53f7"
        ::={a200macpoolentry 4}    

    a200macpoolphyport  OBJECT-TYPE
        SYNTAX        INTEGER
        MAX-ACCESS  read-only
        STATUS      current
        DESCRIPTION    "Mac\u5730\u5740\u6240\u5728\u7684\u7aef\u53e3\u53f7"
        ::={a200macpoolentry 5}    

       a200macpoolisused  OBJECT-TYPE
        SYNTAX        INTEGER
        MAX-ACCESS  read-only
        STATUS      current
        DESCRIPTION    "Mac\u5730\u5740\u72b6\u6001\uff1a  =0\uff1a\u7a7a\u95f2,  =1\uff1a\u4f7f\u7528"
        ::={a200macpoolentry 6}    

       a200macpoolRowStatus  OBJECT-TYPE
        SYNTAX        RowStatus
        MAX-ACCESS  read-create
        STATUS      current
        DESCRIPTION    "insert,delete"
        ::={a200macpoolentry 7}    
--end of macpool table 

--slc table begin    
   a200slcTable OBJECT-TYPE
        SYNTAX        SEQUENCE OF A200SlcEntry
        MAX-ACCESS    not-accessible
        STATUS      current
        DESCRIPTION    "\u7528\u6237\u7535\u8def\u8868\uff0c\u63cf\u8ff0\u7528\u6237\u7535\u8def\u7684\u72b6\u6001\uff0c\u53ca\u7535\u8def\u529f\u80fd\u914d\u7f6e"
        ::={a200-mib 10}

   a200slcentry OBJECT-TYPE
        SYNTAX        A200SlcEntry
        MAX-ACCESS    not-accessible
        STATUS      current
        DESCRIPTION    "describe colunms and index in slc table"
        INDEX { a200slcrackno, a200slcshelfno, 
                a200slcslotno, a200slcindex}
        ::={a200slcTable 1}

   A200SlcEntry::=
       SEQUENCE{
           a200slcindex                  INTEGER,
           a200slcpkg                    INTEGER,
           a200slcstatus                 INTEGER,
           a200slcdftevent               INTEGER,
           a200slcTerminationID          OCTET STRING,
           a200slcusermode               INTEGER,
           a200slcFaxMode                INTEGER,
           a200slcQovsId                 INTEGER,
           a200slcCIDType                INTEGER,
           a200slcMgId                   INTEGER,
           a200slcDigitLen               INTEGER,
           a200slcImType                 INTEGER,
           a200slcphonenum               DisplayString,
           a200slcecenable               INTEGER,
           a200slcuserclass              INTEGER,
           a200slcPktToPcmGain           INTEGER,
           a200slcPcmToPktGain           INTEGER,
           a200slcModEndIndex            INTEGER,
           a200slcmonitorflag            INTEGER,
           a200slcmonitoreerack          INTEGER,
           a200slcmonitoreeshelf         INTEGER,
           a200slcmonitoreeslot          INTEGER,
           a200slcmonitoreeindex         INTEGER,
           a200lockoutSlcTid             OCTET STRING,      
           a200slcrackno                 INTEGER,
           a200slcshelfno                INTEGER,           
       a200slcslotno                 INTEGER,           
           a200slcFeedCurrent            INTEGER
          }           

         
     a200slcindex    OBJECT-TYPE
        SYNTAX        INTEGER
        MAX-ACCESS  read-only
        STATUS      current
        DESCRIPTION    "\u7535\u8def\u5e8f\u53f7"
        ::={a200slcentry 1}    
  
    a200slcpkg    OBJECT-TYPE
        SYNTAX        INTEGER
        MAX-ACCESS  read-write
        STATUS      current
        DESCRIPTION    "\u7535\u8def\u652f\u6301\u7684\u5305\u7c7b\u578b\uff0c\u6309\u4f4d\u53d6\u503c"
        ::={a200slcentry 2}    
    
    a200slcstatus   OBJECT-TYPE
        SYNTAX        INTEGER
        MAX-ACCESS  read-only
        STATUS      current
        DESCRIPTION    "\u7535\u8def\u72b6\u6001\uff0c\u6309\u4f4d\u53d6\u503c"
        ::={a200slcentry 3}
  
    a200slcdftevent  OBJECT-TYPE
        SYNTAX        INTEGER(0..127)
        MAX-ACCESS  read-write
        STATUS      current
        DESCRIPTION    "\u7535\u8def\u7f3a\u7701\u68c0\u6d4b\u4e8b\u4ef6\u7c7b\u578b\uff0c\u6309\u4f4d\u53d6\u503c"
        ::={a200slcentry 4}    
        
    a200slcTerminationID  OBJECT-TYPE
        SYNTAX        OCTET STRING (SIZE (0..63))
        MAX-ACCESS  read-only
        STATUS      current
        DESCRIPTION    ""
        ::={a200slcentry 5}
        
    a200slcusermode     OBJECT-TYPE
        SYNTAX        INTEGER{
            usermode_idle(0),
            usermode_h248(1),
            usermode_zte_uni(2),
            usermode_v5(3),
            usermode_z(4),
            usermode_mgcp(5),
            usermode_zte_sni(6),
            usermode_v5_isdn(7),
            usermode_v5_ddn(8),
            usermode_sip(9)
        }
        MAX-ACCESS  read-only
        STATUS      current
        DESCRIPTION    ""
        ::={a200slcentry 6}    
        
    a200slcFaxMode     OBJECT-TYPE
        SYNTAX        INTEGER{
            t30(0),
            t38(1),
            rtp(2),
            fastMODEM(3),
            fastFAX(4),
            lowSpeedModem(5),
            ipModem(6),
            v34(13),
            highSpeedSwitch(14)
        }
        MAX-ACCESS  read-write
        STATUS      current
        DESCRIPTION    
            "Subscriber line circuit fax mode."
        ::={a200slcentry 7}
        
    a200slcQovsId     OBJECT-TYPE
        SYNTAX        INTEGER(1..5)
        MAX-ACCESS  read-write
        STATUS      current
        DESCRIPTION    ""
        ::={a200slcentry 8}
        
    a200slcCIDType     OBJECT-TYPE
        SYNTAX        INTEGER(1..5)
        MAX-ACCESS  read-write
        STATUS      current
        DESCRIPTION    ""
        ::={a200slcentry 9}
    
    a200slcMgId     OBJECT-TYPE
        SYNTAX        INTEGER(1..255)
        MAX-ACCESS  read-only
        STATUS      current
        DESCRIPTION    ""
        ::={a200slcentry 10}
    
    a200slcDigitLen OBJECT-TYPE
        SYNTAX        INTEGER(2..64)
        MAX-ACCESS  read-only
        STATUS      current
        DESCRIPTION    ""
        ::={a200slcentry 11}
                
    a200slcImType     OBJECT-TYPE
        SYNTAX        INTEGER
            {
                normal(0),
                bt3(3),
                etsi(4),
                bt5(5),
                ohm600(6),
                russia(7)
            }
        MAX-ACCESS  read-write
        STATUS      current
        DESCRIPTION    "Impedance type"
        ::={a200slcentry 12}

    a200slcphonenum     OBJECT-TYPE
        SYNTAX        DisplayString(SIZE(0..32))
        MAX-ACCESS  read-write
        STATUS      current
        DESCRIPTION    ""
        ::={a200slcentry 13}
                        
    a200slcecenable     OBJECT-TYPE
        SYNTAX        INTEGER{enable(1),disable(2),default(0)}
        MAX-ACCESS  read-write
        STATUS      current
        DESCRIPTION    ""
        ::={a200slcentry 14}                

    a200slcuserclass     OBJECT-TYPE
        SYNTAX        INTEGER{normal(0),vip(1)}
        MAX-ACCESS  read-write
        STATUS      current
        DESCRIPTION    ""
        ::={a200slcentry 15}
        
    a200slcPktToPcmGain  OBJECT-TYPE
        SYNTAX        INTEGER(-20..20)
        MAX-ACCESS  read-write
        STATUS      current
        DESCRIPTION    ""
        ::={a200slcentry 16}
        
    a200slcPcmToPktGain  OBJECT-TYPE
        SYNTAX        INTEGER(-20..20)
        MAX-ACCESS  read-write
        STATUS      current
        DESCRIPTION    ""
        ::={a200slcentry 17}
        
    a200slcModEndIndex  OBJECT-TYPE
        SYNTAX        INTEGER(0..31)
        MAX-ACCESS  read-write
        STATUS      current
        DESCRIPTION    ""                  
        ::={a200slcentry 18}  
        
    a200slcmonitorflag  OBJECT-TYPE
        SYNTAX        INTEGER(1..2)
        MAX-ACCESS  read-write
        STATUS      current
        DESCRIPTION    ""                  
        ::={a200slcentry 19}  
        
    a200slcmonitoreerack  OBJECT-TYPE
        SYNTAX        INTEGER(0..3)
        MAX-ACCESS  read-write
        STATUS      current
        DESCRIPTION    ""                  
        ::={a200slcentry 20}  
        
    a200slcmonitoreeshelf  OBJECT-TYPE
        SYNTAX        INTEGER(0..4)
        MAX-ACCESS  read-write
        STATUS      current
        DESCRIPTION    ""                  
        ::={a200slcentry 21}  
        
    a200slcmonitoreeslot  OBJECT-TYPE
        SYNTAX        INTEGER(0..17)
        MAX-ACCESS  read-write
        STATUS      current
        DESCRIPTION    ""                  
        ::={a200slcentry 22}  
        
    a200slcmonitoreeindex  OBJECT-TYPE
        SYNTAX        INTEGER(0..31)
        MAX-ACCESS  read-write
        STATUS      current
        DESCRIPTION    ""                  
        ::={a200slcentry 23}  

    a200lockoutSlcTid   OBJECT-TYPE
        SYNTAX        OCTET STRING(SIZE (0..63))
        MAX-ACCESS  read-only
        STATUS      current
        DESCRIPTION    ""                  
        ::={a200slcentry 24}
        
    a200slcrackno  OBJECT-TYPE
        SYNTAX        INTEGER
        MAX-ACCESS  not-accessible
        STATUS      current
        DESCRIPTION    "\u7535\u8def\u677f\u6240\u5728\u673a\u67b6\u53f7"
        ::={a200slcentry 25}
        
    a200slcshelfno OBJECT-TYPE
        SYNTAX        INTEGER
        MAX-ACCESS  not-accessible
        STATUS      current
        DESCRIPTION    "\u7535\u8def\u677f\u6240\u5728\u673a\u6846\u53f7"
        ::={a200slcentry 26}

    a200slcslotno     OBJECT-TYPE
        SYNTAX        INTEGER
        MAX-ACCESS  not-accessible
        STATUS      current
        DESCRIPTION    "\u7535\u8def\u677f\u6240\u5728\u69fd\u4f4d\u53f7"
        ::={a200slcentry 27}
    
    a200slcFeedCurrent   OBJECT-TYPE
        SYNTAX      INTEGER
            {
                curr25mA(1), 
                curr32mA(2), 
                curr40mA(3)
            }
        MAX-ACCESS  read-write
        STATUS      current
        DESCRIPTION "Feed current"
        DEFVAL      { curr25mA }
        ::={a200slcentry 28}
                      
--end of slc table 
                  

--ips table begin    
   a200ipsTable OBJECT-TYPE
        SYNTAX        SEQUENCE OF A200IpsEntry
        MAX-ACCESS    not-accessible
        STATUS      current
        DESCRIPTION    "ips\u7535\u8def\u63cf\u8ff0\u8868\uff0c\u63cf\u8ff0MG\u4e2dips\u7535\u8def\u7684\u72b6\u6001\u53ca\u5c5e\u6027"
        ::={a200-mib 12}

   a200ipsentry OBJECT-TYPE
        SYNTAX        A200IpsEntry
        MAX-ACCESS    not-accessible
        STATUS      current
        DESCRIPTION    "describe colunms and index in slc table"
        INDEX { a200ipsrackno, a200ipsshelfno, 
                a200ipsslotno, a200ipsubdevno, a200ipsindex}
        ::={a200ipsTable 1}

    A200IpsEntry::=
           SEQUENCE{
            a200ipsubdevno       INTEGER,
            a200ipsindex      INTEGER,
            a200ipsstatus      INTEGER,
            a200ipspkg          Unsigned32,
                    a200ipsmuxtype      INTEGER,
            a200ipsmodmtype      INTEGER,
            a200ipslpt          Unsigned32,
            a200ipsrpt         Unsigned32,
            a200ipslptimmin      INTEGER,
            a200ipslptimmax      INTEGER,
            a200ipsrptimmin      INTEGER,
            a200ipsrptimmax      INTEGER,
            a200ipstmmdtyp      INTEGER,
            a200ipscallerid      INTEGER,
            a200ipsTerminationID OCTET STRING,
            a200ipsmgid          INTEGER,
            a200ipsDigitLen      INTEGER,
            a200ipsrackno        INTEGER,
            a200ipsshelfno       INTEGER,            
            a200ipsslotno        INTEGER     
            }           

        a200ipsubdevno       OBJECT-TYPE
        SYNTAX        INTEGER
        MAX-ACCESS  not-accessible
        STATUS      current
        DESCRIPTION    "ips\u7535\u8def\u6240\u5728\u7684\u677f\u5185\u5b50\u8bbe\u5907\u7f16\u53f7"
        ::={a200ipsentry 1}    

        a200ipsindex        OBJECT-TYPE
        SYNTAX        INTEGER
        MAX-ACCESS  not-accessible
        STATUS      current
        DESCRIPTION    "ips\u7535\u8def\u5728\u677f\u5185\u5b50\u8bbe\u5907\u4e2d\u7684\u5e8f\u53f7"
        ::={a200ipsentry 2}    
 
        a200ipsstatus     OBJECT-TYPE
        SYNTAX        INTEGER
        MAX-ACCESS  read-only
        STATUS      current
        DESCRIPTION    "\u7535\u8def\u72b6\u6001\uff0c\u6309\u4f4d\u53d6\u503c"
        ::={a200ipsentry 3}    
 
        a200ipspkg         OBJECT-TYPE
        SYNTAX        Unsigned32
        MAX-ACCESS  read-only
        STATUS      current
        DESCRIPTION    "\u7535\u8def\u652f\u6301\u7684\u5305\u7c7b\u578b\uff0c\u6309\u4f4d\u53d6\u503c"
        ::={a200ipsentry 4}    
 
    a200ipsmuxtype     OBJECT-TYPE
        SYNTAX        INTEGER
        MAX-ACCESS  read-write
        STATUS      current
        DESCRIPTION    "\u590d\u7528\u7c7b\u578b"
        ::={a200ipsentry 5}    
 
    a200ipsmodmtype OBJECT-TYPE
        SYNTAX        INTEGER
        MAX-ACCESS  read-only
        STATUS      current
        DESCRIPTION    "Modem\u7c7b\u578b"
        ::={a200ipsentry 6}    
 
        a200ipslpt         OBJECT-TYPE
        SYNTAX        Unsigned32
        MAX-ACCESS  read-only
        STATUS      current
        DESCRIPTION    "\u7535\u8def\u652f\u6301\u7684\u63a5\u6536\uff08\u672c\u7aef\uff09\u51c0\u8377\u7c7b\u578b\uff0c\u6309\u4f4d\u53d6\u503c"
        ::={a200ipsentry 7}    
 
    a200ipsrpt        OBJECT-TYPE
        SYNTAX        Unsigned32
        MAX-ACCESS  read-only
        STATUS      current
        DESCRIPTION    "\u7535\u8def\u652f\u6301\u7684\u53d1\u9001\uff08\u8fdc\u7aef\uff09\u51c0\u8377\u7c7b\u578b\uff0c\u6309\u4f4d\u53d6\u503c"
        ::={a200ipsentry 8}    
 
        a200ipslptimmin OBJECT-TYPE
        SYNTAX        INTEGER
        MAX-ACCESS  read-write
        STATUS      current
        DESCRIPTION    "\u63a5\u6536\uff08\u672c\u7aef\uff09\u7aef\u53e3\u6253\u5305\u65f6\u957f\u6700\u5c0f\u503c"
        ::={a200ipsentry 9}    
 
    a200ipslptimmax OBJECT-TYPE
        SYNTAX        INTEGER
        MAX-ACCESS  read-write
        STATUS      current
        DESCRIPTION    "\u63a5\u6536\uff08\u672c\u7aef\uff09\u7aef\u53e3\u6253\u5305\u65f6\u957f\u6700\u5927\u503c"
        ::={a200ipsentry 10}    
 
    a200ipsrptimmin OBJECT-TYPE
        SYNTAX        INTEGER
        MAX-ACCESS  read-write
        STATUS      current
        DESCRIPTION    "\u53d1\u9001\uff08\u8fdc\u7aef\uff09\u7aef\u53e3\u6253\u5305\u65f6\u957f\u6700\u5c0f\u503c"
        ::={a200ipsentry 11}    
 
    a200ipsrptimmax OBJECT-TYPE
        SYNTAX        INTEGER
        MAX-ACCESS  read-write
        STATUS      current
        DESCRIPTION    "\u53d1\u9001\uff08\u8fdc\u7aef\uff09\u7aef\u53e3\u6253\u5305\u65f6\u957f\u6700\u5927\u503c"
        ::={a200ipsentry 12}    
 
        a200ipstmmdtyp     OBJECT-TYPE
        SYNTAX        INTEGER
        MAX-ACCESS  read-only
        STATUS      current
        DESCRIPTION    "\u5a92\u4f53\u7c7b\u578b"
        ::={a200ipsentry 13}    

        a200ipscallerid OBJECT-TYPE
        SYNTAX        INTEGER
        MAX-ACCESS  read-only
        STATUS      current
        DESCRIPTION    "\u662f\u5426\u652f\u6301\u6765\u7535\u663e\u793a\uff0c
                =0: \u4e0d\u652f\u6301\uff0c  =1: \u652f\u6301"
        ::={a200ipsentry 14}    
        
        a200ipsTerminationID OBJECT-TYPE
        SYNTAX        OCTET STRING (SIZE (0..63))
        MAX-ACCESS  read-only
        STATUS      current
        DESCRIPTION    ""
        ::={a200ipsentry 15}
    
    a200ipsmgid OBJECT-TYPE
        SYNTAX        INTEGER(1..255)
        MAX-ACCESS  read-only
        STATUS      current
        DESCRIPTION    ""
        ::={a200ipsentry 16}
    
    a200ipsDigitLen  OBJECT-TYPE
        SYNTAX        INTEGER(2..64)
        MAX-ACCESS  read-only
        STATUS      current
        DESCRIPTION    ""
        ::={a200ipsentry 17}

    a200ipsrackno  OBJECT-TYPE
        SYNTAX        INTEGER
        MAX-ACCESS  not-accessible
        STATUS      current
        DESCRIPTION    "\u7535\u8def\u677f\u6240\u5728\u673a\u67b6\u53f7"
        ::={a200ipsentry 18}
        
    a200ipsshelfno OBJECT-TYPE
        SYNTAX        INTEGER
        MAX-ACCESS  not-accessible
        STATUS      current
        DESCRIPTION    "\u7535\u8def\u677f\u6240\u5728\u673a\u6846\u53f7"
        ::={a200ipsentry 19}

    a200ipsslotno     OBJECT-TYPE
        SYNTAX        INTEGER
        MAX-ACCESS  not-accessible
        STATUS      current
        DESCRIPTION    "\u7535\u8def\u677f\u6240\u5728\u69fd\u4f4d\u53f7"
        ::={a200ipsentry 20}
            
--end of ips table 

--conf table begin    
   a200confTable OBJECT-TYPE
        SYNTAX        SEQUENCE OF A200ConfEntry
        MAX-ACCESS    not-accessible
        STATUS      current
        DESCRIPTION    "\u4f1a\u8bae\u7535\u8bdd\u7535\u8def\u63cf\u8ff0\u8868\uff0c\u63cf\u8ff0\u4f1a\u8bae\u7535\u8bdd\u7535\u8def\u8d44\u6e90\u7684\u72b6\u6001\u3001\u7c7b\u578b"
        ::={a200-mib 13}

   a200confentry OBJECT-TYPE
        SYNTAX        A200ConfEntry
        MAX-ACCESS    not-accessible
        STATUS      current
        DESCRIPTION    "describe colunms and index in conf table"
        INDEX { a200boardrackno, a200boardshelfno, 
                a200boardslotno, a200confsubdevno,a200confindex}
        ::={a200confTable 1}

    A200ConfEntry::=
           SEQUENCE{
        a200confsubdevno    INTEGER,
        a200confindex         INTEGER,
        a200confstatus         INTEGER,
        a200confset         INTEGER,
        a200confgroup         INTEGER
            }           

    a200confsubdevno    OBJECT-TYPE
        SYNTAX        INTEGER
        MAX-ACCESS  not-accessible
        STATUS      current
        DESCRIPTION    "\u4f1a\u8bae\u7535\u8def\u6240\u5728\u7684\u677f\u5185\u5b50\u8bbe\u5907\u7f16\u53f7"
        ::={a200confentry 1}    
    
    a200confindex     OBJECT-TYPE
        SYNTAX        INTEGER
        MAX-ACCESS  read-only
        STATUS      current
        DESCRIPTION    "\u4f1a\u8bae\u7535\u8def\u5728\u677f\u5185\u5b50\u8bbe\u5907\u4e2d\u7684\u5e8f\u53f7"
        ::={a200confentry 2}    

    a200confstatus     OBJECT-TYPE
        SYNTAX        INTEGER
        MAX-ACCESS  read-only
        STATUS      current
        DESCRIPTION    "\u7535\u8def\u72b6\u6001\uff0c\u6309\u4f4d\u53d6\u503c"
        ::={a200confentry 3}    

    a200confset     OBJECT-TYPE
        SYNTAX        INTEGER
        MAX-ACCESS  read-only
        STATUS      current
        DESCRIPTION    "\u7535\u8def\u5f53\u524d\u6240\u5c5e\u7684\u4f1a\u8bae\u7ec4\u53f7"
        ::={a200confentry 4}    

    a200confgroup     OBJECT-TYPE
        SYNTAX        INTEGER
        MAX-ACCESS  read-only
        STATUS      current
        DESCRIPTION    "\u7535\u8def\u5f53\u524d\u6240\u5c5e\u7684\u4f1a\u8bae\u7fa4\u53f7"
        ::={a200confentry 5}    
--end of conf table 

-----------------------------------------
-- statistics information begin
-----------------------------------------
--call resource statistics begin    
   a200resstatisTable OBJECT-TYPE
        SYNTAX        SEQUENCE OF A200ResStatisEntry
        MAX-ACCESS    not-accessible
        STATUS      current
        DESCRIPTION    "\u7edf\u8ba1\u5f53\u524d\u8d44\u6e90\u7535\u8def\u53ef\u7528\u60c5\u51b5\uff0c\u4ee5\u4e0b\u8d44\u6e90\u7535\u8def\u7684\u5360\u7528\u6570, \u95ed\u585e\u6570, \u7a7a\u95f2\u6570\uff1a
                      rtp,slc,tone,dtmf,mfc,cid,conf"
        ::={a200-mib 14}

   a200resstatisEntry OBJECT-TYPE
        SYNTAX        A200ResStatisEntry
        MAX-ACCESS    not-accessible
        STATUS      current
        DESCRIPTION    "describe colunms and index in a200resstatisTable table"
        INDEX {a200mgid }
        ::={a200resstatisTable 1}

    A200ResStatisEntry::=
           SEQUENCE{
        a200slcused       INTEGER,
        a200slcidle       INTEGER,
        a200slcblocked    INTEGER,
        a200rtpused       INTEGER,
        a200rtpidle       INTEGER,
        a200rtpblocked    INTEGER,
        a200dtmfused      INTEGER,
        a200dtmfidle       INTEGER,
        a200dtmfblocked   INTEGER,
        a200toneused      INTEGER,
        a200toneidle       INTEGER,
        a200toneblocked   INTEGER,
        a200cidused       INTEGER,
        a200cididle       INTEGER,
        a200cidblocked    INTEGER,
        a200mfcused       INTEGER,
        a200mfcidle       INTEGER,
        a200mfcblocked    INTEGER,
        a200confused      INTEGER,
        a200confidle       INTEGER,
        a200confblocked   INTEGER,
        a200trunkused      INTEGER,
        a200trunkidle     INTEGER,
        a200trunkblock    INTEGER,
        a200cpuratio      INTEGER
            }           

        a200slcused  OBJECT-TYPE
        SYNTAX        INTEGER
        MAX-ACCESS  read-only
        STATUS      current
        DESCRIPTION    "\u5360\u7528\u7528\u6237\u7535\u8def\u6570"
        ::={a200resstatisEntry 1}    

        a200slcidle     OBJECT-TYPE
        SYNTAX        INTEGER
        MAX-ACCESS  read-only
        STATUS      current
        DESCRIPTION    "\u7a7a\u95f2\u7528\u6237\u7535\u8def\u6570"
        ::={a200resstatisEntry 2}    

        a200slcblocked  OBJECT-TYPE
        SYNTAX        INTEGER
        MAX-ACCESS  read-only
        STATUS      current
        DESCRIPTION    "\u95ed\u585e\u7528\u6237\u7535\u8def\u6570"
        ::={a200resstatisEntry 3}    

        a200rtpused    OBJECT-TYPE
        SYNTAX        INTEGER
        MAX-ACCESS  read-only
        STATUS      current
        DESCRIPTION    "\u5360\u7528rtp\u7535\u8def\u6570"
        ::={a200resstatisEntry 4}    

        a200rtpidle     OBJECT-TYPE
        SYNTAX        INTEGER
        MAX-ACCESS  read-only
        STATUS      current
        DESCRIPTION    "\u7a7a\u95f2rtp\u7535\u8def\u6570"
        ::={a200resstatisEntry 5}    

        a200rtpblocked  OBJECT-TYPE
        SYNTAX        INTEGER
        MAX-ACCESS  read-only
        STATUS      current
        DESCRIPTION    "\u95ed\u585ertp\u7535\u8def\u6570"
        ::={a200resstatisEntry 6}    

        a200dtmfused  OBJECT-TYPE
        SYNTAX        INTEGER
        MAX-ACCESS  read-only
        STATUS      current
        DESCRIPTION    "\u5360\u7528dtmf\u7535\u8def\u6570"
        ::={a200resstatisEntry 7}    

        a200dtmfidle  OBJECT-TYPE
        SYNTAX        INTEGER
        MAX-ACCESS  read-only
        STATUS      current
        DESCRIPTION    "\u7a7a\u95f2dtmf\u7535\u8def\u6570"
        ::={a200resstatisEntry 8}    

        a200dtmfblocked  OBJECT-TYPE
        SYNTAX        INTEGER
        MAX-ACCESS  read-only
        STATUS      current
        DESCRIPTION    "\u95ed\u585edtmf\u7535\u8def\u6570"
        ::={a200resstatisEntry 9}    

        a200toneused  OBJECT-TYPE
        SYNTAX        INTEGER
        MAX-ACCESS  read-only
        STATUS      current
        DESCRIPTION    "\u5360\u7528tone\uff08\u97f3\u8d44\u6e90\uff09\u7535\u8def\u6570"
        ::={a200resstatisEntry 10}    

        a200toneidle  OBJECT-TYPE
        SYNTAX        INTEGER
        MAX-ACCESS  read-only
        STATUS      current
        DESCRIPTION    "\u7a7a\u95f2tone\uff08\u97f3\u8d44\u6e90\uff09\u7535\u8def\u6570"
        ::={a200resstatisEntry 11}    

        a200toneblocked  OBJECT-TYPE
        SYNTAX        INTEGER
        MAX-ACCESS  read-only
        STATUS      current
        DESCRIPTION    "\u95ed\u585etone\uff08\u97f3\u8d44\u6e90\uff09\u7535\u8def\u6570"
        ::={a200resstatisEntry 12}    

        a200cidused   OBJECT-TYPE
        SYNTAX        INTEGER
        MAX-ACCESS  read-only
        STATUS      current
        DESCRIPTION    "\u5360\u7528cid\u7535\u8def\u6570"
        ::={a200resstatisEntry 13}    

        a200cididle       OBJECT-TYPE
        SYNTAX        INTEGER
        MAX-ACCESS  read-only
        STATUS      current
        DESCRIPTION    "\u7a7a\u95f2cid\u7535\u8def\u6570"
        ::={a200resstatisEntry 14}    

        a200cidblocked  OBJECT-TYPE
        SYNTAX        INTEGER
        MAX-ACCESS  read-only
        STATUS      current
        DESCRIPTION    "\u95ed\u585ecid\u7535\u8def\u6570"
        ::={a200resstatisEntry 15}    

        a200mfcused  OBJECT-TYPE
        SYNTAX        INTEGER
        MAX-ACCESS  read-only
        STATUS      current
        DESCRIPTION    "\u5360\u7528mfc\u7535\u8def\u6570"
        ::={a200resstatisEntry 16}    

        a200mfcidle      OBJECT-TYPE
        SYNTAX        INTEGER
        MAX-ACCESS  read-only
        STATUS      current
        DESCRIPTION    "\u7a7a\u95f2mfc\u7535\u8def\u6570"
        ::={a200resstatisEntry 17}    

        a200mfcblocked  OBJECT-TYPE
        SYNTAX        INTEGER
        MAX-ACCESS  read-only
        STATUS      current
        DESCRIPTION    "\u95ed\u585emfc\u7535\u8def\u6570"
        ::={a200resstatisEntry 18}    

        a200confused   OBJECT-TYPE
        SYNTAX        INTEGER
        MAX-ACCESS  read-only
        STATUS      current
        DESCRIPTION    "\u5360\u7528\u4f1a\u8bae\u7535\u8bdd\u7535\u8def\u6570"
        ::={a200resstatisEntry 19}    

        a200confidle  OBJECT-TYPE
        SYNTAX        INTEGER
        MAX-ACCESS  read-only
        STATUS      current
        DESCRIPTION    "\u7a7a\u95f2\u4f1a\u8bae\u7535\u8bdd\u7535\u8def\u6570"
        ::={a200resstatisEntry 20}    

        a200confblocked  OBJECT-TYPE
        SYNTAX        INTEGER
        MAX-ACCESS  read-only
        STATUS      current
        DESCRIPTION    "\u95ed\u585e\u4f1a\u8bae\u7535\u8bdd\u7535\u8def\u6570"
        ::={a200resstatisEntry 21}    
        
        a200trunkused  OBJECT-TYPE
        SYNTAX        INTEGER
        MAX-ACCESS  read-only
        STATUS      current
        DESCRIPTION    ""
        ::={a200resstatisEntry 22}
        
        a200trunkidle  OBJECT-TYPE
        SYNTAX        INTEGER
        MAX-ACCESS  read-only
        STATUS      current
        DESCRIPTION    ""
        ::={a200resstatisEntry 23}
                
        a200trunkblock  OBJECT-TYPE
        SYNTAX        INTEGER
        MAX-ACCESS  read-only
        STATUS      current
        DESCRIPTION    ""
        ::={a200resstatisEntry 24}

        a200cpuratio  OBJECT-TYPE
        SYNTAX        INTEGER
        MAX-ACCESS  read-only
        STATUS      current
        DESCRIPTION    "CPU\u5360\u7528\u7387\uff0c\u4ee5\u767e\u5206\u6570\u8868\u793a\uff1b\u5982=35 \u8868\u793aCPU\u5360\u7528\u7387\u4e3a35%"
        ::={a200resstatisEntry 25}    

--call resource statistics end    
    
--call accumulate table begin    
   a200callaccTable OBJECT-TYPE
        SYNTAX        SEQUENCE OF A200CallAccEntry
        MAX-ACCESS    not-accessible
        STATUS      current
        DESCRIPTION    "\u547c\u53eb\u7d2f\u8ba1\u6570\u636e"
        ::={a200-mib 15}

   a200callaccentry OBJECT-TYPE
        SYNTAX        A200CallAccEntry
        MAX-ACCESS    not-accessible
        STATUS      current
        DESCRIPTION    "describe colunms and index in callacc table"
        INDEX {a200mgid }
        ::={a200callaccTable 1}

    A200CallAccEntry::=
           SEQUENCE{
        a200callAccFail     Counter32,
        a200callAccSucc     Counter32,
        a200callAccLkFail       Counter32,
        a200callAccRtpUse     Counter32,
        a200callAccSlcUse    Counter32
            }           

    a200callAccFail    OBJECT-TYPE
        SYNTAX        Counter32
        MAX-ACCESS  read-only
        STATUS      current
        DESCRIPTION    "\u5931\u8d25\u547c\u53eb\u6b21\u6570"
        ::={a200callaccentry 1}    

    a200callAccSucc    OBJECT-TYPE
        SYNTAX        Counter32
        MAX-ACCESS  read-only
        STATUS      current
        DESCRIPTION    "\u6210\u529f\u547c\u53eb\u6b21\u6570"
        ::={a200callaccentry 2}    

    a200callAccLkFail    OBJECT-TYPE
        SYNTAX        Counter32
        MAX-ACCESS  read-only
        STATUS      current
        DESCRIPTION    "\u547c\u53eb\u94fe\u8def\u65ad\u6b21\u6570"
        ::={a200callaccentry 3}    

    a200callAccRtpUse    OBJECT-TYPE
        SYNTAX        Counter32
        MAX-ACCESS  read-only
        STATUS      current
        DESCRIPTION    "rtp \u5360\u7528\u65f6\u957f"
        ::={a200callaccentry 4}    

    a200callAccSlcUse    OBJECT-TYPE
        SYNTAX        Counter32
        MAX-ACCESS  read-only
        STATUS      current
        DESCRIPTION    "slc \u5360\u7528\u65f6\u957f"
        ::={a200callaccentry 5}    
--call accumulate table 

--H248 accumulate table begin    
   a200h248accTable OBJECT-TYPE
        SYNTAX        SEQUENCE OF A200H248AccEntry
        MAX-ACCESS    not-accessible
        STATUS      current
        DESCRIPTION    "H248\u6d41\u91cf\u7edf\u8ba1"
        ::={a200-mib 16}

   a200h248accentry OBJECT-TYPE
        SYNTAX        A200H248AccEntry
        MAX-ACCESS    not-accessible
        STATUS      current
        DESCRIPTION    "describe colunms and index in h248acc table"
        INDEX {a200mgid }
        ::={a200h248accTable 1}

    A200H248AccEntry::=
           SEQUENCE{
           a200h248AccRecMsg    Counter64,    
        a200h248AccSendMsg      Counter64,
        a200h248AccRecMsgByte   Counter64,
        a200h248AccSendMsgByte  Counter64,
        a200h248AccProtErr      Counter64,
        a200h248AccTimerOut     Counter64,
        a200h248AccDisconnect   Counter64,
        a200h248AccMgcChange    Counter64,
        a200h248AccTransErr     Counter64
            }           

    a200h248AccRecMsg    OBJECT-TYPE
        SYNTAX        Counter64
        MAX-ACCESS  read-only
        STATUS      current
        DESCRIPTION    "H248 \u63a5\u6536\u6d88\u606f\u4e2a\u6570 "
        ::={a200h248accentry 1}    

    a200h248AccSendMsg   OBJECT-TYPE
        SYNTAX        Counter64
        MAX-ACCESS  read-only
        STATUS      current
        DESCRIPTION    "H248 \u53d1\u9001\u6d88\u606f\u4e2a\u6570"
        ::={a200h248accentry 2}

    a200h248AccRecMsgByte  OBJECT-TYPE
        SYNTAX        Counter64
        MAX-ACCESS  read-only
        STATUS      current
        DESCRIPTION    "H248 \u63a5\u6536\u6d88\u606f\u5b57\u8282\u6570 "
        ::={a200h248accentry 3}

    a200h248AccSendMsgByte  OBJECT-TYPE
        SYNTAX        Counter64
        MAX-ACCESS  read-only
        STATUS      current
        DESCRIPTION    "H248 \u53d1\u9001\u6d88\u606f\u5b57\u8282\u6570"
        ::={a200h248accentry 4}

    a200h248AccProtErr    OBJECT-TYPE
        SYNTAX        Counter64
        MAX-ACCESS  read-only
        STATUS      current
        DESCRIPTION    "H248 \u4fe1\u4ee4\u5c42\u51fa\u9519\u603b\u6570"
        ::={a200h248accentry 5}

    a200h248AccTimerOut   OBJECT-TYPE
        SYNTAX        Counter64
        MAX-ACCESS  read-only
        STATUS      current
        DESCRIPTION    "H248 \u6240\u6709\u5b9a\u65f6\u5668\u6ea2\u51fa\u6b21\u6570"
        ::={a200h248accentry 6}

    a200h248AccDisconnect  OBJECT-TYPE
        SYNTAX        Counter64
        MAX-ACCESS  read-only
        STATUS      current
        DESCRIPTION    "H248 \u4f20\u8f93\u94fe\u8def\u4e22\u5931\u6b21\u6570"
        ::={a200h248accentry 7}

    a200h248AccMgcChange   OBJECT-TYPE
        SYNTAX        Counter64
        MAX-ACCESS  read-only
        STATUS      current
        DESCRIPTION    "mgc \u5012\u6362\u6b21\u6570"
        ::={a200h248accentry 8}

    a200h248AccTransErr   OBJECT-TYPE
        SYNTAX        Counter64
        MAX-ACCESS  read-only
        STATUS      current
        DESCRIPTION    "H248 \u4f20\u8f93\u5c42\u53d1\u51fa\u7684\u6240\u6709\u544a\u8b66\u603b\u6570"
        ::={a200h248accentry 9}
            
--H248 accumulate table end

--net flow accumulate table begin    
   a200netaccTable OBJECT-TYPE
        SYNTAX        SEQUENCE OF A200NetAccEntry
        MAX-ACCESS    not-accessible
        STATUS      current
        DESCRIPTION    "\u7f51\u7edc\u6d41\u91cf\u7edf\u8ba1"
        ::={a200-mib 17}

   a200netaccentry OBJECT-TYPE
        SYNTAX        A200NetAccEntry
        MAX-ACCESS    not-accessible
        STATUS      current
        DESCRIPTION    "describe colunms and index in netacc table"
        INDEX {a200mgid }
        ::={a200netaccTable 1}

    A200NetAccEntry::=
           SEQUENCE{
        a200netAccCtlByteRec     Counter64,
        a200netAccCtlByteSend   Counter64,
        a200netAccCtlPackRec    Counter64,
        a200netAccCtlPackSend   Counter64,
        a200netAccMedByteRec    Counter64,
        a200netAccMedByteSend   Counter64,
        a200netAccMedPackRec    Counter64,
        a200netAccMedPackSend   Counter64,
        a200netAccSgByteRec     Counter64,
        a200netAccSgByteSend    Counter64,
        a200netAccSgPackRec     Counter64,
        a200netAccSgPackSend    Counter64
            }           

    a200netAccCtlByteRec     OBJECT-TYPE
        SYNTAX        Counter64
        MAX-ACCESS  read-only
        STATUS      current
        DESCRIPTION    " \u63a5\u6536\u63a7\u5236\u6d41\u5b57\u8282\u6570"
        ::={a200netaccentry 1}    

    a200netAccCtlByteSend   OBJECT-TYPE
        SYNTAX        Counter64
        MAX-ACCESS  read-only
        STATUS      current
        DESCRIPTION    "\u53d1\u9001\u63a7\u5236\u6d41\u5b57\u8282\u6570"
        ::={a200netaccentry 2}    

    a200netAccCtlPackRec    OBJECT-TYPE
        SYNTAX        Counter64
        MAX-ACCESS  read-only
        STATUS      current
        DESCRIPTION    "\u63a5\u6536\u63a7\u5236\u6d41\u5305\u4e2a\u6570 "
        ::={a200netaccentry 3}    

    a200netAccCtlPackSend   OBJECT-TYPE
        SYNTAX        Counter64
        MAX-ACCESS  read-only
        STATUS      current
        DESCRIPTION    "\u53d1\u9001\u63a7\u5236\u6d41\u5305\u4e2a\u6570"
        ::={a200netaccentry 4}    

    a200netAccMedByteRec   OBJECT-TYPE
        SYNTAX        Counter64
        MAX-ACCESS  read-only
        STATUS      current
        DESCRIPTION    "\u63a5\u6536\u5a92\u4f53\u6d41\u5b57\u8282\u6570"
        ::={a200netaccentry 5}    

    a200netAccMedByteSend  OBJECT-TYPE
        SYNTAX        Counter64
        MAX-ACCESS  read-only
        STATUS      current
        DESCRIPTION    "\u53d1\u9001\u5a92\u4f53\u6d41\u5b57\u8282\u6570"
        ::={a200netaccentry 6}    

    a200netAccMedPackRec   OBJECT-TYPE
        SYNTAX        Counter64
        MAX-ACCESS  read-only
        STATUS      current
        DESCRIPTION    "\u63a5\u6536\u5a92\u4f53\u6d41\u5305\u4e2a\u6570"
        ::={a200netaccentry 7}    

    a200netAccMedPackSend   OBJECT-TYPE
        SYNTAX        Counter64
        MAX-ACCESS  read-only
        STATUS      current
        DESCRIPTION    "\u53d1\u9001\u5a92\u4f53\u6d41\u5305\u4e2a\u6570"
        ::={a200netaccentry 8}    

    a200netAccSgByteRec     OBJECT-TYPE
        SYNTAX        Counter64
        MAX-ACCESS  read-only
        STATUS      current
        DESCRIPTION    "\u63a5\u6536SG\u6d41\u5b57\u8282\u6570"
        ::={a200netaccentry 9}    

    a200netAccSgByteSend    OBJECT-TYPE
        SYNTAX        Counter64
        MAX-ACCESS  read-only
        STATUS      current
        DESCRIPTION    "\u53d1\u9001SG\u6d41\u5b57\u8282\u6570"
        ::={a200netaccentry 10}    

    a200netAccSgPackRec     OBJECT-TYPE
        SYNTAX        Counter64
        MAX-ACCESS  read-only
        STATUS      current
        DESCRIPTION    "\u63a5\u6536SG\u6d41\u5305\u4e2a\u6570"
        ::={a200netaccentry 11}    

    a200netAccSgPackSend   OBJECT-TYPE
        SYNTAX        Counter64
        MAX-ACCESS  read-only
        STATUS      current
        DESCRIPTION    "\u53d1\u9001SG\u6d41\u5305\u4e2a\u6570"
        ::={a200netaccentry 12}    
                    
--net flow accumulate table end

--alarm pool table begin
       a200alarmpoolTable OBJECT-TYPE
        SYNTAX        SEQUENCE OF A200AlarmPoolEntry
        MAX-ACCESS    not-accessible
        STATUS      current
        DESCRIPTION    "\u4fdd\u5b58\u5f53\u524d\u5c1a\u672a\u6062\u590d\u7684\u5404\u7c7b\u544a\u8b66"
        ::={a200-mib 18}

       a200alarmpoolEntry OBJECT-TYPE
        SYNTAX        A200AlarmPoolEntry
        MAX-ACCESS    not-accessible
        STATUS      current
        DESCRIPTION    "describe colunms and index in alarm pool table"
        INDEX {a200alarmpoolId }
        ::={a200alarmpoolTable 1}

    A200AlarmPoolEntry::=
           SEQUENCE{
            a200alarmpoolId        Counter32,
            a200alarmpoolCode        INTEGER,
            a200alarmpoolLevel        INTEGER,
            a200alarmpoolReason        INTEGER,                        
            a200alarmpoolTime        Counter32,
            a200alarmpoolModuleNo    INTEGER,
            a200alarmpoolPostionMode    INTEGER,
            a200alarmpoolRackNo        INTEGER,
            a200alarmpoolShelfNo    INTEGER,
            a200alarmpoolSlotNo        INTEGER,
            a200alarmpoolMoreInfo    OCTET STRING
            }           

    a200alarmpoolId        OBJECT-TYPE
        SYNTAX        Counter32
        MAX-ACCESS  read-only
        STATUS      current
        DESCRIPTION    "\u544a\u8b66\u6d41\u6c34\u53f7"
        ::={a200alarmpoolEntry  1}    

    a200alarmpoolCode    OBJECT-TYPE
        SYNTAX        INTEGER
        MAX-ACCESS  read-only
        STATUS      current
        DESCRIPTION    "\u544a\u8b66\u7801"
        ::={a200alarmpoolEntry  2}    
    
    a200alarmpoolLevel    OBJECT-TYPE
        SYNTAX        INTEGER
        MAX-ACCESS  read-only
        STATUS      current
        DESCRIPTION    "\u544a\u8b66\u7ea7\u522b"
        ::={a200alarmpoolEntry  3}    
    
    a200alarmpoolReason    OBJECT-TYPE
        SYNTAX        INTEGER
        MAX-ACCESS  read-only
        STATUS      current
        DESCRIPTION    "\u544a\u8b66\u539f\u56e0\u7801"
        ::={a200alarmpoolEntry  4}    
                            
    a200alarmpoolTime    OBJECT-TYPE
        SYNTAX        Counter32
        MAX-ACCESS  read-only
        STATUS      current
        DESCRIPTION    "\u544a\u8b66\u65f6\u95f4\uff08\u81ea2000\u5e741\u67081\u65e50\u65f6\u901d\u53bb\u7684\u79d2\u6570\uff09"
        ::={a200alarmpoolEntry  5}    
    
    a200alarmpoolModuleNo    OBJECT-TYPE
        SYNTAX        INTEGER
        MAX-ACCESS  read-only
        STATUS      current
        DESCRIPTION    "\u544a\u8b66\u6a21\u5757\u53f7"
        ::={a200alarmpoolEntry  6}    

    a200alarmpoolPostionMode    OBJECT-TYPE
        SYNTAX        INTEGER
        MAX-ACCESS  read-only
        STATUS      current
        DESCRIPTION    "\u544a\u8b66\u4f4d\u7f6e\u6a21\u5f0f\uff1a =0 \u65e0\u544a\u8b66\u4f4d\u7f6e
                         =1 \u6709\u544a\u8b66\u4f4d\u7f6e"
        ::={a200alarmpoolEntry  7}    

    a200alarmpoolRackNo    OBJECT-TYPE
        SYNTAX        INTEGER
        MAX-ACCESS  read-only
        STATUS      current
        DESCRIPTION    "\u5f53a200alarmpoolPostionMode =1 \u65f6\uff0c\u544a\u8b66\u673a\u67b6\u4f4d\u7f6e"
        ::={a200alarmpoolEntry  8}    
    
    a200alarmpoolShelfNo    OBJECT-TYPE
        SYNTAX        INTEGER
        MAX-ACCESS  read-only
        STATUS      current
        DESCRIPTION    "\u5f53a200alarmpoolPostionMode =1 \u65f6\uff0c\u544a\u8b66\u673a\u6846\u4f4d\u7f6e"
        ::={a200alarmpoolEntry  9}    

    a200alarmpoolSlotNo    OBJECT-TYPE
        SYNTAX        INTEGER
        MAX-ACCESS  read-only
        STATUS      current
        DESCRIPTION    "\u5f53a200alarmpoolPostionMode =1 \u65f6\uff0c\u544a\u8b66\u69fd\u4f4d\u4f4d\u7f6e"
        ::={a200alarmpoolEntry  10}    
    
    a200alarmpoolMoreInfo    OBJECT-TYPE
        SYNTAX        OCTET STRING (SIZE (0..30))
        MAX-ACCESS  read-only
        STATUS      current
        DESCRIPTION    "\u544a\u8b66\u9644\u52a0\u4fe1\u606f"
        ::={a200alarmpoolEntry  11}    
    
--alarm pool table end

--route table begin    
   a200routeTable OBJECT-TYPE
        SYNTAX        SEQUENCE OF A200RouteEntry
        MAX-ACCESS    not-accessible
        STATUS      current
        DESCRIPTION    ""
        ::={a200-mib 19}

   a200routeEntry OBJECT-TYPE
        SYNTAX        A200RouteEntry
        MAX-ACCESS    not-accessible
        STATUS      current
        DESCRIPTION    "describe colunms and index in route table"
        INDEX { a200routerackno, a200routeshelfno, a200routeslotno, 
            a200routephyport, a200routeportip, a200routesrcip,
            a200routedestip }
        ::={a200routeTable 1}

   A200RouteEntry::=
           SEQUENCE{
            a200routerackno      INTEGER,
            a200routeshelfno     INTEGER,
            a200routeslotno      INTEGER,
            a200routephyport     INTEGER,
            a200routeportip      IpAddress,
            a200routesrcip       IpAddress,
        a200routedestip      IpAddress,
        a200routesrcmask     IpAddress,
            a200routedestmask    IpAddress,
            a200routenexthop     IpAddress,
            a200routeRowStatus   RowStatus
            }           

    a200routerackno  OBJECT-TYPE
        SYNTAX        INTEGER
        MAX-ACCESS  read-only
        STATUS      current
        DESCRIPTION    ""
        ::={a200routeEntry 1}    
      
    a200routeshelfno  OBJECT-TYPE
        SYNTAX        INTEGER
        MAX-ACCESS  read-only
        STATUS      current
        DESCRIPTION    ""
        ::={a200routeEntry 2}    
      
    a200routeslotno  OBJECT-TYPE
        SYNTAX        INTEGER
        MAX-ACCESS  read-only
        STATUS      current
        DESCRIPTION    ""
        ::={a200routeEntry 3}    
    
    a200routephyport  OBJECT-TYPE
        SYNTAX        INTEGER
        MAX-ACCESS  read-only
        STATUS      current
        DESCRIPTION    ""
        ::={a200routeEntry 4}    
    
    a200routeportip   OBJECT-TYPE
        SYNTAX        IpAddress
        MAX-ACCESS  read-only
        STATUS      current
        DESCRIPTION    ""
        ::={a200routeEntry 5}    
  
    a200routesrcip  OBJECT-TYPE
        SYNTAX        IpAddress
        MAX-ACCESS  read-only
        STATUS      current
        DESCRIPTION    ""
        ::={a200routeEntry 6}    
    
    a200routedestip  OBJECT-TYPE
        SYNTAX        IpAddress
        MAX-ACCESS  read-only
        STATUS      current
        DESCRIPTION    ""
        ::={a200routeEntry 7}    

    a200routesrcmask    OBJECT-TYPE
        SYNTAX        IpAddress
        MAX-ACCESS  read-create
        STATUS      current
        DESCRIPTION    ""
        ::={a200routeEntry 8}    

    a200routedestmask   OBJECT-TYPE
        SYNTAX        IpAddress
        MAX-ACCESS  read-create
        STATUS      current
        DESCRIPTION    ""
        ::={a200routeEntry 9}    
        
    a200routenexthop   OBJECT-TYPE
        SYNTAX        IpAddress
        MAX-ACCESS  read-create
        STATUS      current
        DESCRIPTION    ""
        ::={a200routeEntry 10}            
        
    a200routeRowStatus   OBJECT-TYPE
        SYNTAX        RowStatus
        MAX-ACCESS  read-create
        STATUS      current
        DESCRIPTION    "insert,delete,update"
        ::={a200routeEntry 11}            
--end of route table
 
--NAT table begin    
   a200natTable OBJECT-TYPE
        SYNTAX        SEQUENCE OF A200NATEntry
        MAX-ACCESS    not-accessible
        STATUS      current
        DESCRIPTION    ""
        ::={a200-mib 20}

   a200natEntry OBJECT-TYPE
        SYNTAX        A200NATEntry
        MAX-ACCESS    not-accessible
        STATUS      current
        DESCRIPTION    "describe colunms and index in NAT table"
        INDEX { a200natSubCard }
        ::={a200natTable 1}

   A200NATEntry::=
           SEQUENCE{
            a200natExIp          IpAddress,
            a200natUdpPort       INTEGER,
            a200natSubCard       INTEGER,
            a200natRowStatus     RowStatus
            }           
    
    a200natExIp  OBJECT-TYPE
        SYNTAX        IpAddress
        MAX-ACCESS  read-create
        STATUS      current
        DESCRIPTION    ""
        ::={a200natEntry 5}    
    
    a200natUdpPort   OBJECT-TYPE
        SYNTAX        INTEGER
        MAX-ACCESS  read-create
        STATUS      current
        DESCRIPTION    ""
        ::={a200natEntry 6}    

    a200natSubCard   OBJECT-TYPE
        SYNTAX        INTEGER
        MAX-ACCESS  read-only
        STATUS      current
        DESCRIPTION    ""
        ::={a200natEntry 11}            
        
    a200natRowStatus   OBJECT-TYPE
        SYNTAX        RowStatus
        MAX-ACCESS  read-create
        STATUS      current
        DESCRIPTION    "insert,delete,update"
        ::={a200natEntry 13}            
--end of nat table

--CtlPort table begin    
   a200CtlPortTable OBJECT-TYPE
        SYNTAX        SEQUENCE OF A200CtlPortEntry
        MAX-ACCESS    not-accessible
        STATUS      current
        DESCRIPTION    ""
        ::={a200-mib 21}

   a200CtlPortEntry OBJECT-TYPE
        SYNTAX        A200CtlPortEntry
        MAX-ACCESS    not-accessible
        STATUS      current
        DESCRIPTION    "describe colunms and index in CtlPort table"
        INDEX { a200CtlPortCtlId }
        ::={a200CtlPortTable 1}

   A200CtlPortEntry::=
           SEQUENCE{
            a200CtlPortCtlId     INTEGER,
            a200CtlPortInfo      INTEGER,
            a200CtlPortUdpPort   INTEGER,
            a200CtlPortRowStatus RowStatus
            }           

    a200CtlPortCtlId  OBJECT-TYPE
        SYNTAX        INTEGER(2..40)
        MAX-ACCESS  read-only
        STATUS      current
        DESCRIPTION    ""
        ::={a200CtlPortEntry 1}    
      
    a200CtlPortInfo  OBJECT-TYPE
        SYNTAX        INTEGER(0..1)
        MAX-ACCESS  read-create
        STATUS      current
        DESCRIPTION    ""
        ::={a200CtlPortEntry 2}    
      
    a200CtlPortUdpPort  OBJECT-TYPE
        SYNTAX        INTEGER(2..65535)
        MAX-ACCESS  read-create
        STATUS      current
        DESCRIPTION    ""
        ::={a200CtlPortEntry 3}    
    
    a200CtlPortRowStatus  OBJECT-TYPE
        SYNTAX        RowStatus
        MAX-ACCESS  read-create
        STATUS      current
        DESCRIPTION    "insert,delete,update"
        ::={a200CtlPortEntry 4}    
--end of CtlPort table

--BoardIP table begin    
   a200BoardIPTable OBJECT-TYPE
        SYNTAX        SEQUENCE OF A200BoardIPEntry
        MAX-ACCESS    not-accessible
        STATUS      current
        DESCRIPTION    ""
        ::={a200-mib 22}

   a200BoardIPEntry OBJECT-TYPE
        SYNTAX        A200BoardIPEntry
        MAX-ACCESS    not-accessible
        STATUS      current
        DESCRIPTION    "describe colunms and index in BoardIPTable table"
        INDEX { a200BoardIPrackno, a200BoardIPshelfno, a200BoardIPslotno,
                   a200BoardIPphyport, a200BoardIPipno }
        ::={a200BoardIPTable 1}

   A200BoardIPEntry::=
           SEQUENCE{
            a200BoardIPrackno    INTEGER,
            a200BoardIPshelfno   INTEGER,
            a200BoardIPslotno    INTEGER,
            a200BoardIPphyport   INTEGER,
            a200BoardIPipno      INTEGER,
            a200BoardIPipaddr    IpAddress,
            a200BoardIPRowStatus RowStatus,
            a200BoardIPsubmask   IpAddress
            }           

    a200BoardIPrackno  OBJECT-TYPE
        SYNTAX        INTEGER
        MAX-ACCESS  read-only
        STATUS      current
        DESCRIPTION    ""
        ::={a200BoardIPEntry 1}    
      
    a200BoardIPshelfno  OBJECT-TYPE
        SYNTAX        INTEGER
        MAX-ACCESS  read-only
        STATUS      current
        DESCRIPTION    ""
        ::={a200BoardIPEntry 2}    
      
    a200BoardIPslotno  OBJECT-TYPE
        SYNTAX        INTEGER
        MAX-ACCESS  read-only
        STATUS      current
        DESCRIPTION    ""
        ::={a200BoardIPEntry 3}    
        
    a200BoardIPphyport  OBJECT-TYPE
        SYNTAX        INTEGER
        MAX-ACCESS  read-only
        STATUS      current
        DESCRIPTION    ""
        ::={a200BoardIPEntry 4}    
        
    a200BoardIPipno  OBJECT-TYPE
        SYNTAX        INTEGER
        MAX-ACCESS  read-only
        STATUS      current
        DESCRIPTION    ""
        ::={a200BoardIPEntry 5}                    
    
    a200BoardIPipaddr  OBJECT-TYPE
        SYNTAX        IpAddress
        MAX-ACCESS  read-create
        STATUS      current
        DESCRIPTION    ""
        ::={a200BoardIPEntry 6}    
        
    a200BoardIPRowStatus  OBJECT-TYPE
        SYNTAX        RowStatus
        MAX-ACCESS  read-create
        STATUS      current
        DESCRIPTION    "only update insert & delete, no read"
        ::={a200BoardIPEntry 7}    
        
    a200BoardIPsubmask  OBJECT-TYPE
        SYNTAX        IpAddress
        MAX-ACCESS  read-create
        STATUS      current
        DESCRIPTION    ""
        ::={a200BoardIPEntry 8}    
        
--end of BoardIP table

--BoardMac table begin    
   a200BoardMacTable OBJECT-TYPE
        SYNTAX        SEQUENCE OF A200BoardMacEntry
        MAX-ACCESS    not-accessible
        STATUS      current
        DESCRIPTION    ""
        ::={a200-mib 23}

   a200BoardMacEntry OBJECT-TYPE
        SYNTAX        A200BoardMacEntry
        MAX-ACCESS    not-accessible
        STATUS      current
        DESCRIPTION    "describe colunms and index in BoardMacTable table"
        INDEX { a200BoardMacrackno, a200BoardMacshelfno, a200BoardMacslotno,
                   a200BoardMacphyport }
        ::={a200BoardMacTable 1}

   A200BoardMacEntry::=
           SEQUENCE{
            a200BoardMacrackno    INTEGER,
            a200BoardMacshelfno   INTEGER,
            a200BoardMacslotno    INTEGER,
            a200BoardMacphyport   INTEGER,
            a200BoardMacmacaddr   MacAddress
            }           

    a200BoardMacrackno  OBJECT-TYPE
        SYNTAX        INTEGER
        MAX-ACCESS  read-only
        STATUS      current
        DESCRIPTION    ""
        ::={a200BoardMacEntry 1}    
      
    a200BoardMacshelfno  OBJECT-TYPE
        SYNTAX        INTEGER
        MAX-ACCESS  read-only
        STATUS      current
        DESCRIPTION    ""
        ::={a200BoardMacEntry 2}    
      
    a200BoardMacslotno  OBJECT-TYPE
        SYNTAX        INTEGER
        MAX-ACCESS  read-only
        STATUS      current
        DESCRIPTION    ""
        ::={a200BoardMacEntry 3}    
        
    a200BoardMacphyport  OBJECT-TYPE
        SYNTAX        INTEGER
        MAX-ACCESS  read-only
        STATUS      current
        DESCRIPTION    ""
        ::={a200BoardMacEntry 4}    
        
    a200BoardMacmacaddr  OBJECT-TYPE
        SYNTAX        MacAddress
        MAX-ACCESS  read-write
        STATUS      current
        DESCRIPTION    "only update,not read"
        ::={a200BoardMacEntry 5}                    
    
--end of BoardIP table

--BoardOperation table begin    
   a200BoardOperationTable OBJECT-TYPE
        SYNTAX        SEQUENCE OF A200BoardOperationEntry
        MAX-ACCESS    not-accessible
        STATUS      current
        DESCRIPTION    ""
        ::={a200-mib 24}

   a200BoardOperationentry OBJECT-TYPE
        SYNTAX        A200BoardOperationEntry
        MAX-ACCESS    not-accessible
        STATUS      current
        DESCRIPTION    "describe colunms and index in BoardOperation table"
        INDEX { a200BoardOperationrackno,a200BoardOperationshelfno,
                a200BoardOperationslotno }
        ::={a200BoardOperationTable 1}
        
   A200BoardOperationEntry::=
       SEQUENCE{
           a200BoardOperationrackno       INTEGER,
           a200BoardOperationshelfno      INTEGER,
           a200BoardOperationslotno     INTEGER,
        a200BoardOpetionSubInfo     INTEGER,
        a200BoardOperationType       INTEGER,        
        a200BoardOperationRowStatus  RowStatus,
        a200BoardOperation4MHWNo     INTEGER
        }
        
    a200BoardOperationrackno  OBJECT-TYPE
        SYNTAX        INTEGER
        MAX-ACCESS  read-only
        STATUS      current
        DESCRIPTION    ""
        ::={a200BoardOperationentry 1}
        
    a200BoardOperationshelfno OBJECT-TYPE
        SYNTAX        INTEGER
        MAX-ACCESS  read-only
        STATUS      current
        DESCRIPTION    ""
        ::={a200BoardOperationentry 2}

    a200BoardOperationslotno     OBJECT-TYPE
        SYNTAX        INTEGER
        MAX-ACCESS  read-only
        STATUS      current
        DESCRIPTION    ""
        ::={a200BoardOperationentry 3}

    a200BoardOpetionSubInfo    OBJECT-TYPE
        SYNTAX        INTEGER
        MAX-ACCESS  read-create
        STATUS      current
        DESCRIPTION    ""
        ::={a200BoardOperationentry 4}

    a200BoardOperationType  OBJECT-TYPE
        SYNTAX        INTEGER
        MAX-ACCESS  read-create
        STATUS      current
        DESCRIPTION    ""
        ::={a200BoardOperationentry 5}
        
    a200BoardOperationRowStatus  OBJECT-TYPE
        SYNTAX        RowStatus
        MAX-ACCESS  read-create
        STATUS      current
        DESCRIPTION    "insert,delete"
        ::={a200BoardOperationentry 6}
        
    a200BoardOperation4MHWNo  OBJECT-TYPE
        SYNTAX        INTEGER
        MAX-ACCESS  read-create
        STATUS      current
        DESCRIPTION    ""
        ::={a200BoardOperationentry 7}

--end of BoardOperation table 

--TerminationIDOperation table begin    
   a200TerminationIDOperationTable OBJECT-TYPE
        SYNTAX        SEQUENCE OF A200TerminationIDOperationEntry
        MAX-ACCESS    not-accessible
        STATUS      current
        DESCRIPTION    ""
        ::={a200-mib 25}

   a200TerminationIDOperationentry OBJECT-TYPE
        SYNTAX        A200TerminationIDOperationEntry
        MAX-ACCESS    not-accessible
        STATUS      current
        DESCRIPTION    "describe colunms and index in TerminationIDOperation table"
        INDEX { a200TerminationIDOperationrackno,a200TerminationIDOperationshelfno,
                a200TerminationIDOperationslotno,a200TerminationIDOperationSubInfo }
        ::={a200TerminationIDOperationTable 1}
        
   A200TerminationIDOperationEntry::=
       SEQUENCE{
           a200TerminationIDOperationrackno       INTEGER,
           a200TerminationIDOperationshelfno      INTEGER,
           a200TerminationIDOperationslotno       INTEGER,
        a200TerminationIDOperationSubInfo         INTEGER,           
        a200TerminationIDOperationTMID           OCTET STRING,
        a200TerminationIDOperationRowStatus    RowStatus,
        a200TerminationIDOperationType         INTEGER,
        a200TerminationIDOperationBeginNo      INTEGER,
        a200TerminationIDOperationBeginIndex   INTEGER,
            a200TerminationIDOperationSum          INTEGER,
            a200TerminationIDOperationMgId         INTEGER,
            a200TerminationIDOperationDigitLen     INTEGER
        
        }
        
    a200TerminationIDOperationrackno  OBJECT-TYPE
        SYNTAX        INTEGER
        MAX-ACCESS  read-only
        STATUS      current
        DESCRIPTION    ""
        ::={a200TerminationIDOperationentry 1}
        
    a200TerminationIDOperationshelfno OBJECT-TYPE
        SYNTAX        INTEGER
        MAX-ACCESS  read-only
        STATUS      current
        DESCRIPTION    ""
        ::={a200TerminationIDOperationentry 2}

    a200TerminationIDOperationslotno     OBJECT-TYPE
        SYNTAX        INTEGER
        MAX-ACCESS  read-only
        STATUS      current
        DESCRIPTION    ""
        ::={a200TerminationIDOperationentry 3}

        a200TerminationIDOperationSubInfo  OBJECT-TYPE
        SYNTAX        INTEGER
        MAX-ACCESS  read-only
        STATUS      current
        DESCRIPTION    ""
        ::={a200TerminationIDOperationentry 4}
        
    a200TerminationIDOperationTMID    OBJECT-TYPE
        SYNTAX        OCTET STRING (SIZE(0 .. 63))
        MAX-ACCESS  read-create
        STATUS      current
        DESCRIPTION    ""
        ::={a200TerminationIDOperationentry 5}
        
        a200TerminationIDOperationRowStatus  OBJECT-TYPE
        SYNTAX        RowStatus
        MAX-ACCESS  read-create
        STATUS      current
        DESCRIPTION    "insert,delete"
        ::={a200TerminationIDOperationentry 6}
        
        
        a200TerminationIDOperationType    OBJECT-TYPE
        SYNTAX        INTEGER{
                    type1(1),
                    type2(2),
                    type3(3)
        }
        MAX-ACCESS  read-create
        STATUS      current
        DESCRIPTION    "Type 1:USER00100100000-USER00100100031,type 2:USER0-USER31,type 3:USER000-USER031"
        ::={a200TerminationIDOperationentry 7}
        
      a200TerminationIDOperationBeginNo    OBJECT-TYPE
        SYNTAX        INTEGER
        MAX-ACCESS  read-create
        STATUS      current
        DESCRIPTION    "Use for type 2"
        ::={a200TerminationIDOperationentry 8}
        
        a200TerminationIDOperationBeginIndex   OBJECT-TYPE
        SYNTAX        INTEGER(0..47)
        MAX-ACCESS  read-create
        STATUS      current
        DESCRIPTION    ""
        ::={a200TerminationIDOperationentry 9}
        
    a200TerminationIDOperationSum       OBJECT-TYPE
        SYNTAX        INTEGER(1..192)
        MAX-ACCESS  read-create
        STATUS      current
        DESCRIPTION    ""
        ::={a200TerminationIDOperationentry 10}
        
        
    a200TerminationIDOperationMgId       OBJECT-TYPE
        SYNTAX        INTEGER(1..255)
        MAX-ACCESS  read-create
        STATUS      current
        DESCRIPTION    ""
        ::={a200TerminationIDOperationentry 11}
        
        a200TerminationIDOperationDigitLen    OBJECT-TYPE
        SYNTAX        INTEGER(2..64)
        MAX-ACCESS  read-create
        STATUS      current
        DESCRIPTION    ""
        ::={a200TerminationIDOperationentry 12}
        
   
--end of TerminationIDOperation table 

--Start of the a200TLineTable
    a200TLineTable OBJECT-TYPE
    SYNTAX        SEQUENCE OF A200TLineEntry
    MAX-ACCESS    not-accessible
    STATUS      current
    DESCRIPTION    "For the testing"
    ::={a200-mib 26}
    
    a200TLineEntry    OBJECT-TYPE
    SYNTAX        A200TLineEntry
    MAX-ACCESS    not-accessible
    STATUS      current
    DESCRIPTION    ""
    INDEX        {a200TLineNo}
    ::= {a200TLineTable 1}
    
    A200TLineEntry ::= SEQUENCE
    {
        a200TLineNo        INTEGER,
           a200TLineGroup        INTEGER,
           a200TLineRackNo        INTEGER,
           a200TLineShelfNo    INTEGER,
           a200TLineStatus        INTEGER
       }
       
       a200TLineNo        OBJECT-TYPE
       SYNTAX            INTEGER(1..5)
       MAX-ACCESS        not-accessible
       STATUS            current
       DESCRIPTION        "this object is mapped to DB with the index of 47|1"
       ::= {a200TLineEntry 1}
       
       a200TLineGroup        OBJECT-TYPE                                                                      
       SYNTAX            INTEGER(1..5)
       MAX-ACCESS        read-write
       STATUS            current
       DESCRIPTION        "this object is mapped to DB with the index of 47|2"                                                                                                                                        
       ::= {a200TLineEntry 2}
       
       a200TLineRackNo        OBJECT-TYPE
       SYNTAX            INTEGER
       MAX-ACCESS        read-only
       STATUS            current
       DESCRIPTION        "this object is mapped to DB with the index of 47|3, it should be valued as 1"
       ::= {a200TLineEntry 3}
       
       a200TLineShelfNo    OBJECT-TYPE
       SYNTAX            INTEGER(1..5)
       MAX-ACCESS        read-only
       STATUS            current
       DESCRIPTION        "this object is mapped to DB with the index of 47|4"
       ::= {a200TLineEntry 4}
       
       
       a200TLineStatus        OBJECT-TYPE
       SYNTAX            INTEGER {
                     idle(0),
                     seized(1)    
                   }
       MAX-ACCESS        read-only
       STATUS            current
       DESCRIPTION        "this object is mapped to DB with the index of 47|5"
       ::= {a200TLineEntry 5}
       
--End of The a200TLineTable

--Start of the a200CapacityCfgTable

    a200CapacityCfgTable    OBJECT-TYPE
    SYNTAX            SEQUENCE OF A200CapacityCfgEntry
    MAX-ACCESS        not-accessible
    STATUS          current
    DESCRIPTION        "For capacity configuration. MUST reboot after configuration."
    ::= {a200-mib 27}
    
    a200CapacityCfgEntry    OBJECT-TYPE
    SYNTAX            A200CapacityCfgEntry
    MAX-ACCESS        not-accessible
    STATUS            current
    DESCRIPTION        ""
    INDEX            {a200CapacityCfgId}
    ::= {a200CapacityCfgTable 1}

    A200CapacityCfgEntry  ::= SEQUENCE
    {
        a200BoardSlcCapacity        INTEGER,
        a200BoardAprCapacity        INTEGER,
        a200DasCapacity            INTEGER,
        a200DnalCapacity        INTEGER,
        a200DyDasCapacity        INTEGER,
        a200DyDnalCapacity        INTEGER,
        a200ToneidCapacity        INTEGER,
        a200TermidCapacity        INTEGER,
        a200BoardAdslCapacity      INTEGER,
        a200CapacityCfgId        INTEGER,
        a200CapacityRowStatus    RowStatus,
        a200DasDigitNum         INTEGER
    }

    a200BoardSlcCapacity    OBJECT-TYPE
       SYNTAX            INTEGER(0..65535)
       MAX-ACCESS        read-write
       STATUS            current
       DESCRIPTION        "this object is mapped to DB with the index of 22|1, default value is 24"
       ::= {a200CapacityCfgEntry 1}
           
    a200BoardAprCapacity    OBJECT-TYPE
       SYNTAX            INTEGER(0..65535)
       MAX-ACCESS        read-write
       STATUS            current
       DESCRIPTION        "this object is mapped to DB with the index of 22|2, default value is 2"
       ::= {a200CapacityCfgEntry 2}
       
       a200DasCapacity        OBJECT-TYPE
       SYNTAX            INTEGER(0..65535)
       MAX-ACCESS        read-write
       STATUS            current
       DESCRIPTION        "this object is mapped to DB with the index of 22|3, default value is 100"
       ::= {a200CapacityCfgEntry 3}
       
       
       a200DnalCapacity    OBJECT-TYPE
       SYNTAX            INTEGER(0..65535)
       MAX-ACCESS        read-write
       STATUS            current
       DESCRIPTION        "this object is mapped to DB with the index of 22|4, default value is 512"
       ::= {a200CapacityCfgEntry 4}
       
       a200DyDasCapacity    OBJECT-TYPE
       SYNTAX            INTEGER(0..65535)
       MAX-ACCESS        read-write
       STATUS            current
       DESCRIPTION        "this object is mapped to DB with the index of 22|5, default value is 512"
       ::= {a200CapacityCfgEntry 5}
       
       a200DyDnalCapacity    OBJECT-TYPE
       SYNTAX            INTEGER(0..65535)
       MAX-ACCESS        read-write
       STATUS            current
       DESCRIPTION        "this object is mapped to DB with the index of 22|6, default value is 4095"
       ::= {a200CapacityCfgEntry 6}
       
       a200ToneidCapacity    OBJECT-TYPE
       SYNTAX            INTEGER(0..65535)
       MAX-ACCESS        read-write
       STATUS            current
       DESCRIPTION        "this object is mapped to DB with the index of 22|7, default value is 800"
       ::= {a200CapacityCfgEntry 7}
       
       a200TermidCapacity    OBJECT-TYPE
       SYNTAX            INTEGER(0..65535)
       MAX-ACCESS        read-write
       STATUS            current
       DESCRIPTION        "this object is mapped to DB with the index of 22|8, default value is 4096"
       ::= {a200CapacityCfgEntry 8}
       
       a200BoardAdslCapacity    OBJECT-TYPE
       SYNTAX            INTEGER(0..65535)
       MAX-ACCESS        read-write
       STATUS            current
       DESCRIPTION        "this object is mapped to DB with the index of 22|9, default value is 24"
       ::= {a200CapacityCfgEntry 9}
       
       a200CapacityCfgId    OBJECT-TYPE
       SYNTAX            INTEGER
       MAX-ACCESS        not-accessible
       STATUS            current
       DESCRIPTION        "this object must be valued with 1(i.e only 1 tuple of data in the DB)"
       ::= {a200CapacityCfgEntry 10}
       
       a200CapacityRowStatus    OBJECT-TYPE
       SYNTAX            RowStatus
       MAX-ACCESS        read-create
       STATUS            current
       DESCRIPTION        "only insert operation is allowed"
       ::= {a200CapacityCfgEntry 11}
       
       a200DasDigitNum    OBJECT-TYPE
       SYNTAX            INTEGER(1..16)
       MAX-ACCESS        read-write
       STATUS            current
       DESCRIPTION        ""
       ::= {a200CapacityCfgEntry 12}
       
--End of a200CapacityCfgTable.


--Start of a200TrapCfgTable.

    a200TrapCfgTable    OBJECT-TYPE
    SYNTAX            SEQUENCE OF A200TrapCfgEntry
    MAX-ACCESS        not-accessible
    STATUS          current
    DESCRIPTION        "Table of configurations of sending trap messages"
    ::= {a200-mib 28}
    
    a200TrapCfgEntry    OBJECT-TYPE
    SYNTAX            A200TrapCfgEntry
    MAX-ACCESS        not-accessible
    STATUS            current
    DESCRIPTION        ""
    INDEX            {a200TrapCfgId}
    ::= {a200TrapCfgTable 1}

    A200TrapCfgEntry  ::= SEQUENCE
    {
        a200TrapCfgId               INTEGER,
        a200TrapCfgSendTrapPort        INTEGER,
        a200TrapCfgSendTrapIP       IpAddress,
        a200TrapCfgRowStatus        RowStatus,
        a200TrapCfgTrapType         INTEGER
    }

    a200TrapCfgId    OBJECT-TYPE
       SYNTAX            INTEGER(1..16)
       MAX-ACCESS        not-accessible
       STATUS            current
       DESCRIPTION        "this object is mapped to DB with the index of 48|1"
       ::= {a200TrapCfgEntry 1}
           
    a200TrapCfgSendTrapPort    OBJECT-TYPE
       SYNTAX            INTEGER(0..65535)
       MAX-ACCESS        read-create
       STATUS            current
       DESCRIPTION        "this object is mapped to DB with the index of 48|3"
       ::= {a200TrapCfgEntry 2}
       
       a200TrapCfgSendTrapIP        OBJECT-TYPE
       SYNTAX            IpAddress
       MAX-ACCESS        read-create
       STATUS            current
       DESCRIPTION        "this object is mapped to DB with the index of 48|4"
       ::= {a200TrapCfgEntry 3}

       a200TrapCfgRowStatus    OBJECT-TYPE
       SYNTAX            RowStatus
       MAX-ACCESS        read-create
       STATUS            current
       DESCRIPTION        "delete & insert is allowed."
       ::= {a200TrapCfgEntry 4}
       
       
       a200TrapCfgTrapType    OBJECT-TYPE
       SYNTAX            INTEGER {typeOam(0), typePCCW(1)}
       MAX-ACCESS        read-create
       STATUS            current
       DESCRIPTION        "this object is mapped to DB with the index of 48|5"
       ::= {a200TrapCfgEntry 5}
       
--End of a200TrapCfgTable.


--Start of a200AppServerTable.

    a200AppServerTable    OBJECT-TYPE
    SYNTAX            SEQUENCE OF A200AppServerEntry
    MAX-ACCESS        not-accessible
    STATUS          current
    DESCRIPTION        "Application server's attributes"
    ::= {a200-mib 29}
    
    a200AppServerEntry    OBJECT-TYPE
    SYNTAX            A200AppServerEntry
    MAX-ACCESS        not-accessible
    STATUS            current
    DESCRIPTION        ""
    INDEX            {a200AppServerID}
    ::= {a200AppServerTable 1}

    A200AppServerEntry  ::= SEQUENCE
    {
        a200AppServerID               INTEGER,
        a200AppServerProtocol         INTEGER,
        a200AppServerMode             INTEGER,
        a200AppServerModeEval         INTEGER,
        a200AppServerStat             INTEGER,
        a200AppServerRowStatus        RowStatus
    }

    a200AppServerID     OBJECT-TYPE
       SYNTAX            INTEGER(1..128)
       MAX-ACCESS        not-accessible
       STATUS            current
       DESCRIPTION        "Application server ID"
       ::= {a200AppServerEntry 1}
           
    a200AppServerProtocol    OBJECT-TYPE
       SYNTAX            INTEGER 
       {
           m3ua(1),
           m2ua(2),
           m2pa(3),
           sua(4),
           iua(5)
       }
       MAX-ACCESS        read-create
       STATUS            current
       DESCRIPTION       
           "Application server's protocol."
       DEFVAL            {iua}
       ::= {a200AppServerEntry 2}
       
    a200AppServerMode    OBJECT-TYPE
       SYNTAX            INTEGER 
       {
           masterSlave(1),
           share(2),
           broadcast(3)
       }
       MAX-ACCESS        read-create
       STATUS            current
       DESCRIPTION       "Application server's working mode"
       DEFVAL            {masterSlave}
       ::= {a200AppServerEntry 3}

    a200AppServerModeEval    OBJECT-TYPE
       SYNTAX            INTEGER(0..255)
       MAX-ACCESS        read-create
       STATUS            current
       DESCRIPTION        "N + K"
       ::= {a200AppServerEntry 4}

    a200AppServerStat    OBJECT-TYPE
       SYNTAX            INTEGER {
                           down(0), inactive(1),
                           active(2), pending(4)
                       }
       MAX-ACCESS        read-only
       STATUS            current
       DESCRIPTION        "Current status of application server"
       ::= {a200AppServerEntry 5}

       a200AppServerRowStatus    OBJECT-TYPE
       SYNTAX            RowStatus
       MAX-ACCESS        read-create
       STATUS            current
       DESCRIPTION        "rowstatus"
       ::= {a200AppServerEntry 6}

--End of a200AppServerTable.



--Start of a200AppServerProcTable.

    a200AppServerProcTable    OBJECT-TYPE
    SYNTAX            SEQUENCE OF A200AppServerProcEntry
    MAX-ACCESS        not-accessible
    STATUS          current
    DESCRIPTION        "Process of application server"
    ::= {a200-mib 30}
    
    a200AppServerProcEntry    OBJECT-TYPE
    SYNTAX            A200AppServerProcEntry
    MAX-ACCESS        not-accessible
    STATUS            current
    DESCRIPTION        ""
    INDEX            {a200AppServerProcID}
    ::= {a200AppServerProcTable 1}

    A200AppServerProcEntry  ::= SEQUENCE
    {
        a200AppServerProcID            INTEGER,
        a200AppServerProcDestPort   INTEGER,
        a200AppServerProcLoclPort   INTEGER,
        a200AppServerProcSctpID     INTEGER,
        a200AppServerProcUpProto    INTEGER,
        a200AppServerProcDownProto  INTEGER,
        a200AppServerProcDestIP     IpAddress,
        a200AppServerProcInStream   INTEGER,
        a200AppServerProcOutStream  INTEGER,
        a200AppServerProcStat       INTEGER,
        a200AppServerProcModule     INTEGER,
        a200AppServerProcClieOrServ INTEGER,
        a200AppServerProcRowStatus  RowStatus
    }

    a200AppServerProcID     OBJECT-TYPE
       SYNTAX            INTEGER(1..128)
       MAX-ACCESS        not-accessible
       STATUS            current
       DESCRIPTION        "Application server process ID"
       ::= {a200AppServerProcEntry 1}
           
    a200AppServerProcDestPort    OBJECT-TYPE
       SYNTAX            INTEGER (0..65535)
       MAX-ACCESS        read-create
       STATUS            current
       DESCRIPTION        "Destination Port"
       ::= {a200AppServerProcEntry 2}
       
       a200AppServerProcLoclPort    OBJECT-TYPE
       SYNTAX            INTEGER (0..65535)
       MAX-ACCESS        read-create
       STATUS            current
       DESCRIPTION        "Local machine's port"
       ::= {a200AppServerProcEntry 3}
       
    
    a200AppServerProcSctpID     OBJECT-TYPE
       SYNTAX            INTEGER
       MAX-ACCESS        read-only
       STATUS            current
       DESCRIPTION        "SCTP ID"
       ::= {a200AppServerProcEntry 4}
    
    a200AppServerProcUpProto    OBJECT-TYPE
       SYNTAX            INTEGER {iua(5)}
       MAX-ACCESS        read-create
       STATUS            current
       DESCRIPTION        "Upper layer's protocol type"
       ::= {a200AppServerProcEntry 5}
    
    a200AppServerProcDownProto    OBJECT-TYPE
       SYNTAX            INTEGER {udp(1), ip(2)}
       MAX-ACCESS        read-create
       STATUS            current
       DESCRIPTION        "lower layer's protocol type"
       ::= {a200AppServerProcEntry 6}

    a200AppServerProcDestIP    OBJECT-TYPE
       SYNTAX            IpAddress
       MAX-ACCESS        read-create
       STATUS            current
       DESCRIPTION        "Destination IP address"
       ::= {a200AppServerProcEntry 7}

    a200AppServerProcInStream    OBJECT-TYPE
       SYNTAX            INTEGER(0..16)
       MAX-ACCESS        read-create
       STATUS            current
       DESCRIPTION        "in-stream, default value is 4"
       ::= {a200AppServerProcEntry 8}
       
       a200AppServerProcOutStream    OBJECT-TYPE
       SYNTAX            INTEGER(0..16)
       MAX-ACCESS        read-create
       STATUS            current
       DESCRIPTION        "out-stream, default value is 4"
       ::= {a200AppServerProcEntry 9}


    a200AppServerProcStat    OBJECT-TYPE
       SYNTAX            INTEGER {
                                     aspLost(0),
                                     aspDown(1),
                                     aspInactive(2),
                                     aspActive(4),
                                     aspStandby(8),
                                     aspManual(64),
                                     aspCongest(128)
                                }
       MAX-ACCESS        read-only
       STATUS            current
       DESCRIPTION        "Current status"
       ::= {a200AppServerProcEntry 10}

       a200AppServerProcModule    OBJECT-TYPE
       SYNTAX            INTEGER
       MAX-ACCESS        read-create
       STATUS            current
       DESCRIPTION        "Module identity. Default value is 2"
       ::= {a200AppServerProcEntry 11}
       
       a200AppServerProcClieOrServ     OBJECT-TYPE
       SYNTAX            INTEGER {client(1), server(2)}
       MAX-ACCESS        read-create
       STATUS            current
       DESCRIPTION        "Client or server? default is server(2)."
       ::= {a200AppServerProcEntry 12}


       a200AppServerProcRowStatus    OBJECT-TYPE
       SYNTAX            RowStatus
       MAX-ACCESS        read-create
       STATUS            current
       DESCRIPTION        "rowstatus"
       ::= {a200AppServerProcEntry 13}

--End of a200AppServerTable.



--Start of a200ASASPTable.

    a200ASASPTable    OBJECT-TYPE
    SYNTAX            SEQUENCE OF A200ASASPEntry
    MAX-ACCESS        not-accessible
    STATUS          current
    DESCRIPTION        "Relationship table of application server and its process"
    ::= {a200-mib 31}
    
    a200ASASPEntry    OBJECT-TYPE
    SYNTAX            A200ASASPEntry
    MAX-ACCESS        not-accessible
    STATUS            current
    DESCRIPTION        ""
    INDEX            {a200ASPID, a200ASID}
    ::= {a200ASASPTable 1}

    A200ASASPEntry   ::= SEQUENCE
    {
        a200ASPID           INTEGER,
        a200ASID            INTEGER,
        a200ASQueue         INTEGER,
        a200ASASPRowStatus  RowStatus
    }
       
       a200ASPID     OBJECT-TYPE
       SYNTAX            INTEGER(1..128)
       MAX-ACCESS        not-accessible
       STATUS            current
       DESCRIPTION        "Application server process ID"
       ::= {a200ASASPEntry 1}
       
       a200ASID     OBJECT-TYPE
       SYNTAX            INTEGER(1..128)
       MAX-ACCESS        not-accessible
       STATUS            current
       DESCRIPTION        "Application server ID"
       ::= {a200ASASPEntry 2}
       
       a200ASQueue     OBJECT-TYPE
       SYNTAX            INTEGER {aspInit(0), aspDown(1), aspUp(2), aspActive(4)}
       MAX-ACCESS        read-only
       STATUS            current
       DESCRIPTION        ""
       ::= {a200ASASPEntry 3}
       
       a200ASASPRowStatus     OBJECT-TYPE
       SYNTAX            RowStatus
       MAX-ACCESS        read-create
       STATUS            current
       DESCRIPTION        ""
       ::= {a200ASASPEntry 4}
       
--End of a200ASASPTable.


--Start of a200M2uaLinkTable.

    a200M2uaLinkTable    OBJECT-TYPE
    SYNTAX            SEQUENCE OF A200M2uaLinkEntry
    MAX-ACCESS        not-accessible
    STATUS          current
    DESCRIPTION        "M2UA link table"
    ::= {a200-mib 32}
    
    a200M2uaLinkEntry    OBJECT-TYPE
    SYNTAX            A200M2uaLinkEntry
    MAX-ACCESS        not-accessible
    STATUS            current
    DESCRIPTION        ""
    INDEX            {a200M2uaLinkID}
    ::= {a200M2uaLinkTable 1}

    A200M2uaLinkEntry   ::= SEQUENCE
    {
        a200M2uaLinkID          INTEGER,
        a200M2uaLinkASID        INTEGER,
        a200M2uaLinkIfID        INTEGER,
        a200M2uaLinkRowStatus   RowStatus
    }
    
    a200M2uaLinkID     OBJECT-TYPE
       SYNTAX            INTEGER(1..512)
       MAX-ACCESS        not-accessible
       STATUS            current
       DESCRIPTION        "link ID"
       ::= {a200M2uaLinkEntry 1}
       
       a200M2uaLinkASID     OBJECT-TYPE
       SYNTAX            INTEGER(1..128)
       MAX-ACCESS        read-create
       STATUS            current
       DESCRIPTION        "Application server ID"
       ::= {a200M2uaLinkEntry 2}
       
       
       a200M2uaLinkIfID     OBJECT-TYPE
       SYNTAX            INTEGER(1..65535)
       MAX-ACCESS        read-create
       STATUS            current
       DESCRIPTION        "interface ID"
       ::= {a200M2uaLinkEntry 3}
       
       a200M2uaLinkRowStatus     OBJECT-TYPE
       SYNTAX            RowStatus
       MAX-ACCESS        read-create
       STATUS            current
       DESCRIPTION        "RowStatus"
       ::= {a200M2uaLinkEntry 4}
       
--End of a200M2uaLinkTable.


--Start of a200DLinkTable.

    a200DLinkTable    OBJECT-TYPE
    SYNTAX            SEQUENCE OF A200DLinkEntry
    MAX-ACCESS        not-accessible
    STATUS          current
    DESCRIPTION        "DLink table"
    ::= {a200-mib 33}
    
    a200DLinkEntry    OBJECT-TYPE
    SYNTAX            A200DLinkEntry
    MAX-ACCESS        not-accessible
    STATUS            current
    DESCRIPTION        ""
    INDEX            {a200DLinkRack, a200DLinkShelf, a200DLinkSlot, a200DLinkPCMNo, a200DLinkIdx}
    ::= {a200DLinkTable 1}

    A200DLinkEntry   ::= SEQUENCE
    {
        a200DLinkRack           INTEGER,
        a200DLinkShelf          INTEGER,
        a200DLinkSlot           INTEGER,
        a200DLinkPCMNo          INTEGER,
        a200DLinkIdx            INTEGER,
        a200DLinkID             INTEGER,
        a200DLinkInfo           INTEGER,
        a200DLinkRowStatus      RowStatus,
        a200DLinkProtocol                INTEGER,
    a200DLinkStatus                    INTEGER
    }
       
       a200DLinkRack     OBJECT-TYPE
       SYNTAX            INTEGER(1)
       MAX-ACCESS        not-accessible
       STATUS            current
       DESCRIPTION        "rack"
       ::= {a200DLinkEntry 1}
       
       
       a200DLinkShelf     OBJECT-TYPE
       SYNTAX            INTEGER(1..5)
       MAX-ACCESS        not-accessible
       STATUS            current
       DESCRIPTION        "shelf"
       ::= {a200DLinkEntry 2}
       
       a200DLinkSlot     OBJECT-TYPE
       SYNTAX            INTEGER(3..16)
       MAX-ACCESS        not-accessible
       STATUS            current
       DESCRIPTION        "slot"
       ::= {a200DLinkEntry 3}
       
       a200DLinkPCMNo     OBJECT-TYPE
       SYNTAX            INTEGER(0..8)
       MAX-ACCESS        not-accessible
       STATUS            current
       DESCRIPTION        "slot"
       ::= {a200DLinkEntry 4}
       
       a200DLinkIdx     OBJECT-TYPE
       SYNTAX            INTEGER(0..30)
       MAX-ACCESS        not-accessible
       STATUS            current
       DESCRIPTION        "index"
       ::= {a200DLinkEntry 5}
       
       a200DLinkID     OBJECT-TYPE
       SYNTAX            INTEGER(1..128)
       MAX-ACCESS        read-only
       STATUS            current
       DESCRIPTION        "D link ID"
       ::= {a200DLinkEntry 6}
       
       a200DLinkInfo     OBJECT-TYPE
       SYNTAX            INTEGER {networkSide(0), subscriberSide(1)}
       MAX-ACCESS        read-only
       STATUS            current
       DESCRIPTION        "other infomations. default value is networkSide(0)"
       ::= {a200DLinkEntry 7}
       
       a200DLinkRowStatus     OBJECT-TYPE
       SYNTAX            RowStatus
       MAX-ACCESS        read-create
       STATUS            current
       DESCRIPTION        "RowStatus"
       ::= {a200DLinkEntry 8}
       
       a200DLinkProtocol   OBJECT-TYPE
       SYNTAX            INTEGER{ptl_2BplusD(1), ptl_30BplusD(2), ptl_23BplusD(3)}
       MAX-ACCESS        read-only
       STATUS            current
       DESCRIPTION        ""
       ::= {a200DLinkEntry 9}
       
       a200DLinkStatus   OBJECT-TYPE
       SYNTAX            INTEGER
       MAX-ACCESS        read-only
       STATUS            current
       DESCRIPTION        ""
       ::= {a200DLinkEntry 10}
       
--End of a200DLinkTable.


--Start of a200DspOperTable

   a200DspOperTable OBJECT-TYPE
        SYNTAX        SEQUENCE OF A200DspOperEntry
        MAX-ACCESS    not-accessible
        STATUS      current
        DESCRIPTION    ""
        ::={a200-mib 34}

   a200DspOperEntry OBJECT-TYPE
        SYNTAX        A200DspOperEntry
        MAX-ACCESS    not-accessible
        STATUS      current
        DESCRIPTION    ""
        INDEX { a200DspOperRack, a200DspOperShelf, 
                a200DspOperSlot, a200DspOperSubdev}
        ::={a200DspOperTable 1}

    A200DspOperEntry ::=
           SEQUENCE{
               a200DspOperRack     INTEGER,
               a200DspOperShelf    INTEGER,
               a200DspOperSlot      INTEGER,
               a200DspOperSubdev    INTEGER,
            a200DspOperKind        INTEGER
            }           

    a200DspOperRack  OBJECT-TYPE
        SYNTAX        INTEGER
        MAX-ACCESS  not-accessible
        STATUS      current
        DESCRIPTION    ""
        ::={a200DspOperEntry 1}    
    
    a200DspOperShelf   OBJECT-TYPE
        SYNTAX        INTEGER
        MAX-ACCESS  not-accessible
        STATUS      current
        DESCRIPTION    ""
        ::={a200DspOperEntry 2}    
    
    a200DspOperSlot   OBJECT-TYPE
        SYNTAX        INTEGER
        MAX-ACCESS  not-accessible
        STATUS      current
        DESCRIPTION    ""
        ::={a200DspOperEntry 3}    
        
    a200DspOperSubdev   OBJECT-TYPE
        SYNTAX        INTEGER
        MAX-ACCESS  not-accessible
        STATUS      current
        DESCRIPTION    ""
        ::={a200DspOperEntry 4}        
        
        
    a200DspOperKind     OBJECT-TYPE
        SYNTAX        INTEGER
        MAX-ACCESS  read-write
        STATUS      current
        DESCRIPTION    "write only, 1:DTMF 2:TONE 3:CID 4:MFC 5:CONF"
        ::={a200DspOperEntry 5}    

--End of a200DspOperTable



   a200DLinkOperTable OBJECT-TYPE
        SYNTAX        SEQUENCE OF A200DLinkOperEntry
        MAX-ACCESS    not-accessible
        STATUS      current
        DESCRIPTION    ""
        ::={a200-mib 35}

   a200DLinkOperEntry OBJECT-TYPE
        SYNTAX         A200DLinkOperEntry
        MAX-ACCESS    not-accessible
        STATUS      current
        DESCRIPTION    ""
        INDEX { a200DLinkOperRack, a200DLinkOperShelf,a200DLinkOperSlot, 
            a200DLinkOperPCMNo, a200DLinkOperLinkIdx}
        ::={a200DLinkOperTable 1}

    A200DLinkOperEntry ::=
           SEQUENCE{
               a200DLinkOperRack         INTEGER,
                    a200DLinkOperShelf        INTEGER,
                    a200DLinkOperSlot         INTEGER,
                    a200DLinkOperPCMNo        INTEGER,
                    a200DLinkOperLinkIdx      INTEGER,
                    a200DLinkOperLinkID       INTEGER,
                    a200DLinkOperLinkInfo     INTEGER,
                    a200DLinkOperASID         INTEGER,
                    a200DLinkOperIfID         INTEGER,                    
                    a200DLinkOperNumber       INTEGER,
                    a200DLinkOperRowStatus    RowStatus
            }           

    a200DLinkOperRack  OBJECT-TYPE
        SYNTAX        INTEGER(1)
        MAX-ACCESS  not-accessible
        STATUS      current
        DESCRIPTION    ""
        ::={a200DLinkOperEntry 1}    
    
    a200DLinkOperShelf  OBJECT-TYPE
        SYNTAX        INTEGER(1..5)
        MAX-ACCESS  not-accessible
        STATUS      current
        DESCRIPTION    ""
        ::={a200DLinkOperEntry 2}    
        
    a200DLinkOperSlot      OBJECT-TYPE
        SYNTAX        INTEGER(3..16)
        MAX-ACCESS  not-accessible
        STATUS      current
        DESCRIPTION    ""
        ::={a200DLinkOperEntry 3}
  
  a200DLinkOperPCMNo      OBJECT-TYPE
        SYNTAX        INTEGER(0..8)
        MAX-ACCESS  not-accessible
        STATUS      current
        DESCRIPTION    ""
        ::={a200DLinkOperEntry 4}        
        
    a200DLinkOperLinkIdx      OBJECT-TYPE
        SYNTAX        INTEGER(0..30)
        MAX-ACCESS  not-accessible
        STATUS      current
        DESCRIPTION    ""
        ::={a200DLinkOperEntry 5}    
        
    a200DLinkOperLinkID      OBJECT-TYPE
        SYNTAX        INTEGER(1..128)
        MAX-ACCESS  read-create
        STATUS      current
        DESCRIPTION    ""
        ::={a200DLinkOperEntry 6}    
        
    a200DLinkOperLinkInfo      OBJECT-TYPE
        SYNTAX        INTEGER{
            networkSide(0),
            subscriberSide(1)
        }
        MAX-ACCESS  read-create
        STATUS      current
        DESCRIPTION    ""
        ::={a200DLinkOperEntry 7}    
        
    a200DLinkOperASID      OBJECT-TYPE
        SYNTAX        INTEGER(1..128)
        MAX-ACCESS  read-create
        STATUS      current
        DESCRIPTION    ""
        ::={a200DLinkOperEntry 8}    
        
    a200DLinkOperIfID      OBJECT-TYPE
        SYNTAX        INTEGER(1..128)
        MAX-ACCESS  read-create
        STATUS      current
        DESCRIPTION    ""
        ::={a200DLinkOperEntry 9}    
        
    a200DLinkOperNumber      OBJECT-TYPE
        SYNTAX        INTEGER(1..8)
        MAX-ACCESS  read-create
        STATUS      current
        DESCRIPTION    ""
        ::={a200DLinkOperEntry 10}    
        
    a200DLinkOperRowStatus      OBJECT-TYPE
        SYNTAX        RowStatus
        MAX-ACCESS  read-create
        STATUS      current
        DESCRIPTION    ""
        ::={a200DLinkOperEntry 11}
        
    a200ISDNPRATable    OBJECT-TYPE
    SYNTAX            SEQUENCE OF  A200ISDNPRAEntry
    MAX-ACCESS        not-accessible
    STATUS          current
    DESCRIPTION        "ISDN-PRA table"
    ::= {a200-mib 36}
    
    a200ISDNPRAEntry    OBJECT-TYPE
    SYNTAX            A200ISDNPRAEntry
    MAX-ACCESS        not-accessible
    STATUS            current
    DESCRIPTION        ""
    INDEX            {a200ISDNPRARack, a200ISDNPRAShelf, a200ISDNPRASlot, a200ISDNPRAE1No, a200ISDNPRAIndex}
    ::= {a200ISDNPRATable 1}

    A200ISDNPRAEntry   ::= SEQUENCE
    {
        a200ISDNPRARack           INTEGER,
        a200ISDNPRAShelf          INTEGER,
        a200ISDNPRASlot           INTEGER,
        a200ISDNPRAE1No           INTEGER,
        a200ISDNPRAIndex          INTEGER,
        a200ISDNPRALinkID         INTEGER,
        a200ISDNPRALinkInfo       INTEGER
    }
       
       a200ISDNPRARack     OBJECT-TYPE
       SYNTAX            INTEGER
       MAX-ACCESS        not-accessible
       STATUS            current
       DESCRIPTION        "rack"
       ::= {a200ISDNPRAEntry 1}
       
       
       a200ISDNPRAShelf     OBJECT-TYPE
       SYNTAX            INTEGER
       MAX-ACCESS        not-accessible
       STATUS            current
       DESCRIPTION        "shelf"
       ::= {a200ISDNPRAEntry 2}
       
       a200ISDNPRASlot     OBJECT-TYPE
       SYNTAX            INTEGER
       MAX-ACCESS        not-accessible
       STATUS            current
       DESCRIPTION        "slot"
       ::= {a200ISDNPRAEntry 3}
       
       a200ISDNPRAE1No     OBJECT-TYPE
       SYNTAX            INTEGER
       MAX-ACCESS        not-accessible
       STATUS            current
       DESCRIPTION        "E1No"
       ::= {a200ISDNPRAEntry 4}
       
       a200ISDNPRAIndex     OBJECT-TYPE
       SYNTAX            INTEGER(0..31)
       MAX-ACCESS        not-accessible
       STATUS            current
       DESCRIPTION        "index"
       ::= {a200ISDNPRAEntry 5}
       
       a200ISDNPRALinkID     OBJECT-TYPE
       SYNTAX            INTEGER(1..512)
       MAX-ACCESS        read-only
       STATUS            current
       DESCRIPTION        "D link ID"
       ::= {a200ISDNPRAEntry 6}
       
       a200ISDNPRALinkInfo     OBJECT-TYPE
       SYNTAX            INTEGER {networkSide(0), subscriberSide(1)}
       MAX-ACCESS        read-only
       STATUS            current
       DESCRIPTION        "other infomations. default value is networkSide(0)"
       ::= {a200ISDNPRAEntry 7}

    a200ISDNPRAOperTable OBJECT-TYPE
        SYNTAX        SEQUENCE OF A200ISDNPRAOperEntry
        MAX-ACCESS    not-accessible
        STATUS      current
        DESCRIPTION    ""
        ::={a200-mib 37}

   a200ISDNPRAOperEntry OBJECT-TYPE
        SYNTAX         A200ISDNPRAOperEntry
        MAX-ACCESS    not-accessible
        STATUS      current
        DESCRIPTION    ""
        INDEX { a200ISDNPRAOperRack, a200ISDNPRAOperShelf, a200ISDNPRAOperSlot,
            a200ISDNPRAOperE1No, a200ISDNPRAOperLinkIdx}
        ::={a200ISDNPRAOperTable 1}

    A200ISDNPRAOperEntry ::=
           SEQUENCE{
               a200ISDNPRAOperRack      INTEGER,
                    a200ISDNPRAOperShelf     INTEGER,
                    a200ISDNPRAOperSlot             INTEGER,
                    a200ISDNPRAOperE1No      INTEGER,
                    a200ISDNPRAOperLinkIdx   INTEGER,
                    a200ISDNPRAOperLinkID    INTEGER,
                    a200ISDNPRAOperLinkInfo  INTEGER,
                    a200ISDNPRAOperASID      INTEGER,
                    a200ISDNPRAOperIfID      INTEGER,
                    a200ISDNPRAOperNumber    INTEGER,
                    a200ISDNPRAOperRowStatus RowStatus
            }           

  a200ISDNPRAOperRack  OBJECT-TYPE
        SYNTAX        INTEGER
        MAX-ACCESS  not-accessible
        STATUS      current
        DESCRIPTION    ""
        ::={a200ISDNPRAOperEntry 1}    
    
    a200ISDNPRAOperShelf  OBJECT-TYPE
        SYNTAX        INTEGER
        MAX-ACCESS  not-accessible
        STATUS      current
        DESCRIPTION    ""
        ::={a200ISDNPRAOperEntry 2}    
        
    a200ISDNPRAOperSlot      OBJECT-TYPE
        SYNTAX        INTEGER
        MAX-ACCESS  not-accessible
        STATUS      current
        DESCRIPTION    ""
        ::={a200ISDNPRAOperEntry 3}
        
    a200ISDNPRAOperE1No      OBJECT-TYPE
        SYNTAX        INTEGER
        MAX-ACCESS  not-accessible
        STATUS      current
        DESCRIPTION    ""
        ::={a200ISDNPRAOperEntry 4}        
        
    a200ISDNPRAOperLinkIdx      OBJECT-TYPE
        SYNTAX        INTEGER(0..31)
        MAX-ACCESS  not-accessible
        STATUS      current
        DESCRIPTION    ""
        ::={a200ISDNPRAOperEntry 5}    
        
    a200ISDNPRAOperLinkID      OBJECT-TYPE
        SYNTAX        INTEGER(1..512)
        MAX-ACCESS  read-create
        STATUS      current
        DESCRIPTION    ""
        ::={a200ISDNPRAOperEntry 6}    
        
    a200ISDNPRAOperLinkInfo      OBJECT-TYPE
        SYNTAX        INTEGER{
            networkSide(0),
            subscriberSide(1)
        }
        MAX-ACCESS  read-create
        STATUS      current
        DESCRIPTION    ""
        ::={a200ISDNPRAOperEntry 7}    
        
    a200ISDNPRAOperASID      OBJECT-TYPE
        SYNTAX        INTEGER(1..127)
        MAX-ACCESS  read-create
        STATUS      current
        DESCRIPTION    ""
        ::={a200ISDNPRAOperEntry 8}    
        
    a200ISDNPRAOperIfID      OBJECT-TYPE
        SYNTAX        INTEGER(1..65535)
        MAX-ACCESS  read-create
        STATUS      current
        DESCRIPTION    ""
        ::={a200ISDNPRAOperEntry 9}    
        
    a200ISDNPRAOperNumber      OBJECT-TYPE
        SYNTAX        INTEGER(1..8)
        MAX-ACCESS  read-create
        STATUS      current
        DESCRIPTION    ""
        ::={a200ISDNPRAOperEntry 10}    
        
    a200ISDNPRAOperRowStatus      OBJECT-TYPE
        SYNTAX        RowStatus
        MAX-ACCESS  read-create
        STATUS      current
        DESCRIPTION    ""
        ::={a200ISDNPRAOperEntry 11}





--END OF TABLE DEFINATION
----------------------------------------------

-- TRAP RELATED DEFINATION BEGIN
    a200trap OBJECT IDENTIFIER ::= { a200-mib 50 }
    
    a200alarmtrap  NOTIFICATION-TYPE
        OBJECTS {
            a200alarmId,
            a200alarmCode,
            a200alarmLevel,
            a200alarmReason,                        
            a200alarmTime,
            a200alarmModuleNo,
            a200alarmPostionMode,
            a200alarmRackNo,
            a200alarmShelfNo,
            a200alarmSlotNo,
            a200alarmMoreInfo
              }
      STATUS    current
      DESCRIPTION "\u544a\u8b66trap \u7528\u4e8e\u62a5\u544aMG\u4e2d\u53d1\u751f\u7684\u6545\u969c"
      ::= {a200trap 1}

    a200alarmrestoretrap  NOTIFICATION-TYPE
        OBJECTS {
            a200alarmId,
            a200alarmTime,
            a200alarmModuleNo,
            a200alarmPostionMode,
            a200alarmRackNo,
            a200alarmShelfNo,
            a200alarmSlotNo,
      a200alarmState,
            a200alarmCheckSum            
              }
      STATUS    current
      DESCRIPTION "\u544a\u8b66\u6062\u590dtrap\uff0c\u7528\u4e8e\u590d\u4f4d\u5148\u524d\u53d1\u751f\u7684\u544a\u8b66"
      ::= {a200trap 2}

    a200notifytrap  NOTIFICATION-TYPE
        OBJECTS {
            a200alarmId,
            a200alarmCode,
            a200alarmLevel,
            a200alarmReason,                        
            a200alarmTime,
            a200alarmModuleNo,
            a200alarmPostionMode,
            a200alarmRackNo,
            a200alarmShelfNo,
            a200alarmSlotNo,
            a200notifyMoreInfo
              }
      STATUS    current
      DESCRIPTION "\u901a\u77e5trap \u4e0a\u62a5MG\u4e2d\u53d1\u751f\u7684\u4e00\u4e9b\u4e8b\u4ef6\uff0c\u4e0d\u7528\u6062\u590d"
      ::= {a200trap 3}

    a200trapbindobj OBJECT IDENTIFIER ::= { a200-mib 51 }
    
    a200alarmId     OBJECT-TYPE
        SYNTAX        INTEGER
        MAX-ACCESS  accessible-for-notify
        STATUS      current
        DESCRIPTION    "\u544a\u8b66id, \u544a\u8b66\u8fdb\u7a0b\u4ea7\u751f,\u7528\u4e8e\u6807\u8bb0\u4e00\u6b21\u544a\u8b66, 
                \u4e5f\u4f5c\u4e3a\u544a\u8b66\u590d\u4f4d\u65f6\u6807\u8bc6\u5f85\u590d\u4f4d\u544a\u8b66\u7684\u4f9d\u636e"
        ::={ a200trapbindobj 1 }
        
    a200alarmCode   OBJECT-TYPE
        SYNTAX        INTEGER
        MAX-ACCESS  accessible-for-notify
        STATUS      current
        DESCRIPTION    "\u544a\u8b66\u7801\uff0c\u7528\u4e8e\u6807\u8bc6\u544a\u8b66\u4e8b\u4ef6"
        ::={ a200trapbindobj 2 }
            
    a200alarmLevel  OBJECT-TYPE
        SYNTAX        INTEGER
        MAX-ACCESS  accessible-for-notify
        STATUS      current
        DESCRIPTION    "\u544a\u8b66\u7b49\u7ea7\uff0c\u8868\u793a\u544a\u8b66\u7684\u4e25\u91cd\u7a0b\u5ea6\uff0c\u53d6\u503c\uff08 1--4 \uff09, 1\u7ea7\u6700\u4e25\u91cd "
        ::={ a200trapbindobj 3 }

    a200alarmReason  OBJECT-TYPE
        SYNTAX        INTEGER
        MAX-ACCESS  accessible-for-notify
        STATUS      current
        DESCRIPTION    "\u544a\u8b66\u539f\u56e0"
        ::={ a200trapbindobj 4 }
        
    a200alarmTime  OBJECT-TYPE
        SYNTAX        Counter32
        MAX-ACCESS  accessible-for-notify
        STATUS      current
        DESCRIPTION    "\u544a\u8b66\u65f6\u95f4\uff08\u81ea2000\u5e741\u67081\u65e50\u65f6\u901d\u53bb\u7684\u79d2\u6570\uff09"
        ::={ a200trapbindobj 5 }

    a200alarmModuleNo  OBJECT-TYPE
        SYNTAX        INTEGER
        MAX-ACCESS  accessible-for-notify
        STATUS      current
        DESCRIPTION    "\u53d1\u51fa\u544a\u8b66\u7684\u6a21\u5757\u7684\u6a21\u5757\u53f7"
        ::={ a200trapbindobj 6 }
    
    a200alarmPostionMode  OBJECT-TYPE
        SYNTAX        INTEGER
        MAX-ACCESS  accessible-for-notify
        STATUS      current
        DESCRIPTION    "\u544a\u8b66\u662f\u5426\u9644\u52a0\u673a\u67b6\u4f4d\u7f6e: =0 \u65e0\u4f4d\u7f6e, =1 \u6709\u4f4d\u7f6e"
        ::={ a200trapbindobj 7 }
        
    a200alarmRackNo  OBJECT-TYPE
        SYNTAX        INTEGER
        MAX-ACCESS  accessible-for-notify
        STATUS      current
        DESCRIPTION    " \u5f53 a200alarmPostionMode=1\u65f6\uff0c \u544a\u8b66\u6e90\u6240\u5728\u673a\u67b6"
        ::={ a200trapbindobj 8 }
        
    a200alarmShelfNo  OBJECT-TYPE
        SYNTAX        INTEGER
        MAX-ACCESS  accessible-for-notify
        STATUS      current
        DESCRIPTION    "\u5f53 a200alarmPostionMode=1\u65f6\uff0c \u544a\u8b66\u6e90\u6240\u5728\u673a\u6846"
        ::={ a200trapbindobj 9 }
    
    a200alarmSlotNo  OBJECT-TYPE
        SYNTAX        INTEGER
        MAX-ACCESS  accessible-for-notify
        STATUS      current
        DESCRIPTION    "\u5f53 a200alarmPostionMode=1\u65f6\uff0c \u544a\u8b66\u6e90\u6240\u5728\u69fd\u4f4d"
        ::={ a200trapbindobj 10 }
        
    a200alarmState  OBJECT-TYPE
        SYNTAX        INTEGER
        MAX-ACCESS  accessible-for-notify
        STATUS      current
        DESCRIPTION    "\u544a\u8b66\u6062\u590d\u65f6\u7535\u8def\u677f\u7684\u72b6\u6001"
        ::={ a200trapbindobj 11 }
    
    a200alarmCheckSum  OBJECT-TYPE
        SYNTAX        INTEGER
        MAX-ACCESS  accessible-for-notify
        STATUS      current
        DESCRIPTION    "\u6821\u9a8c\u548c"
        ::={ a200trapbindobj 12 } 
        
    a200alarmMoreInfo  OBJECT-TYPE
        SYNTAX        OCTET STRING (SIZE (0..30))
        MAX-ACCESS  accessible-for-notify
        STATUS      current
        DESCRIPTION    " \u544a\u8b66\u9644\u52a0\u4fe1\u606f"
        ::={ a200trapbindobj 13 } 
        
    a200notifyMoreInfo  OBJECT-TYPE
        SYNTAX        OCTET STRING (SIZE (0..60))
        MAX-ACCESS  accessible-for-notify
        STATUS      current
        DESCRIPTION    " \u901a\u77e5\u9644\u52a0\u4fe1\u606f"
        ::={ a200trapbindobj 14 }               
        
-- System-Control Related Operation(e.g. get the status of H.248 link, reboot a board, ...) MIB
-- Created by WuFeng
-- Date of creation : 2004.10.10

    msagSysCtrl OBJECT IDENTIFIER ::= { a200-mib 100 }
    
    h248LinkStatus              OBJECT-TYPE
        SYNTAX                  INTEGER {linkup(0), linkdown(1)}
        MAX-ACCESS              read-only
        STATUS                  current
        DESCRIPTION             "H248 Link status, a scalar object"
        ::=  {msagSysCtrl   1}
    
    
--Start of msagSlcCtrlTable

    msagSlcCtrlTable OBJECT-TYPE
        SYNTAX        SEQUENCE OF MsagSlcCtrlEntry
        MAX-ACCESS    not-accessible
        STATUS      current
        DESCRIPTION    ""
        ::={msagSysCtrl 5}

   msagSlcCtrlEntry OBJECT-TYPE
        SYNTAX        MsagSlcCtrlEntry
        MAX-ACCESS    not-accessible
        STATUS      current
        DESCRIPTION    ""
        INDEX {msagSlcCtrlRack, msagSlcCtrlShelf, msagSlcCtrlSlot, msagSlcBegin,msagSlcEnd}
        ::={msagSlcCtrlTable 1}

    MsagSlcCtrlEntry ::=
           SEQUENCE{
               msagSlcCtrlRack               INTEGER,
               msagSlcCtrlShelf              INTEGER,
               msagSlcCtrlSlot               INTEGER,
               msagSlcBegin                  INTEGER,
               msagSlcEnd                    INTEGER,
               msagSlcBlockOper              INTEGER,
               msagSlcUnblockOper            INTEGER,
               msagSlcHighImpedanceOper      INTEGER,
               msagSlcNoneHighImpedanceOper  INTEGER
        }
        
    msagSlcCtrlRack  OBJECT-TYPE
        SYNTAX        INTEGER
        MAX-ACCESS  not-accessible
        STATUS      current
        DESCRIPTION    ""
        ::={msagSlcCtrlEntry 1}    
    
    msagSlcCtrlShelf   OBJECT-TYPE
        SYNTAX        INTEGER
        MAX-ACCESS  not-accessible
        STATUS      current
        DESCRIPTION    ""
        ::={msagSlcCtrlEntry 2}    
    
    msagSlcCtrlSlot   OBJECT-TYPE
        SYNTAX        INTEGER
        MAX-ACCESS  not-accessible
        STATUS      current
        DESCRIPTION    ""
        ::={msagSlcCtrlEntry 3}    
    
    msagSlcBegin  OBJECT-TYPE
        SYNTAX        INTEGER
        MAX-ACCESS  not-accessible
        STATUS      current
        DESCRIPTION    "start circuit No."
        ::={msagSlcCtrlEntry 4}
    
    msagSlcEnd     OBJECT-TYPE
        SYNTAX        INTEGER
        MAX-ACCESS  not-accessible
        STATUS      current
        DESCRIPTION    "end of the circuit No. , should be larger or equal to msagSlcBegin"
        ::={msagSlcCtrlEntry 5}

    msagSlcBlockOper     OBJECT-TYPE
        SYNTAX        INTEGER(1)
        MAX-ACCESS  read-write
        STATUS      current
        DESCRIPTION    "block slc"
        ::={msagSlcCtrlEntry 6}
        
        
    msagSlcUnblockOper     OBJECT-TYPE
        SYNTAX        INTEGER(1)
        MAX-ACCESS  read-write
        STATUS      current
        DESCRIPTION    "unblock slc"
        ::={msagSlcCtrlEntry 7}
        
    msagSlcHighImpedanceOper     OBJECT-TYPE
        SYNTAX        INTEGER(1)
        MAX-ACCESS    read-write
        STATUS        current
        DESCRIPTION   "Set slc to high-impedance state."
        ::={msagSlcCtrlEntry 8}
        
    msagSlcNoneHighImpedanceOper     OBJECT-TYPE
        SYNTAX        INTEGER(1)
        MAX-ACCESS    read-write
        STATUS        current
        DESCRIPTION   "Set slc to none high-impedance state."
        ::={msagSlcCtrlEntry 9}
        
--End of msagSlcCtrlTable

--Start of msagIpsCtrlTable

    msagIpsCtrlTable OBJECT-TYPE
        SYNTAX        SEQUENCE OF MsagIpsCtrlEntry
        MAX-ACCESS    not-accessible
        STATUS      current
        DESCRIPTION    ""
        ::={msagSysCtrl 6}

   msagIpsCtrlEntry OBJECT-TYPE
        SYNTAX        MsagIpsCtrlEntry
        MAX-ACCESS    not-accessible
        STATUS      current
        DESCRIPTION    ""
        INDEX {msagIpsBegin,msagIpsEnd}
        ::={msagIpsCtrlTable 1}

    MsagIpsCtrlEntry ::=
           SEQUENCE{
               msagIpsBegin          INTEGER,
               msagIpsEnd            INTEGER,
            msagIpsBlockOper      INTEGER,
            msagIpsUnblockOper    INTEGER
        }
        
   
    msagIpsBegin  OBJECT-TYPE
        SYNTAX        INTEGER
        MAX-ACCESS  not-accessible
        STATUS      current
        DESCRIPTION    "start circuit No."
        ::={msagIpsCtrlEntry 5}
    
    msagIpsEnd     OBJECT-TYPE
        SYNTAX        INTEGER
        MAX-ACCESS  not-accessible
        STATUS      current
        DESCRIPTION    "end of the circuit No. , should be larger or equal to msagIpsBegin"
        ::={msagIpsCtrlEntry 6}

    msagIpsBlockOper     OBJECT-TYPE
        SYNTAX        INTEGER(1)
        MAX-ACCESS  read-write
        STATUS      current
        DESCRIPTION    "block ips"
        ::={msagIpsCtrlEntry 7}
        
        
    msagIpsUnblockOper     OBJECT-TYPE
        SYNTAX        INTEGER(1)
        MAX-ACCESS  read-write
        STATUS      current
        DESCRIPTION    "unblock ips"
        ::={msagIpsCtrlEntry 8}
        
--End of msagIpsCtrlTable

--Start of msagDspCtrlTable

    msagDspCtrlTable OBJECT-TYPE
        SYNTAX        SEQUENCE OF MsagDspCtrlEntry
        MAX-ACCESS    not-accessible
        STATUS      current
        DESCRIPTION    ""
        ::={msagSysCtrl 7}

   msagDspCtrlEntry OBJECT-TYPE
        SYNTAX        MsagDspCtrlEntry
        MAX-ACCESS    not-accessible
        STATUS      current
        DESCRIPTION    ""
        INDEX {msagDspCtrlRack, msagDspCtrlShelf, msagDspCtrlSlot, msagDspNo, msagDspBegin,msagDspEnd}
        ::={msagDspCtrlTable 1}

    MsagDspCtrlEntry ::=
           SEQUENCE{
               msagDspCtrlRack       INTEGER,
               msagDspCtrlShelf      INTEGER,
               msagDspCtrlSlot       INTEGER,
               msagDspNo             INTEGER,
               msagDspBegin          INTEGER,
               msagDspEnd            INTEGER,
            msagDspBlockOper      INTEGER,
            msagDspUnblockOper    INTEGER
        }
        
    msagDspCtrlRack  OBJECT-TYPE
        SYNTAX        INTEGER
        MAX-ACCESS  not-accessible
        STATUS      current
        DESCRIPTION    ""
        ::={msagDspCtrlEntry 1}    
    
    msagDspCtrlShelf   OBJECT-TYPE
        SYNTAX        INTEGER
        MAX-ACCESS  not-accessible
        STATUS      current
        DESCRIPTION    ""
        ::={msagDspCtrlEntry 2}    
    
    msagDspCtrlSlot   OBJECT-TYPE
        SYNTAX        INTEGER
        MAX-ACCESS  not-accessible
        STATUS      current
        DESCRIPTION    ""
        ::={msagDspCtrlEntry 3}    
    
    msagDspNo    OBJECT-TYPE
        SYNTAX        INTEGER
        MAX-ACCESS  not-accessible
        STATUS      current
        DESCRIPTION    ""
        ::={msagDspCtrlEntry 4}    
    
    msagDspBegin  OBJECT-TYPE
        SYNTAX        INTEGER
        MAX-ACCESS  not-accessible
        STATUS      current
        DESCRIPTION    "start circuit No."
        ::={msagDspCtrlEntry 5}
    
    msagDspEnd     OBJECT-TYPE
        SYNTAX        INTEGER
        MAX-ACCESS  not-accessible
        STATUS      current
        DESCRIPTION    "end of the circuit No. , should be larger or equal to msagDspBegin"
        ::={msagDspCtrlEntry 6}

    msagDspBlockOper     OBJECT-TYPE
        SYNTAX        INTEGER(1)
        MAX-ACCESS  read-write
        STATUS      current
        DESCRIPTION    "block dsp"
        ::={msagDspCtrlEntry 7}
        
        
    msagDspUnblockOper     OBJECT-TYPE
        SYNTAX        INTEGER(1)
        MAX-ACCESS  read-write
        STATUS      current
        DESCRIPTION    "unblock dsp"
        ::={msagDspCtrlEntry 8}

--End of msagDspCtrlTable

--Start of msagConfCtrlTable

    msagConfCtrlTable OBJECT-TYPE
        SYNTAX        SEQUENCE OF MsagConfCtrlEntry
        MAX-ACCESS    not-accessible
        STATUS      current
        DESCRIPTION    ""
        ::={msagSysCtrl 8}

   msagConfCtrlEntry OBJECT-TYPE
        SYNTAX        MsagConfCtrlEntry
        MAX-ACCESS    not-accessible
        STATUS      current
        DESCRIPTION    ""
        INDEX {msagConfCtrlRack, msagConfCtrlShelf, msagConfCtrlSlot, msagConfBegin,msagConfEnd,msagConfSubdevNo}
        ::={msagConfCtrlTable 1}

    MsagConfCtrlEntry ::=
           SEQUENCE{
               msagConfCtrlRack       INTEGER,
               msagConfCtrlShelf      INTEGER,
               msagConfCtrlSlot       INTEGER,
               msagConfBegin          INTEGER,
               msagConfEnd            INTEGER,
              msagConfBlockOper      INTEGER,
              msagConfUnblockOper    INTEGER,
              msagConfSubdevNo       INTEGER 
        }
        
    msagConfCtrlRack  OBJECT-TYPE
        SYNTAX        INTEGER
        MAX-ACCESS  not-accessible
        STATUS      current
        DESCRIPTION    ""
        ::={msagConfCtrlEntry 1}    
    
    msagConfCtrlShelf   OBJECT-TYPE
        SYNTAX        INTEGER
        MAX-ACCESS  not-accessible
        STATUS      current
        DESCRIPTION    ""
        ::={msagConfCtrlEntry 2}    
    
    msagConfCtrlSlot   OBJECT-TYPE
        SYNTAX        INTEGER
        MAX-ACCESS  not-accessible
        STATUS      current
        DESCRIPTION    ""
        ::={msagConfCtrlEntry 3}    
    
    msagConfBegin  OBJECT-TYPE
        SYNTAX        INTEGER
        MAX-ACCESS  not-accessible
        STATUS      current
        DESCRIPTION    "start circuit No."
        ::={msagConfCtrlEntry 4}
    
    msagConfEnd     OBJECT-TYPE
        SYNTAX        INTEGER
        MAX-ACCESS  not-accessible
        STATUS      current
        DESCRIPTION    "end of the circuit No. , should be larger or equal to msagConfBegin"
        ::={msagConfCtrlEntry 5}

    msagConfBlockOper     OBJECT-TYPE
        SYNTAX        INTEGER(1)
        MAX-ACCESS  read-write
        STATUS      current
        DESCRIPTION    "block conferrence"
        ::={msagConfCtrlEntry 6}
        
        
    msagConfUnblockOper     OBJECT-TYPE
        SYNTAX        INTEGER(1)
        MAX-ACCESS  read-write
        STATUS      current
        DESCRIPTION    "unblock conferrence"
        ::={msagConfCtrlEntry 7}
        
        msagConfSubdevNo  OBJECT-TYPE
        SYNTAX        INTEGER
        MAX-ACCESS  not-accessible
        STATUS      current
        DESCRIPTION    ""
        ::={msagConfCtrlEntry 8}

--End of msagConfCtrlTable

    msagTransferVer    OBJECT-TYPE
        SYNTAX        OCTET STRING(SIZE(9..80))
        MAX-ACCESS  read-write
        STATUS      current
        DESCRIPTION "
                      msagTransferVer provides a mechanism that 
                    we can transfer version files from a specific
                    ftp server to MSAG.
                      msagTransferVer is NOT available for READ
                    operation.
                    
                      This object is made up of ftp server's ip and
                    the name of version file. A '@' mark is used to seperate
                    the ip and the name.
                    
                   Example:
                      10.61.90.100@\ver\adlg.bin

                      Both username and password on the ftp server
                    are 'zte'(excluded single quotations)
                    "
        ::={msagSysCtrl 9}

        
    msagLoadVer     OBJECT-TYPE
        SYNTAX        OCTET STRING(SIZE(4))
        MAX-ACCESS  read-write
        STATUS      current
        DESCRIPTION "
                      msagLoadVer provide a mechanism that we 
                    can manully inform the MSAG to load version
                    to a specific board(e.g. adlg, ICS...)
                    
                      msagLoadVer is NOT available for READ operation.
                      
                      BYTE 1 = rack  NO.
                      BYTE 2 = shelf NO.
                      BYTE 3 = slot  NO.
                      BYTE 4 = subcard flag. CPU(0),
                    89C52[or 8031](1), FPGA(2)  CNIC(3)
                      
                      BYTE 4 must be present when the board is
                    ICS. For the other boards, BYTE 4 are ignored.
                    
                      When manager SET this object to agent,
                    a specific board will load version from
                    the main ICS which reside in master
                    frame(shelf).
                    "
        ::={msagSysCtrl 10}
    
    msagSyncVer     OBJECT-TYPE
        SYNTAX        OCTET STRING(SIZE(0..32))
        MAX-ACCESS  read-write
        STATUS      current
        DESCRIPTION "
                      msagSyncVer provide a mechanism that transfer
                    a version file from main ICS(on master shelf)
                    to backup ICS(on master shelf).
                    
                      msagSyncVer is NOT available for READ operation.
                      
                      The value of msagSyncVer is the file name.
                    
                      When manager SET this object to agent,
                    the version file will be synchronized to
                    backup ICS.
                    "
        ::={msagSysCtrl 11}

    msagSystemReboot            OBJECT-TYPE
        SYNTAX                  OCTET STRING(SIZE(4))
        MAX-ACCESS              read-write
        STATUS                  current
        DESCRIPTION             "
                                This object is write-only.
                                Make MSAG system reboot or a slave shelf reboot.
                                BYTE 1 = rack
                                BYTE 2 = shelf
                                BYTE 3 = slot
                                BYTE 4: reserved
                                
                                Example:
                                1.Set [1][3][9][] will make master shelf to reset(MSAG system reboot)
                                2.Set [1][3][10][] will make master shelf to reset(MSAG system reboot)
                                3.Set [1][1][9][] will make slave shelf 1 to reset(slave shelf reboot)
                                4.Set [1][1][10][] will make slave shelf 1 to reset(slave shelf reboot)
                                "
        ::={msagSysCtrl 12}


    msagMasterCpuAlarmThreshold  OBJECT-TYPE
        SYNTAX                  INTEGER(1..99)
        MAX-ACCESS              read-write
        STATUS                  current
        DESCRIPTION             "
                                Read & set the threshold of MASTER CPU.
                                A MASTER CPU too-busy alarm will be produced when
                                the cpu rate is higher than the threshold.
                                "
        ::={msagSysCtrl 13}

    msagSlaveCpuAlarmThreshold  OBJECT-TYPE
        SYNTAX                  INTEGER(1..99)
        MAX-ACCESS              read-write
        STATUS                  current
        DESCRIPTION             "
                                Read & set the threshold of SLAVE CPU(8031).
                                A SLAVE CPU too-busy alarm will be produced when
                                the cpu rate is higher than the threshold.
                                "
        ::={msagSysCtrl 14}
        
    msagVersion OBJECT-TYPE
          SYNTAX      DisplayString (SIZE (0..10))
          MAX-ACCESS  read-only
          STATUS      current
            DESCRIPTION    "The version of SNMP Agent"
            ::= { msagSysCtrl 15 } 
            
   msagTimeZone OBJECT-TYPE
        SYNTAX                  INTEGER(0..24)
        MAX-ACCESS              read-write
        STATUS                  current
        DESCRIPTION             "The time zone"
        ::={msagSysCtrl 16}
   
   msagNTPIPAddr OBJECT-TYPE
        SYNTAX      IpAddress
        MAX-ACCESS  read-write
        STATUS      current
        DESCRIPTION "The IP address of NTP Server"                 
        ::= { msagSysCtrl 17 }
            
   msagGetVersionList OBJECT-TYPE
    SYNTAX      OCTET STRING(SIZE(4))
    MAX-ACCESS  read-write
        STATUS      current
        DESCRIPTION "
                    This object is write-only.
                    Refresh the list of version files stored in MSAG flash.
                    SNMP manager can read the list at any time after doing
                    the refresh operation.
                    
                    Access the list via msagVersionListTable.
                    
                    Set the value with the SPN(rack-shelf-slot) of the
                    board on which the version files reside will cause a refresh action.

                    BYTE 1 = rack
                    BYTE 2 = shelf
                    BYTE 3 = slot
                    BYTE 4 : reserved
                    
                    Examples:
                    1. Set [1][3][9][] will refresh the version file list on ICS board 1-3-9
                    2. Set [1][1][10][] will refresh slave shelf ICS board 1-1-10
                    "
        ::={msagSysCtrl  18}

    msagVersionListTable OBJECT-TYPE
        SYNTAX        SEQUENCE OF MsagVersionListTableEntry
        MAX-ACCESS    not-accessible
        STATUS      current
        DESCRIPTION    ""
        ::={msagSysCtrl 19} 

    msagVersionListTableEntry OBJECT-TYPE
        SYNTAX        MsagVersionListTableEntry
        MAX-ACCESS    not-accessible
        STATUS      current
        DESCRIPTION    ""
        INDEX {msagVersionListRack, msagVersionListShelf, msagVersionListSlot, msagVersionListEntry}
        ::={msagVersionListTable 1}

      MsagVersionListTableEntry ::=
           SEQUENCE{
               msagVersionListRack       INTEGER,
               msagVersionListShelf      INTEGER,
               msagVersionListSlot       INTEGER,
               msagVersionListEntry      INTEGER,
               msagVersionContent        DisplayString
        }

    msagVersionListRack  OBJECT-TYPE
        SYNTAX        INTEGER(1)
        MAX-ACCESS  not-accessible
        STATUS      current
        DESCRIPTION    ""
        ::={msagVersionListTableEntry 1}    
    
      msagVersionListShelf   OBJECT-TYPE
        SYNTAX        INTEGER(1..5)
        MAX-ACCESS  not-accessible
        STATUS      current
        DESCRIPTION    ""
        ::={msagVersionListTableEntry 2}    
    
      msagVersionListSlot   OBJECT-TYPE
        SYNTAX        INTEGER(9..10)
        MAX-ACCESS  not-accessible
        STATUS      current
        DESCRIPTION    ""
        ::={msagVersionListTableEntry 3}    
    
    msagVersionListEntry  OBJECT-TYPE
        SYNTAX        INTEGER(0..999)
        MAX-ACCESS  not-accessible
        STATUS      current
        DESCRIPTION    "Version List Entry, Entry 0 never exists, used to mark the start"
        ::={msagVersionListTableEntry 4}

    msagVersionContent  OBJECT-TYPE
        SYNTAX        DisplayString
        MAX-ACCESS  read-only
        STATUS      current
        DESCRIPTION    "Version List Entry"
        ::={msagVersionListTableEntry 5}
        
        msagExchangeVersion OBJECT-TYPE
        SYNTAX        INTEGER(9..10)
        MAX-ACCESS    read-write
        STATUS      current
        DESCRIPTION    "write only
                     9:exchange the main cpu version at 9 slot, 
                     10:exchange the main cpu version at 10 slot"
        ::={msagSysCtrl 20} 
        
        msagSetResult OBJECT-TYPE
        SYNTAX        INTEGER
        MAX-ACCESS    read-only
        STATUS      current
        DESCRIPTION    "the error code"
        ::={msagSysCtrl 21}
        
        msagTransferVerResult OBJECT-TYPE
    SYNTAX        INTEGER
        MAX-ACCESS  read-only
        STATUS      current
        DESCRIPTION    ""
        ::={msagSysCtrl 22}
        
    msagLoadADLGVerResult OBJECT-TYPE
    SYNTAX        DisplayString (SIZE (0..32))
        MAX-ACCESS  read-only
        STATUS      current
        DESCRIPTION    ""
        ::={msagSysCtrl 23}
        
    msagLoadMPRVerResult OBJECT-TYPE
    SYNTAX        DisplayString (SIZE (0..32))
        MAX-ACCESS  read-only
        STATUS      current
        DESCRIPTION    ""
        ::={msagSysCtrl 24}
        
    msagLoadSlaveICSVerResult OBJECT-TYPE
    SYNTAX        DisplayString (SIZE (0..32))
        MAX-ACCESS  read-only
        STATUS      current
        DESCRIPTION    ""
        ::={msagSysCtrl 25}
        
    msagSyncVerResult OBJECT-TYPE
    SYNTAX        DisplayString (SIZE (0..32))
        MAX-ACCESS  read-only
        STATUS      current
        DESCRIPTION    ""
        ::={msagSysCtrl 26}
        
        
        msagV5IntfaceResult OBJECT-TYPE
    SYNTAX        INTEGER
        MAX-ACCESS  read-only
        STATUS      current
        DESCRIPTION    ""
        ::={msagSysCtrl 28}
        
        msagV5LinkResult OBJECT-TYPE
    SYNTAX        INTEGER
        MAX-ACCESS  read-only
        STATUS      current
        DESCRIPTION    ""
        ::={msagSysCtrl 29}
        
        msagh248ConnMGCInfo  OBJECT-TYPE
    SYNTAX        DisplayString(SIZE(0..32)) 
        MAX-ACCESS  read-only
        STATUS      current
        DESCRIPTION    ""
        ::={msagSysCtrl 30}
        
        
        msagServiceH248  OBJECT-TYPE
    SYNTAX         INTEGER{notSupport(0),support(1)}
        MAX-ACCESS  read-only
        STATUS      current
        DESCRIPTION    ""
        ::={msagSysCtrl 32}
        
        msagServiceMGCP  OBJECT-TYPE
    SYNTAX         INTEGER{notSupport(0),support(1)}
        MAX-ACCESS  read-only
        STATUS      current
        DESCRIPTION    ""
        ::={msagSysCtrl 33}
        
        msagServiceV5  OBJECT-TYPE
    SYNTAX         INTEGER{notSupport(0),support(1)}
        MAX-ACCESS  read-only
        STATUS      current
        DESCRIPTION    ""
        ::={msagSysCtrl 34}
        
        msagServiceISDN  OBJECT-TYPE
    SYNTAX         INTEGER{notSupport(0),support(1)}
        MAX-ACCESS  read-only
        STATUS      current
        DESCRIPTION    ""
        ::={msagSysCtrl 35}

        msagSaveDbResult OBJECT-TYPE
            SYNTAX        INTEGER
        MAX-ACCESS  read-only
        STATUS      current
        DESCRIPTION    ""
        ::={msagSysCtrl 36}
        
        
        
        msagSaveData  OBJECT-TYPE
    SYNTAX         INTEGER{
      mainControlBoard(0),
      backControlBoard(1),
      allControlBoard(2)
      }
        MAX-ACCESS  read-write
        STATUS      current
        DESCRIPTION    ""
        ::={msagSysCtrl 38}
        
        
        msagNTPBACKIPAddr    OBJECT-TYPE
                SYNTAX         IpAddress
        MAX-ACCESS  read-write
        STATUS      current
        DESCRIPTION    ""
        ::={msagSysCtrl 40}
        
        msagNTPCURNTIP     OBJECT-TYPE
                SYNTAX         INTEGER{useMainNTPIp(1),useBackNTPIp(2)}
        MAX-ACCESS  read-write
        STATUS      current
        DESCRIPTION    ""
        ::={msagSysCtrl 41}
        
        
        msagFixToneType  OBJECT-TYPE
    SYNTAX         INTEGER{dsp(1),ips(2)}
        MAX-ACCESS  read-write
        STATUS      current
        DESCRIPTION    ""
        ::={msagSysCtrl 43}
        
        msagCallStatis OBJECT-TYPE
        SYNTAX        OCTET STRING (SIZE (0..1002))
        MAX-ACCESS  read-only
        STATUS      current
        DESCRIPTION    ""
        ::={msagSysCtrl 44}

    msagToneArea     OBJECT-TYPE
        SYNTAX      INTEGER
            {
                mainLand(1),
                hongKong(2),
                singaPore(3),
                russia(4),
                belgium(5),
                saudi(6)
            }
        MAX-ACCESS  read-write
        STATUS      current
        DESCRIPTION    "Tone area"
        ::={msagSysCtrl 45}
        
    
    msagAlerm2CSV  OBJECT-TYPE
        SYNTAX         INTEGER{disable(0),enable(1)}
        MAX-ACCESS  read-write
        STATUS      current
        DESCRIPTION    ""
        ::={msagSysCtrl 47}    

    msagSwitchMGC  OBJECT-TYPE
        SYNTAX         INTEGER(1..4)
        MAX-ACCESS  read-write
        STATUS      current
        DESCRIPTION    ""
        ::={msagSysCtrl 48}


    msagAccessRatio  OBJECT-TYPE
        SYNTAX         DisplayString(SIZE(1..32))
        MAX-ACCESS  read-only
        STATUS      current
        DESCRIPTION    ""
        ::={msagSysCtrl 49}
        
    msagNTPThrshld  OBJECT-TYPE
    SYNTAX         INTEGER(7..65535)
        MAX-ACCESS  read-write
        STATUS      current
        DESCRIPTION    ""
        ::={msagSysCtrl 50}
        
        
    msagUPLKDTCTIL OBJECT-TYPE
        SYNTAX                  INTEGER
        MAX-ACCESS              read-write
        STATUS                  current
        DESCRIPTION             ""
        ::={msagSysCtrl 51}
        
  msagUPLKDTCTCT OBJECT-TYPE
        SYNTAX                  INTEGER
        MAX-ACCESS              read-write
        STATUS                  current
        DESCRIPTION             ""
        ::={msagSysCtrl 52}
        
        
        
  msagBatchLoadVer OBJECT-TYPE
        SYNTAX                  OCTET STRING(SIZE(5))
        MAX-ACCESS              read-write
        STATUS                  current
        DESCRIPTION             ""
        ::={msagSysCtrl 55}


    msagBoardDownloadResultTable OBJECT-TYPE
    SYNTAX    SEQUENCE OF MsagBoardDownloadResultEntry
    MAX-ACCESS  not-accessible
    STATUS    current
    DESCRIPTION  ""
    ::={msagSysCtrl 56}

    msagBoardDownloadResultEntry OBJECT-TYPE
    SYNTAX      MsagBoardDownloadResultEntry
    MAX-ACCESS  not-accessible
    STATUS      current
    DESCRIPTION ""
    INDEX {msagBDRRack, msagBDRShelf, msagBDRSlot}
    ::={msagBoardDownloadResultTable 1}

    MsagBoardDownloadResultEntry ::=
       SEQUENCE{
           msagBDRRack       INTEGER,
           msagBDRShelf      INTEGER,
           msagBDRSlot       INTEGER,
           msagBDRResult     DisplayString
    }

    msagBDRRack  OBJECT-TYPE
    SYNTAX      INTEGER(1)
    MAX-ACCESS  not-accessible
    STATUS      current
    DESCRIPTION ""
    ::={msagBoardDownloadResultEntry 1}

    msagBDRShelf   OBJECT-TYPE
    SYNTAX      INTEGER(0..4)
    MAX-ACCESS  not-accessible
    STATUS      current
    DESCRIPTION ""
    ::={msagBoardDownloadResultEntry 2}

    msagBDRSlot   OBJECT-TYPE
    SYNTAX      INTEGER(3..16)
    MAX-ACCESS  not-accessible
    STATUS      current
    DESCRIPTION ""
    ::={msagBoardDownloadResultEntry 3}

    msagBDRResult  OBJECT-TYPE
    SYNTAX      DisplayString
    MAX-ACCESS  read-only
    STATUS      current
    DESCRIPTION "Board Download Result"
    ::={msagBoardDownloadResultEntry 4}

 
  msagCharge16KCWidth OBJECT-TYPE
        SYNTAX                  Unsigned32
        MAX-ACCESS              read-write
        STATUS                  current
        DESCRIPTION             ""
        ::={msagSysCtrl 57}
        
  msagCharge16KCInterval OBJECT-TYPE
        SYNTAX                  Unsigned32
        MAX-ACCESS              read-write
        STATUS                  current
        DESCRIPTION             ""
        ::={msagSysCtrl 58}
        
   msagCharge16KCVol OBJECT-TYPE
        SYNTAX                  INTEGER
        MAX-ACCESS              read-write
        STATUS                  current
        DESCRIPTION             ""
        ::={msagSysCtrl 59}
            
   msagCallLimit OBJECT-TYPE
        SYNTAX                  INTEGER{limitByMg(1),limitByMgc(2),unLimit(3)}
        MAX-ACCESS              read-write
        STATUS                  current
        DESCRIPTION             ""
        ::={msagSysCtrl 60} 
   
   msagCpuBsLimit OBJECT-TYPE
        SYNTAX                  INTEGER{disable(2),enable(1)}
        MAX-ACCESS              read-write
        STATUS                  current
        DESCRIPTION             ""
        ::={msagSysCtrl 61} 
         
   msagUPortLimit OBJECT-TYPE
        SYNTAX                  INTEGER{disable(2),enable(1)}
        MAX-ACCESS              read-write
        STATUS                  current
        DESCRIPTION             ""
        ::={msagSysCtrl 62} 
   
   msagIpsLimit OBJECT-TYPE
        SYNTAX                  INTEGER{disable(2),enable(1)}
        MAX-ACCESS              read-write
        STATUS                  current
        DESCRIPTION             ""
        ::={msagSysCtrl 63}         
        
   h248StatistcRecMsg OBJECT-TYPE
        SYNTAX                  Unsigned32
        MAX-ACCESS              read-only
        STATUS                  current
        DESCRIPTION             ""
        ::={msagSysCtrl 64}
    h248StatistcSendMsg OBJECT-TYPE
        SYNTAX                  Unsigned32
        MAX-ACCESS              read-only
        STATUS                  current
        DESCRIPTION             ""
        ::={msagSysCtrl 65}

  h248StatistcRecMsgByte OBJECT-TYPE
        SYNTAX                  Unsigned32
        MAX-ACCESS              read-only
        STATUS                  current
        DESCRIPTION             ""
        ::={msagSysCtrl 66}

    h248StatistcSendMsgByte OBJECT-TYPE
        SYNTAX                  Unsigned32
        MAX-ACCESS              read-only
        STATUS                  current
        DESCRIPTION             ""
        ::={msagSysCtrl 67}

  h248StatistcProtocolError OBJECT-TYPE
        SYNTAX                  Unsigned32
        MAX-ACCESS              read-only
        STATUS                  current
        DESCRIPTION             ""
        ::={msagSysCtrl 68}

  h248StatistcTimerOut OBJECT-TYPE
        SYNTAX                  Unsigned32
        MAX-ACCESS              read-only
        STATUS                  current
        DESCRIPTION             ""
        ::={msagSysCtrl 69}

  h248StatistcDisconnect OBJECT-TYPE
        SYNTAX                  Unsigned32
        MAX-ACCESS              read-only
        STATUS                  current
        DESCRIPTION             ""
        ::={msagSysCtrl 70}

  h248StatistcMGCChange OBJECT-TYPE
        SYNTAX                  Unsigned32
        MAX-ACCESS              read-only
        STATUS                  current
        DESCRIPTION             ""
        ::={msagSysCtrl 71}

  h248StatistcTransmitError OBJECT-TYPE
        SYNTAX                  Unsigned32
        MAX-ACCESS              read-only
        STATUS                  current
        DESCRIPTION             ""
        ::={msagSysCtrl 72}

  calloptOpenMsgAck OBJECT-TYPE
        SYNTAX                  INTEGER{send(1),notsend(2)}
        MAX-ACCESS              read-write
        STATUS                  current
        DESCRIPTION             ""
        ::={msagSysCtrl 73}
        
  calloptPlayToneAck OBJECT-TYPE
        SYNTAX                  INTEGER{send(1),notsend(2)}
        MAX-ACCESS              read-write
        STATUS                  current
        DESCRIPTION             ""
        ::={msagSysCtrl 74}
        
  calloptSubPriority OBJECT-TYPE
        SYNTAX                  INTEGER{higher(1),nothigher(2)}
        MAX-ACCESS              read-write
        STATUS                  current
        DESCRIPTION             ""
        ::={msagSysCtrl 75}

  calloptNumMax OBJECT-TYPE
        SYNTAX                  INTEGER(0..16)
        MAX-ACCESS              read-write
        STATUS                  current
        DESCRIPTION             ""
        ::={msagSysCtrl 76}

  calloptH248MsgAck OBJECT-TYPE
        SYNTAX                  INTEGER{send(1),notsend(2)}
        MAX-ACCESS              read-write
        STATUS                  current
        DESCRIPTION             ""
        ::={msagSysCtrl 77}

  calloptH248MsgPn OBJECT-TYPE
        SYNTAX                  INTEGER{send(1),notsend(2)}
        MAX-ACCESS              read-write
        STATUS                  current
        DESCRIPTION             ""
        ::={msagSysCtrl 78}
        
  calloptH248Statistic OBJECT-TYPE
        SYNTAX                  INTEGER{send(1),notsend(2)}
        MAX-ACCESS              read-write
        STATUS                  current
        DESCRIPTION             ""
        ::={msagSysCtrl 79}

  calloptH248HookOffEvent OBJECT-TYPE
        SYNTAX                  INTEGER{alwayssend(1),notalways(2)}
        MAX-ACCESS              read-write
        STATUS                  current
        DESCRIPTION             ""
        ::={msagSysCtrl 80}

  calloptH248HookOnEvent OBJECT-TYPE
        SYNTAX                  INTEGER{alwayssend(1),notalways(2)}
        MAX-ACCESS              read-write
        STATUS                  current
        DESCRIPTION             ""
        ::={msagSysCtrl 81}
        
  calloptServiceAbnormal OBJECT-TYPE
        SYNTAX                  INTEGER{alwayssend(1),notalways(2)}
        MAX-ACCESS              read-write
        STATUS                  current
        DESCRIPTION             ""
        ::={msagSysCtrl 82}

  calloptMgProtocolErr OBJECT-TYPE
        SYNTAX                  INTEGER{alwayssend(1),notalways(2)}
        MAX-ACCESS              read-write
        STATUS                  current
        DESCRIPTION             ""
        ::={msagSysCtrl 83}

  calloptMgcProtocolErr OBJECT-TYPE
        SYNTAX                  INTEGER{alwayssend(1),notalways(2)}
        MAX-ACCESS              read-write
        STATUS                  current
        DESCRIPTION             ""
        ::={msagSysCtrl 84}

  calloptMgInsideErr OBJECT-TYPE
        SYNTAX                  INTEGER{alwayssend(1),notalways(2)}
        MAX-ACCESS              read-write
        STATUS                  current
        DESCRIPTION             ""
        ::={msagSysCtrl 85}

  calloptHookOffLimiteCycle OBJECT-TYPE
        SYNTAX                  INTEGER(30..600)
        MAX-ACCESS              read-write
        STATUS                  current
        DESCRIPTION             ""
        ::={msagSysCtrl 86}

  calloptHookOffLimiteBlock OBJECT-TYPE
        SYNTAX                  INTEGER(15..600)
        MAX-ACCESS              read-write
        STATUS                  current
        DESCRIPTION             ""
        ::={msagSysCtrl 87}

   calloptHookOffLimiteUnblock OBJECT-TYPE
        SYNTAX                  INTEGER(12..600)
        MAX-ACCESS              read-write
        STATUS                  current
        DESCRIPTION             ""
        ::={msagSysCtrl 88}

   calloptMgcCallGapping OBJECT-TYPE
        SYNTAX                  INTEGER{breakdown(0),notbreakdown(1)}
        MAX-ACCESS              read-write
        STATUS                  current
        DESCRIPTION             ""
        ::={msagSysCtrl 89}

        nTimerTable OBJECT-TYPE
        SYNTAX        SEQUENCE OF NTimerEntry
        MAX-ACCESS    not-accessible
        STATUS      current
        DESCRIPTION    ""
        ::={msagSysCtrl 90}

        nTimerEntry OBJECT-TYPE
        SYNTAX         NTimerEntry
        MAX-ACCESS    not-accessible
        STATUS      current
        DESCRIPTION    ""
        INDEX {Index}
        ::={nTimerTable 1}

      NTimerEntry ::=
           SEQUENCE{
          Index              INTEGER,
          FlashDelay         INTEGER,
          CalledPartyReanwer INTEGER,
          H248BusyStatus     INTEGER,
          HowlTone           INTEGER,
          H248Short          INTEGER,
          H248Long           INTEGER,
          RTPtimer           INTEGER,
          H248RingPattern    INTEGER,
          CallAlarm          INTEGER,
          InterCallAlarm     INTEGER,
          FreshTnet          INTEGER,
          CheckContext       INTEGER,
          UpPort             INTEGER,
          ResReportPeriod    INTEGER,
          AgMustDetOvrLd     INTEGER,
          ErrReplyInformSSEn INTEGER,
          CookieEchoFormat   INTEGER,
          CheckSumFormat     INTEGER,
          IuaIsdnHwFormat    INTEGER
            }

      Index  OBJECT-TYPE
        SYNTAX        INTEGER(1)
        MAX-ACCESS  read-write
        STATUS      current
        DESCRIPTION    ""
        ::={nTimerEntry 1}

      FlashDelay  OBJECT-TYPE
        SYNTAX        INTEGER(10..50)
        MAX-ACCESS  read-write
        STATUS      current
        DESCRIPTION    ""
        ::={nTimerEntry 2}

      CalledPartyReanwer  OBJECT-TYPE
        SYNTAX        INTEGER(10..600)
        MAX-ACCESS  read-write
        STATUS      current
        DESCRIPTION    ""
        ::={nTimerEntry 3}

      H248BusyStatus  OBJECT-TYPE
        SYNTAX        INTEGER(10..1000)
        MAX-ACCESS  read-write
        STATUS      current
        DESCRIPTION    ""
        ::={nTimerEntry 4}

      HowlTone  OBJECT-TYPE
        SYNTAX        INTEGER(10..1000)
        MAX-ACCESS  read-write
        STATUS      current
        DESCRIPTION    ""
        ::={nTimerEntry 5}

      H248Short  OBJECT-TYPE
        SYNTAX        INTEGER(10..50)
        MAX-ACCESS  read-write
        STATUS      current
        DESCRIPTION    ""
        ::={nTimerEntry 6}

      H248Long  OBJECT-TYPE
        SYNTAX        INTEGER(10..100)
        MAX-ACCESS  read-write
        STATUS      current
        DESCRIPTION    ""
        ::={nTimerEntry 7}

      RTPtimer  OBJECT-TYPE
        SYNTAX        INTEGER(10..50)
        MAX-ACCESS  read-write
        STATUS      current
        DESCRIPTION    ""
        ::={nTimerEntry 8}

      H248RingPattern  OBJECT-TYPE
        SYNTAX        INTEGER{ms(1),tenms(2),hundredms(3)}
        MAX-ACCESS  read-write
        STATUS      current
        DESCRIPTION    ""
        ::={nTimerEntry 9}

      CallAlarm  OBJECT-TYPE
        SYNTAX        INTEGER(10..500)
        MAX-ACCESS  read-write
        STATUS      current
        DESCRIPTION    ""
        ::={nTimerEntry 10}

      InterCallAlarm  OBJECT-TYPE
        SYNTAX        INTEGER(10..300)
        MAX-ACCESS  read-write
        STATUS      current
        DESCRIPTION    ""
        ::={nTimerEntry 11}

      FreshTnet  OBJECT-TYPE
        SYNTAX        INTEGER(10..600)
        MAX-ACCESS  read-write
        STATUS      current
        DESCRIPTION    ""
        ::={nTimerEntry 12}

      CheckContext  OBJECT-TYPE
        SYNTAX        INTEGER{disable(0),enable(1)}
        MAX-ACCESS  read-write
        STATUS      current
        DESCRIPTION    ""
        ::={nTimerEntry 13}

      UpPort  OBJECT-TYPE
        SYNTAX        INTEGER{withTimeStamp(0),noTimeStamp(1)}
        MAX-ACCESS  read-write
        STATUS      current
        DESCRIPTION    ""
        ::={nTimerEntry 14}

      ResReportPeriod  OBJECT-TYPE
        SYNTAX        INTEGER(0..65535)
        MAX-ACCESS  read-write
        STATUS      current
        DESCRIPTION    ""
        ::={nTimerEntry 15}

      AgMustDetOvrLd  OBJECT-TYPE
        SYNTAX        INTEGER{disable(0),enable(1)}
        MAX-ACCESS  read-write
        STATUS      current
        DESCRIPTION    ""
        ::={nTimerEntry 16}

      ErrReplyInformSSEn  OBJECT-TYPE
        SYNTAX        INTEGER{disable(0),enable(1)}
        MAX-ACCESS  read-write
        STATUS      current
        DESCRIPTION    ""
        ::={nTimerEntry 17}

      CookieEchoFormat  OBJECT-TYPE
        SYNTAX        INTEGER{formZTE(0),formStandard(1)}
        MAX-ACCESS  read-write
        STATUS      current
        DESCRIPTION    ""
        ::={nTimerEntry 18}

      CheckSumFormat  OBJECT-TYPE
        SYNTAX        INTEGER{formADLER32(0),formCRC32(1)}
        MAX-ACCESS  read-write
        STATUS      current
        DESCRIPTION    ""
        ::={nTimerEntry 19}

      IuaIsdnHwFormat  OBJECT-TYPE
        SYNTAX        INTEGER{formDisable(0),formEnable(1)}
        MAX-ACCESS  read-write
        STATUS      current
        DESCRIPTION    ""
        ::={nTimerEntry 20}

---Qovs
    msagVoipQovsResultTable OBJECT-TYPE
        SYNTAX      SEQUENCE OF MsagVoipQovsResultEntry
        MAX-ACCESS  not-accessible
        STATUS      current
        DESCRIPTION ""
        ::= { msagSysCtrl 101 }

    msagVoipQovsResultEntry OBJECT-TYPE
        SYNTAX      MsagVoipQovsResultEntry
        MAX-ACCESS  not-accessible
        STATUS      current
        DESCRIPTION ""
        INDEX {
             msagVoipQRId
             }
        ::= { msagVoipQovsResultTable 1 }

    MsagVoipQovsResultEntry  ::= SEQUENCE {
        msagVoipQRId        INTEGER,
        msagVoipQRResult    DisplayString
    }

    msagVoipQRId    OBJECT-TYPE
        SYNTAX          INTEGER (1..20)
        MAX-ACCESS      not-accessible
        STATUS          current
        DESCRIPTION     ""
        ::= { msagVoipQovsResultEntry 1 }


    msagVoipQRResult    OBJECT-TYPE
        SYNTAX          DisplayString 
        MAX-ACCESS      read-only
        STATUS          current
        DESCRIPTION     ""
        ::= { msagVoipQovsResultEntry 2 }



        msagDHCPSet OBJECT-TYPE
         SYNTAX        INTEGER{enable(1),disable(2)}
        MAX-ACCESS  read-write
        STATUS      current
        DESCRIPTION    ""
        ::={msagSysCtrl 102}

    msagRTPStat OBJECT IDENTIFIER ::= { msagSysCtrl 103 }
    
    msagRTPSendPackageNum OBJECT-TYPE
        SYNTAX      Integer32
        MAX-ACCESS  read-only
        STATUS      current
        DESCRIPTION ""
        ::={msagRTPStat 1}

    msagRTPReceivePackageNum OBJECT-TYPE
        SYNTAX      Integer32
        MAX-ACCESS  read-only
        STATUS      current
        DESCRIPTION ""
        ::={msagRTPStat 2}

    msagRTPSendPakcageSpeed OBJECT-TYPE
        SYNTAX      Integer32
        MAX-ACCESS  read-only
        STATUS      current
        DESCRIPTION ""
        ::={msagRTPStat 3}

    msagRTPReceivePakcageSpeed OBJECT-TYPE
        SYNTAX      Integer32
        MAX-ACCESS  read-only
        STATUS      current
        DESCRIPTION ""
        ::={msagRTPStat 4}

    msagRTPSendPackageByteNum OBJECT-TYPE
        SYNTAX      Integer32
        MAX-ACCESS  read-only
        STATUS      current
        DESCRIPTION ""
        ::={msagRTPStat 5}

    msagRTPReceivePackageByteNum OBJECT-TYPE
        SYNTAX      Integer32
        MAX-ACCESS  read-only
        STATUS      current
        DESCRIPTION ""
        ::={msagRTPStat 6}

    msagRTPSendPakcageByteSpeed OBJECT-TYPE
        SYNTAX      Integer32
        MAX-ACCESS  read-only
        STATUS      current
        DESCRIPTION ""
        ::={msagRTPStat 7}

    msagRTPReceivePakcageByteSpeed OBJECT-TYPE
        SYNTAX      Integer32
        MAX-ACCESS  read-only
        STATUS      current
        DESCRIPTION ""
        ::={msagRTPStat 8}
        
--
    msagNetSendJitter OBJECT-TYPE
        SYNTAX      Integer32
        MAX-ACCESS  read-only
        STATUS      current
        DESCRIPTION ""
        ::={msagRTPStat 9}

    msagNetReceiveJitter OBJECT-TYPE
        SYNTAX      Integer32
        MAX-ACCESS  read-only
        STATUS      current
        DESCRIPTION ""
        ::={msagRTPStat 10}

    msagNetDelay OBJECT-TYPE
        SYNTAX      Integer32
        MAX-ACCESS  read-only
        STATUS      current
        DESCRIPTION ""
        ::={msagRTPStat 11}

    msagNetSendPackageLoss OBJECT-TYPE
        SYNTAX      Integer32
        MAX-ACCESS  read-only
        STATUS      current
        DESCRIPTION ""
        ::={msagRTPStat 12}

    msagNetReceivePackageLoss OBJECT-TYPE
        SYNTAX      Integer32
        MAX-ACCESS  read-only
        STATUS      current
        DESCRIPTION ""
        ::={msagRTPStat 13}

    msagNetBandUsed OBJECT-TYPE
        SYNTAX      Integer32
        MAX-ACCESS  read-only
        STATUS      current
        DESCRIPTION ""
        ::={msagRTPStat 14}
        
-------     
        msagVoipStatEnable OBJECT-TYPE
         SYNTAX        INTEGER{enable(1),disable(0)}
        MAX-ACCESS  read-write
        STATUS      current
        DESCRIPTION    " enable this switch, the voip rtp and qovs stat will start "
        ::={msagSysCtrl 104}
        
        mgcpLinkStatus          OBJECT-TYPE
        SYNTAX                  INTEGER {linkup(0), linkdown(1)}
        MAX-ACCESS              read-only
        STATUS                  current
        DESCRIPTION             "MGCP Link status, a scalar object"
        ::={msagSysCtrl 105}
        
-- End of System-Control Related Operation MIB

    msagSubCardOperTable OBJECT-TYPE
        SYNTAX        SEQUENCE OF MsagSubCardOperEntry
        MAX-ACCESS    not-accessible
        STATUS      current
        DESCRIPTION    ""
        ::={a200-mib 54}
        
        msagSubCardOperEntry OBJECT-TYPE
        SYNTAX         MsagSubCardOperEntry
        MAX-ACCESS    not-accessible
        STATUS      current
        DESCRIPTION    ""
        INDEX { msagSCORack,msagSCOShelf,msagSCOSlot,msagSCOCardNo }
        ::={msagSubCardOperTable 1}

      MsagSubCardOperEntry ::=
           SEQUENCE{
                    msagSCORack       INTEGER,
                    msagSCOShelf      INTEGER,
                    msagSCOSlot       INTEGER,
                    msagSCOCardNo     INTEGER,
                    msagSCOCardStatus RowStatus                            
                }
                
      msagSCORack OBJECT-TYPE
        SYNTAX         INTEGER(1..1)
        MAX-ACCESS  not-accessible
        STATUS      current
        DESCRIPTION    ""
        ::={msagSubCardOperEntry 1}
        
        msagSCOShelf OBJECT-TYPE
        SYNTAX         INTEGER(0..4)
        MAX-ACCESS  not-accessible
        STATUS      current
        DESCRIPTION    ""
        ::={msagSubCardOperEntry 2}
        
        msagSCOSlot OBJECT-TYPE
        SYNTAX         INTEGER(8..12)
        MAX-ACCESS  not-accessible
        STATUS      current
        DESCRIPTION    ""
        ::={msagSubCardOperEntry 3}
        
        msagSCOCardNo OBJECT-TYPE
        SYNTAX         INTEGER(1..2)
        MAX-ACCESS  not-accessible
        STATUS      current
        DESCRIPTION    ""
        ::={msagSubCardOperEntry 4}
        
        msagSCOCardStatus OBJECT-TYPE
        SYNTAX          RowStatus
        MAX-ACCESS  read-write
        STATUS      current
        DESCRIPTION    ""
        ::={msagSubCardOperEntry 6}
        
        
        msagISDNPortAddrTable OBJECT-TYPE
        SYNTAX        SEQUENCE OF MsagISDNPortAddrEntry
        MAX-ACCESS    not-accessible
        STATUS      current
        DESCRIPTION    ""
        ::={a200-mib 56}
        
        msagISDNPortAddrEntry OBJECT-TYPE
        SYNTAX         MsagISDNPortAddrEntry
        MAX-ACCESS    not-accessible
        STATUS      current
        DESCRIPTION    ""
        INDEX { isdnBraRack, isdnBraShelf, isdnBraSlot, isdnBraPort }
        ::={msagISDNPortAddrTable 1}

      MsagISDNPortAddrEntry ::=
           SEQUENCE{
             isdnBraRack         INTEGER,
        isdnBraShelf        INTEGER,
        isdnBraSlot         INTEGER,
        isdnBraPort         INTEGER,
        isdnBraIPAddr       IpAddress,
        isdnBraBeginPort    INTEGER,
        isdnBraHDLCMaxFrame INTEGER,
        isdnBraRowStatus    RowStatus
        }

    isdnBraRack  OBJECT-TYPE
        SYNTAX          INTEGER(1..1)
        MAX-ACCESS  not-accessible
        STATUS      current
        DESCRIPTION    ""
        ::={msagISDNPortAddrEntry 1}    
        
        isdnBraShelf  OBJECT-TYPE
        SYNTAX          INTEGER(1..5)
        MAX-ACCESS  not-accessible
        STATUS      current
        DESCRIPTION    ""
        ::={msagISDNPortAddrEntry 2}    
        
        isdnBraSlot  OBJECT-TYPE
        SYNTAX          INTEGER(3..16)
        MAX-ACCESS  not-accessible
        STATUS      current
        DESCRIPTION    ""
        ::={msagISDNPortAddrEntry 3}    
        
        isdnBraPort  OBJECT-TYPE
        SYNTAX          INTEGER(0..7)
        MAX-ACCESS  not-accessible
        STATUS      current
        DESCRIPTION    ""
        ::={msagISDNPortAddrEntry 4}    
        
        isdnBraIPAddr  OBJECT-TYPE
        SYNTAX          IpAddress
        MAX-ACCESS  read-create
        STATUS      current
        DESCRIPTION    ""
        ::={msagISDNPortAddrEntry 5}
   
    isdnBraBeginPort  OBJECT-TYPE
        SYNTAX          INTEGER(5600..5840)
        MAX-ACCESS  read-create
        STATUS      current
        DESCRIPTION    ""
        ::={msagISDNPortAddrEntry 6}
    
    isdnBraHDLCMaxFrame  OBJECT-TYPE
        SYNTAX          INTEGER(1..65535)
        MAX-ACCESS  read-create
        STATUS      current
        DESCRIPTION    ""
        ::={msagISDNPortAddrEntry 7}
    
    isdnBraRowStatus  OBJECT-TYPE
        SYNTAX          RowStatus
        MAX-ACCESS  read-create
        STATUS      current
        DESCRIPTION    ""
        ::={msagISDNPortAddrEntry 8}    

    msagBoardOperTable OBJECT-TYPE
        SYNTAX        SEQUENCE OF MsagBoardOperEntry
        MAX-ACCESS    not-accessible
        STATUS      current
        DESCRIPTION    ""
        ::={a200-mib 57}
        
        msagBoardOperEntry OBJECT-TYPE
        SYNTAX         MsagBoardOperEntry
        MAX-ACCESS    not-accessible
        STATUS      current
        DESCRIPTION    ""
        INDEX { msagBORack,msagBOShelf,msagBOSlot }
        ::={msagBoardOperTable 1}

      MsagBoardOperEntry ::=
           SEQUENCE{
             msagBORack         INTEGER,
             msagBOShelf        INTEGER,
             msagBOSlot         INTEGER,
             msagBOKind         INTEGER,
             msagBOConnRack     INTEGER,
             msagBOConnShelf    INTEGER,
             msagBOConnSlot     INTEGER,
             msagBOConnPort     INTEGER,
             msagBORowStatus    RowStatus
        }

    msagBORack  OBJECT-TYPE
        SYNTAX          INTEGER(1..1)
        MAX-ACCESS  not-accessible
        STATUS      current
        DESCRIPTION    ""
        ::={msagBoardOperEntry 1}
        
    msagBOShelf  OBJECT-TYPE
        SYNTAX          INTEGER(1..5)
        MAX-ACCESS  not-accessible
        STATUS      current
        DESCRIPTION    ""
        ::={msagBoardOperEntry 2}
    
    msagBOSlot  OBJECT-TYPE
        SYNTAX          INTEGER(3..16)
        MAX-ACCESS  not-accessible
        STATUS      current
        DESCRIPTION    ""
        ::={msagBoardOperEntry 3}    
                
        msagBOKind  OBJECT-TYPE
        SYNTAX          INTEGER{tpICS(1),tpGIS(2)}
        MAX-ACCESS  read-create
        STATUS      current
        DESCRIPTION    ""
        ::={msagBoardOperEntry 4}    
        
        msagBOConnRack  OBJECT-TYPE
        SYNTAX          INTEGER(1..1)
        MAX-ACCESS  read-create
        STATUS      current
        DESCRIPTION    ""
        ::={msagBoardOperEntry 5}    
        
        msagBOConnShelf  OBJECT-TYPE
        SYNTAX          INTEGER(1..5)
        MAX-ACCESS  read-create
        STATUS      current
        DESCRIPTION    ""
        ::={msagBoardOperEntry 6}    
        
        msagBOConnSlot  OBJECT-TYPE
        SYNTAX          INTEGER(3..16)
        MAX-ACCESS  read-create
        STATUS      current
        DESCRIPTION    ""
        ::={msagBoardOperEntry 7}    
        
        msagBOConnPort  OBJECT-TYPE
        SYNTAX          INTEGER(1..8)
        MAX-ACCESS  read-create
        STATUS      current
        DESCRIPTION    ""
        ::={msagBoardOperEntry 8}    
        
        msagBORowStatus  OBJECT-TYPE
        SYNTAX          RowStatus
        MAX-ACCESS  read-create
        STATUS      current
        DESCRIPTION    ""
        ::={msagBoardOperEntry 9}
    
--------------------------------------------------------------------
    
    msagInitRingTable  OBJECT-TYPE
        SYNTAX        SEQUENCE OF MsagInitRingEntry
        MAX-ACCESS    not-accessible
        STATUS      current
        DESCRIPTION    ""
        ::={a200-mib 58}
        
    msagInitRingEntry OBJECT-TYPE
        SYNTAX         MsagInitRingEntry
        MAX-ACCESS    not-accessible
        STATUS      current
        DESCRIPTION    ""
        INDEX { msagIRMgId }
        ::={msagInitRingTable 1}

      MsagInitRingEntry ::=
           SEQUENCE{
             msagIRMgId         INTEGER,
             msagIRType         INTEGER, 
        msagIROnDuration   INTEGER,
        msagIROffDuration  INTEGER,
        a200mgRingProf     INTEGER 
        }

    msagIRMgId  OBJECT-TYPE
        SYNTAX          INTEGER(1..255)
        MAX-ACCESS  not-accessible
        STATUS      current
        DESCRIPTION    ""
        ::={msagInitRingEntry 1}
    
    msagIRType  OBJECT-TYPE
        SYNTAX          INTEGER{tpOnlyCID(1),tpAll(2),tpAllNo(3)}
        MAX-ACCESS  read-write
        STATUS      current
        DESCRIPTION    ""
        ::={msagInitRingEntry 2}
        
    msagIROnDuration OBJECT-TYPE
        SYNTAX          INTEGER(200..400)
        MAX-ACCESS  read-write
        STATUS      current
        DESCRIPTION    ""
        ::={msagInitRingEntry 3}
        
    msagIROffDuration OBJECT-TYPE
        SYNTAX          INTEGER(200..400)
        MAX-ACCESS  read-write
        STATUS      current
        DESCRIPTION    ""
        ::={msagInitRingEntry 4}
        
        
        a200mgRingProf  OBJECT-TYPE
        SYNTAX    INTEGER{mainland(1),hongkong(2),singapore(3),russia(4)}
        MAX-ACCESS     read-write
        STATUS    current
        DESCRIPTION ""
        ::={msagInitRingEntry 5}


---------------------------------------------------------- 
    
        
        
        msagRingPatternTable OBJECT-TYPE
        SYNTAX        SEQUENCE OF MsagRingPatternEntry
        MAX-ACCESS    not-accessible
        STATUS      current
        DESCRIPTION    ""
        ::={a200-mib 59}
        
        msagRingPatternEntry OBJECT-TYPE
        SYNTAX         MsagRingPatternEntry
        MAX-ACCESS    not-accessible
        STATUS      current
        DESCRIPTION    ""
        INDEX { msagRPRingProfile,msagRPId }
        ::={msagRingPatternTable 1}
        
        MsagRingPatternEntry ::=
           SEQUENCE{
             msagRPRingProfile    INTEGER,
             msagRPId             INTEGER,
             msagRPTime           INTEGER,
             msagRPOn1            INTEGER,
             msagRPOff1           INTEGER,
             msagRPOn2            INTEGER,
             msagRPOff2           INTEGER,
             msagRPOn3            INTEGER,
             msagRPOff3           INTEGER,
             msagRPOn4            INTEGER,
             msagRPOff4           INTEGER,
             msagRPOn5            INTEGER,
             msagRPOff5           INTEGER
        }
        
        msagRPRingProfile  OBJECT-TYPE
        SYNTAX          INTEGER{mainland(1),hongkong(2),singapore(3),russia(4)}
        MAX-ACCESS  not-accessible
        STATUS      current
        DESCRIPTION    ""
        ::={msagRingPatternEntry 1}
        
        msagRPId  OBJECT-TYPE
        SYNTAX          INTEGER(0..15)
        MAX-ACCESS  not-accessible
        STATUS      current
        DESCRIPTION    ""
        ::={msagRingPatternEntry 2}
        
        msagRPTime  OBJECT-TYPE
        SYNTAX          INTEGER(0..65535)
        MAX-ACCESS  read-create
        STATUS      current
        DESCRIPTION    ""
        ::={msagRingPatternEntry 3}
        
        msagRPOn1  OBJECT-TYPE
        SYNTAX          INTEGER(0..65535)
        MAX-ACCESS  read-create
        STATUS      current
        DESCRIPTION    ""
        ::={msagRingPatternEntry 4}
        
        msagRPOff1  OBJECT-TYPE
        SYNTAX          INTEGER(0..65535)
        MAX-ACCESS  read-create
        STATUS      current
        DESCRIPTION    ""
        ::={msagRingPatternEntry 5}
        
        msagRPOn2  OBJECT-TYPE
        SYNTAX          INTEGER(0..65535)
        MAX-ACCESS  read-create
        STATUS      current
        DESCRIPTION    ""
        ::={msagRingPatternEntry 6}
        
        msagRPOff2  OBJECT-TYPE
        SYNTAX          INTEGER(0..65535)
        MAX-ACCESS  read-create
        STATUS      current
        DESCRIPTION    ""
        ::={msagRingPatternEntry 7}
        
        msagRPOn3  OBJECT-TYPE
        SYNTAX          INTEGER(0..65535)
        MAX-ACCESS  read-create
        STATUS      current
        DESCRIPTION    ""
        ::={msagRingPatternEntry 8}
        
        msagRPOff3  OBJECT-TYPE
        SYNTAX          INTEGER(0..65535)
        MAX-ACCESS  read-create
        STATUS      current
        DESCRIPTION    ""
        ::={msagRingPatternEntry 9}
        
        msagRPOn4  OBJECT-TYPE
        SYNTAX          INTEGER(0..65535)
        MAX-ACCESS  read-create
        STATUS      current
        DESCRIPTION    ""
        ::={msagRingPatternEntry 10}
        
        msagRPOff4  OBJECT-TYPE
        SYNTAX          INTEGER(0..65535)
        MAX-ACCESS  read-create
        STATUS      current
        DESCRIPTION    ""
        ::={msagRingPatternEntry 11}
        
        msagRPOn5  OBJECT-TYPE
        SYNTAX          INTEGER(0..65535)
        MAX-ACCESS  read-create
        STATUS      current
        DESCRIPTION    ""
        ::={msagRingPatternEntry 12}
        
        msagRPOff5  OBJECT-TYPE
        SYNTAX          INTEGER(0..65535)
        MAX-ACCESS  read-create
        STATUS      current
        DESCRIPTION    ""
        ::={msagRingPatternEntry 13}
        
        msagLoadDftRingProfile OBJECT-TYPE
        SYNTAX         INTEGER{loadDftRP(0)}
        MAX-ACCESS  read-write
        STATUS      current
        DESCRIPTION    ""
        ::={a200-mib 60}
        
        
        trunkTermidTable OBJECT-TYPE
        SYNTAX        SEQUENCE OF TrunkTermidEntry
        MAX-ACCESS    not-accessible
        STATUS      current
        DESCRIPTION    ""
        ::={a200-mib 39}
        
        trunkTermidEntry OBJECT-TYPE
        SYNTAX         TrunkTermidEntry
        MAX-ACCESS    not-accessible
        STATUS      current
        DESCRIPTION    ""
        INDEX { trunkRrack, trunkShelf, trunkSlot, trunkPCMno, trunkIndex}
        ::={trunkTermidTable 1}

      TrunkTermidEntry ::=
           SEQUENCE{
               trunkRrack    INTEGER,
                    trunkShelf    INTEGER,
                    trunkSlot        INTEGER,
                    trunkPCMno    INTEGER,
                    trunkIndex    INTEGER,
                    trunkTermid   OCTET STRING
            }
            
        trunkRrack  OBJECT-TYPE
        SYNTAX        INTEGER(1)
        MAX-ACCESS  not-accessible
        STATUS      current
        DESCRIPTION    ""
        ::={trunkTermidEntry 1}    
    
      trunkShelf   OBJECT-TYPE
        SYNTAX        INTEGER(3)
        MAX-ACCESS  not-accessible
        STATUS      current
        DESCRIPTION    ""
        ::={trunkTermidEntry 2}
        
        trunkSlot   OBJECT-TYPE
        SYNTAX        INTEGER(8)
        MAX-ACCESS  not-accessible
        STATUS      current
        DESCRIPTION    ""
        ::={trunkTermidEntry 3}   
        
        trunkPCMno   OBJECT-TYPE
        SYNTAX        INTEGER(1..8)
        MAX-ACCESS  not-accessible
        STATUS      current
        DESCRIPTION    ""
        ::={trunkTermidEntry 4} 
        
        trunkIndex   OBJECT-TYPE
        SYNTAX        INTEGER(0..31)
        MAX-ACCESS  not-accessible
        STATUS      current
        DESCRIPTION    ""
        ::={trunkTermidEntry 5} 
        
        trunkTermid   OBJECT-TYPE
        SYNTAX        OCTET STRING(SIZE(1..63))
        MAX-ACCESS  read-only
        STATUS      current
        DESCRIPTION    ""
        ::={trunkTermidEntry 6} 
        
        trunkTermidOperTable OBJECT-TYPE
        SYNTAX        SEQUENCE OF TrunkTermidOperEntry
        MAX-ACCESS    not-accessible
        STATUS      current
        DESCRIPTION    ""
        ::={a200-mib 40}
        
        trunkTermidOperEntry OBJECT-TYPE
        SYNTAX         TrunkTermidOperEntry
        MAX-ACCESS    not-accessible
        STATUS      current
        DESCRIPTION    ""
        INDEX { trunkOperRack, trunkOperShelf, trunkOperSlot, trunkOperPCMno}
        ::={trunkTermidOperTable 1}

    TrunkTermidOperEntry ::=
       SEQUENCE{
         trunkOperRack          INTEGER,
         trunkOperShelf         INTEGER,
         trunkOperSlot          INTEGER,
         trunkOperPCMno         INTEGER,
         trunkOperTermidFix     OCTET STRING,
         trunkOperTermidType    INTEGER,
         trunkOperTermidBegNo   INTEGER,
         trunkOperRowStatus     RowStatus,
         trunkOperBeginIndex    INTEGER,
         trunkOperNum           INTEGER,
         trunkOperMgId          INTEGER,
         trunkOperDigitLen      INTEGER
      }

        trunkOperRack  OBJECT-TYPE
        SYNTAX        INTEGER(1)
        MAX-ACCESS  not-accessible
        STATUS      current
        DESCRIPTION    ""
        ::={trunkTermidOperEntry 1}    
    
      trunkOperShelf   OBJECT-TYPE
        SYNTAX        INTEGER(3)
        MAX-ACCESS  not-accessible
        STATUS      current
        DESCRIPTION    ""
        ::={trunkTermidOperEntry 2}
        
        trunkOperSlot   OBJECT-TYPE
        SYNTAX        INTEGER(8)
        MAX-ACCESS  not-accessible
        STATUS      current
        DESCRIPTION    ""
        ::={trunkTermidOperEntry 3}   
        
        trunkOperPCMno   OBJECT-TYPE
        SYNTAX        INTEGER(1..8)
        MAX-ACCESS  not-accessible
        STATUS      current
        DESCRIPTION    ""
        ::={trunkTermidOperEntry 4} 
        
        trunkOperTermidFix   OBJECT-TYPE
        SYNTAX        OCTET STRING(SIZE(1..63))
        MAX-ACCESS  read-create
        STATUS      current
        DESCRIPTION    ""
        ::={trunkTermidOperEntry 5}
        
        trunkOperTermidType   OBJECT-TYPE
        SYNTAX        INTEGER{type1(1),type2(2),type3(3)}
        MAX-ACCESS  read-create
        STATUS      current
        DESCRIPTION    ""
        ::={trunkTermidOperEntry 6} 
        
        trunkOperTermidBegNo   OBJECT-TYPE
        SYNTAX        INTEGER(0..65535)
        MAX-ACCESS  read-create
        STATUS      current
        DESCRIPTION    "when trunkOperTermidType is type2, trunkOperTermidBegNo can be used"
        ::={trunkTermidOperEntry 7}        
        
        
        trunkOperRowStatus   OBJECT-TYPE
        SYNTAX        RowStatus
        MAX-ACCESS  read-create
        STATUS      current
        DESCRIPTION    ""
        ::={trunkTermidOperEntry 8} 

        trunkOperBeginIndex   OBJECT-TYPE
        SYNTAX        INTEGER(1..31)
        MAX-ACCESS  read-create
        STATUS      current
        DESCRIPTION    ""
        ::={trunkTermidOperEntry 9}
        
        trunkOperNum   OBJECT-TYPE
        SYNTAX        INTEGER(1..30)
        MAX-ACCESS  read-create             
        STATUS      current
        DESCRIPTION    ""
        ::={trunkTermidOperEntry 10}
        
        trunkOperMgId   OBJECT-TYPE
        SYNTAX  INTEGER(1..255)
        MAX-ACCESS  read-create
        STATUS      current
        DESCRIPTION    ""
        ::={trunkTermidOperEntry 11}
        
        trunkOperDigitLen   OBJECT-TYPE
        SYNTAX        INTEGER(2..64)
        MAX-ACCESS  read-create
        STATUS      current
        DESCRIPTION    ""
        ::={trunkTermidOperEntry 12}
        
    rtpParApr2Table OBJECT-TYPE
        SYNTAX        SEQUENCE OF RtpParApr2Entry
        MAX-ACCESS    not-accessible
        STATUS      current
        DESCRIPTION    ""
        ::={a200-mib 41}
        
    rtpParApr2Entry OBJECT-TYPE
        SYNTAX         RtpParApr2Entry
        MAX-ACCESS     not-accessible
        STATUS         current
        DESCRIPTION    
            ""
        INDEX { rtpParParid }
        ::={rtpParApr2Table 1}    
   
    RtpParApr2Entry ::= SEQUENCE
        {               
            rtpParParid                        INTEGER,
            rtpParVADOption                    INTEGER,
            rtpParDTMFTransMode                INTEGER,
            rtpParPCMLaw                       INTEGER,
            rtpParPCMSilence                   INTEGER,
            rtpParDCFilter                     INTEGER,
            rtpParPackGain                     INTEGER,
            rtpParPCMGain                      INTEGER,
            rtpParT38Repair                    INTEGER,
            rtpParECM                          INTEGER,
            rtpParSpeedLimit                   INTEGER,
            rtpParErrorResume                  INTEGER,
            rtpParTCFProcess                   INTEGER,
            rtpFaxMode                         INTEGER,
            rtpFaxPri1                         INTEGER,
            rtpFaxPri2                         INTEGER,
            rtpFaxPri3                         INTEGER,
            rtpFaxPri4                         INTEGER,
            rtp2833Type                        INTEGER,
            rtpElectricDtmfCid                 INTEGER,
            rtpDTMFDuplex                      INTEGER,
            rtpIgnoreA                         INTEGER,
            rtpNumBeforeOff                    INTEGER,
            rtpToneDuplex                      INTEGER
        }
                
    rtpParParid  OBJECT-TYPE
        SYNTAX      INTEGER(1..254)
        MAX-ACCESS  not-accessible
        STATUS      current
        DESCRIPTION ""
        ::={rtpParApr2Entry 1}
        
    rtpParVADOption  OBJECT-TYPE
        SYNTAX      INTEGER
            {
                disable(0),
                defaultScheme(1),
                pt13Scheme(2),
                noSilence(3)
            }
        MAX-ACCESS  read-write
        STATUS      current
        DESCRIPTION ""
        ::={rtpParApr2Entry 2}
        
    rtpParDTMFTransMode  OBJECT-TYPE
        SYNTAX      INTEGER
            {
                voiceCoding(1),
                rfc2833(2),
                aal2_IETF(4)
            }
        MAX-ACCESS  read-write
        STATUS      current
        DESCRIPTION ""
        ::={rtpParApr2Entry 3}
        
    rtpParPCMLaw  OBJECT-TYPE
        SYNTAX      INTEGER
            {
                alaw(0),
                ulaw(1)
            }
        MAX-ACCESS  read-write
        STATUS      current
        DESCRIPTION ""
        ::={rtpParApr2Entry 4}
        
    rtpParPCMSilence  OBJECT-TYPE
        SYNTAX      INTEGER
            {
                comfortNoise(0),
                silence(1)
            }
        MAX-ACCESS  read-write
        STATUS      current
        DESCRIPTION ""
        ::={rtpParApr2Entry 5}
        
    rtpParDCFilter  OBJECT-TYPE
        SYNTAX      INTEGER
            {
                enable(0),
                disable(1)
            }
        MAX-ACCESS  read-write
        STATUS      current
        DESCRIPTION ""
        ::={rtpParApr2Entry 6}
        
    rtpParPackGain  OBJECT-TYPE
        SYNTAX      INTEGER(0..200)
        MAX-ACCESS  read-write
        STATUS      current
        DESCRIPTION ""
        ::={rtpParApr2Entry 7}
        
    rtpParPCMGain  OBJECT-TYPE
        SYNTAX      INTEGER(0..200)
        MAX-ACCESS  read-write
        STATUS      current
        DESCRIPTION ""
        ::={rtpParApr2Entry 8}
        
    rtpParT38Repair  OBJECT-TYPE
        SYNTAX      INTEGER
            {
                notReplace(0),
                whiteLine(1),
                lastLine(2)
            }
        MAX-ACCESS  read-write
        STATUS      current
        DESCRIPTION ""
        ::={rtpParApr2Entry 9}
        
    rtpParECM  OBJECT-TYPE
        SYNTAX        INTEGER
            {
                enable(0),
                disable(1)
            }
        MAX-ACCESS  read-write
        STATUS      current
        DESCRIPTION    ""
        ::={rtpParApr2Entry 10}
        
    rtpParSpeedLimit  OBJECT-TYPE
        SYNTAX        INTEGER
            {
                noLimit(0),
                bps2400(1),
                bps4800(2),
                bps7200(3),
                bps9600(4),
                bps12000(5),
                bps14400(6)
            }
        MAX-ACCESS  read-write
        STATUS      current
        DESCRIPTION    ""
        ::={rtpParApr2Entry 11}
        
    rtpParErrorResume  OBJECT-TYPE
        SYNTAX        INTEGER
            {
                redundancy(0),
                fec(1)
            }
        MAX-ACCESS  read-write
        STATUS      current
        DESCRIPTION    ""
        ::={rtpParApr2Entry 12}
        
    rtpParTCFProcess  OBJECT-TYPE
        SYNTAX        INTEGER
            {
                procedure2(0),
                procedure1(1)
            }
        MAX-ACCESS  read-write
        STATUS      current
        DESCRIPTION    ""
        ::={rtpParApr2Entry 13}
        
    rtpFaxMode  OBJECT-TYPE
        SYNTAX        INTEGER
            {
                t30(0),
                t38(1),
                rtp(2),
                halfControl(10),
                fullControl(11)
            }
        MAX-ACCESS  read-write
        STATUS      current
        DESCRIPTION    ""
        ::={rtpParApr2Entry 14}
        
    rtpFaxPri1  OBJECT-TYPE
        SYNTAX        INTEGER
            {
                vbd(1),
                t38(2)
            }
        MAX-ACCESS  not-accessible
        STATUS      current
        DESCRIPTION    ""
        ::={rtpParApr2Entry 15}
        
    rtpFaxPri2  OBJECT-TYPE
        SYNTAX        INTEGER
            {
                vbd(1),
                t38(2)
            }
        MAX-ACCESS  not-accessible
        STATUS      current
        DESCRIPTION    ""
        ::={rtpParApr2Entry 16}
        
    rtpFaxPri3  OBJECT-TYPE
        SYNTAX      INTEGER
            {
                vbd(1),
                t38(2)
            }
        MAX-ACCESS  not-accessible
        STATUS      current
        DESCRIPTION ""
        ::={rtpParApr2Entry 17}
        
    rtpFaxPri4  OBJECT-TYPE
        SYNTAX      INTEGER
            {
                vbd(1),
                t38(2)
            }
        MAX-ACCESS  not-accessible
        STATUS      current
        DESCRIPTION ""
        ::={rtpParApr2Entry 18}
        
    rtp2833Type  OBJECT-TYPE
        SYNTAX       INTEGER
            { 
                type2833Redun(1),
                typeRTP(2),
                type2833NoRedun(3)
            }
        MAX-ACCESS   not-accessible
        STATUS       current
        DESCRIPTION  ""
        ::={rtpParApr2Entry 19}    

    rtpElectricDtmfCid  OBJECT-TYPE
        SYNTAX      INTEGER(100..630)
        MAX-ACCESS  read-write
        STATUS      current
        DESCRIPTION ""
        ::={rtpParApr2Entry 20}       
        
    rtpDTMFDuplex  OBJECT-TYPE
        SYNTAX      INTEGER(0..1)
        MAX-ACCESS  read-write
        STATUS      current
        DESCRIPTION ""
        ::={rtpParApr2Entry 21}        
        
    rtpIgnoreA  OBJECT-TYPE
        SYNTAX      INTEGER(0..1)
        MAX-ACCESS  read-write
        STATUS      current
        DESCRIPTION    ""
        ::={rtpParApr2Entry 22}        
        
    rtpNumBeforeOff  OBJECT-TYPE
        SYNTAX      INTEGER(0..7)
        MAX-ACCESS  read-write
        STATUS      current
        DESCRIPTION ""
        ::={rtpParApr2Entry 23}        
        
    rtpToneDuplex  OBJECT-TYPE
        SYNTAX      INTEGER(0..1)
        MAX-ACCESS  read-write
        STATUS      current
        DESCRIPTION ""
        ::={rtpParApr2Entry 24}                
        
    exRTPApr2Table OBJECT-TYPE
        SYNTAX        SEQUENCE OF ExRTPApr2Entry
        MAX-ACCESS    not-accessible
        STATUS        current
        DESCRIPTION   
            ""
        ::={a200-mib 42}
        
    exRTPApr2Entry OBJECT-TYPE
        SYNTAX        ExRTPApr2Entry
        MAX-ACCESS    not-accessible
        STATUS        current
        DESCRIPTION   
            ""
        INDEX { exRTPParId }
        ::={exRTPApr2Table 1}

    ExRTPApr2Entry ::= SEQUENCE
        {
            exRTPParId                       INTEGER, 
            exRTPDecodeAdapt                 INTEGER, 
            exRTPG723Rate                    INTEGER, 
            exRTPPacketGenerate              INTEGER, 
            exRTPDTMFPayload                 INTEGER, 
            exRTPDTMFPayloadRedund           INTEGER, 
            exRTPFaxDataRedund               INTEGER, 
            exRTPT30MessageRedund            INTEGER, 
            exRTPMasterEchoControl           INTEGER, 
            exRTPHardEchoControl             INTEGER, 
            exRTPHardEchoNumber              INTEGER, 
            exRTPFixedTransGain              INTEGER, 
            exRTPEctxm                       INTEGER, 
            exRTPEcrxm                       INTEGER, 
            exRTPEchoControlLength           INTEGER, 
            exRTPMinLatePacket               INTEGER, 
            exRTPMaxLatePacket               INTEGER, 
            exRTPInitLatePacket              INTEGER, 
            exRTPLatePacketRatio             INTEGER, 
            exRTPFSKLevel                    INTEGER, 
            exRTPG711Redund                  INTEGER,
            exRTPModemMode                   INTEGER,
            exRTPAp                          INTEGER,
            exRTPDeletMode                   INTEGER,
            exRTPNorTpTime                   INTEGER,
            exRTPFaxSwTime                   INTEGER
        }
                
    exRTPParId  OBJECT-TYPE
        SYNTAX      INTEGER(1..254)
        MAX-ACCESS  not-accessible
        STATUS      current
        DESCRIPTION ""
        ::={exRTPApr2Entry 1}
        
    exRTPDecodeAdapt  OBJECT-TYPE
        SYNTAX      INTEGER
            {
                disable(0),
                enable(1)
            }
        MAX-ACCESS  read-write
        STATUS      current
        DESCRIPTION  ""
        ::={exRTPApr2Entry 2}
        
    exRTPG723Rate  OBJECT-TYPE
        SYNTAX      INTEGER
            {
                lowRate(0),
                highRate(1)
            }
        MAX-ACCESS  read-write
        STATUS      current
        DESCRIPTION ""
        ::={exRTPApr2Entry 3}
        
    exRTPPacketGenerate  OBJECT-TYPE
        SYNTAX      INTEGER
            {
                enable(0),
                disable(1)
            }
        MAX-ACCESS  read-write
        STATUS      current
        DESCRIPTION ""
        ::={exRTPApr2Entry 4}
        
    exRTPDTMFPayload  OBJECT-TYPE
        SYNTAX      INTEGER(0..255)
        MAX-ACCESS  read-write
        STATUS      current
        DESCRIPTION ""
        ::={exRTPApr2Entry 5}
        
    exRTPDTMFPayloadRedund  OBJECT-TYPE
        SYNTAX      INTEGER(0..255)
        MAX-ACCESS  read-write
        STATUS      current
        DESCRIPTION ""
        ::={exRTPApr2Entry 6}
        
    exRTPFaxDataRedund  OBJECT-TYPE
        SYNTAX      INTEGER(0..200)
        MAX-ACCESS  read-write
        STATUS      current
        DESCRIPTION ""
        ::={exRTPApr2Entry 7}
        
    exRTPT30MessageRedund  OBJECT-TYPE
        SYNTAX      INTEGER(0..7)
        MAX-ACCESS  read-write
        STATUS      current
        DESCRIPTION ""
        ::={exRTPApr2Entry 8}
        
    exRTPMasterEchoControl  OBJECT-TYPE
        SYNTAX      INTEGER
            {
                disable(0),
                enable(1)
            }
        MAX-ACCESS  read-write
        STATUS      current
        DESCRIPTION ""
        ::={exRTPApr2Entry 9}
        
    exRTPHardEchoControl  OBJECT-TYPE
        SYNTAX      INTEGER
            {
                enable(0),
                disable(1)
            }
        MAX-ACCESS  read-write
        STATUS      current
        DESCRIPTION    ""
        ::={exRTPApr2Entry 10}
        
    exRTPHardEchoNumber  OBJECT-TYPE
        SYNTAX      INTEGER
            {
                enable(0),
                disable(1)
            }
        MAX-ACCESS  read-write
        STATUS      current
        DESCRIPTION ""
        ::={exRTPApr2Entry 11}
        
    exRTPFixedTransGain  OBJECT-TYPE
        SYNTAX      INTEGER
            {
                non_linear(0),
                fixed_gain(1)
            }
        MAX-ACCESS  read-write
        STATUS      current
        DESCRIPTION ""
        ::={exRTPApr2Entry 12}
        
    exRTPEctxm  OBJECT-TYPE
        SYNTAX      INTEGER
            {
                normal(0),
                mute(1)
            }
        MAX-ACCESS  read-write
        STATUS      current
        DESCRIPTION ""
        ::={exRTPApr2Entry 13}
        
    exRTPEcrxm  OBJECT-TYPE
        SYNTAX      INTEGER
            {
                normal(0),
                mute(1)
            }
        MAX-ACCESS  read-write
        STATUS      current
        DESCRIPTION ""
        ::={exRTPApr2Entry 14}
        
    exRTPEchoControlLength  OBJECT-TYPE
        SYNTAX      INTEGER(0..15)
        MAX-ACCESS  read-write
        STATUS      current
        DESCRIPTION ""
        ::={exRTPApr2Entry 15}
        
    exRTPMinLatePacket  OBJECT-TYPE
        SYNTAX      INTEGER(0..255)
        MAX-ACCESS  read-write
        STATUS      current
        DESCRIPTION ""
        ::={exRTPApr2Entry 16}
        
    exRTPMaxLatePacket  OBJECT-TYPE
        SYNTAX      INTEGER(0..255)
        MAX-ACCESS  read-write
        STATUS      current
        DESCRIPTION ""
        ::={exRTPApr2Entry 17}
        
    exRTPInitLatePacket  OBJECT-TYPE
        SYNTAX      INTEGER(0..255)
        MAX-ACCESS  read-write
        STATUS      current
        DESCRIPTION ""
        ::={exRTPApr2Entry 18}
        
    exRTPLatePacketRatio  OBJECT-TYPE
        SYNTAX      INTEGER(0..100)
        MAX-ACCESS  read-write
        STATUS      current
        DESCRIPTION ""
        ::={exRTPApr2Entry 19}
        
    exRTPFSKLevel  OBJECT-TYPE
        SYNTAX      INTEGER(62..182)
        MAX-ACCESS  read-write
        STATUS      current
        DESCRIPTION ""
        ::={exRTPApr2Entry 20}
        
    exRTPG711Redund  OBJECT-TYPE
        SYNTAX        INTEGER
            {
                no_redundancy(0),
                package1(1),
                packages2(2),
                packages3(3)
            }
        MAX-ACCESS  read-write
        STATUS      current
        DESCRIPTION ""
        ::={exRTPApr2Entry 21}
                     
    exRTPModemMode  OBJECT-TYPE
        SYNTAX      INTEGER(0..5)
        MAX-ACCESS  read-write
        STATUS      current
        DESCRIPTION ""
        ::={exRTPApr2Entry 22}
        
    exRTPAp  OBJECT-TYPE
        SYNTAX      INTEGER(1000..65535)
        MAX-ACCESS  read-write
        STATUS      current
        DESCRIPTION ""
        ::={exRTPApr2Entry 23}
        
    exRTPDeletMode  OBJECT-TYPE
        SYNTAX      INTEGER(0..1)
        MAX-ACCESS  read-write
        STATUS      current
        DESCRIPTION ""
        ::={exRTPApr2Entry 24}
        
    exRTPNorTpTime  OBJECT-TYPE
        SYNTAX      INTEGER(0..65535)
        MAX-ACCESS  read-write
        STATUS      current
        DESCRIPTION ""
        ::={exRTPApr2Entry 25}
        
    exRTPFaxSwTime  OBJECT-TYPE
        SYNTAX      INTEGER(0..65535)
        MAX-ACCESS  read-write
        STATUS      current
        DESCRIPTION ""
        ::={exRTPApr2Entry 26}
        
    sysFileDownloadTable OBJECT-TYPE
        SYNTAX        SEQUENCE OF SysFileDownloadEntry
        MAX-ACCESS    not-accessible
        STATUS      current
        DESCRIPTION    ""
        ::={a200-mib 43}
        
        sysFileDownloadEntry OBJECT-TYPE
        SYNTAX         SysFileDownloadEntry
        MAX-ACCESS    not-accessible
        STATUS      current
        DESCRIPTION    ""
        INDEX { sysFileOperType,sysFileServerIP,sysFileDir }
        ::={sysFileDownloadTable 1}

      SysFileDownloadEntry ::=
           SEQUENCE{               
                    sysFileOperType        INTEGER, 
                    sysFileServerIP          IpAddress,     
                    sysFileDir             DisplayString,
                    sysFileName            DisplayString                              
                }
    
    sysFileOperType OBJECT-TYPE
        SYNTAX        INTEGER{
            dbfileNMSFromNE(0),
            dbfileNMSToNE(1),
            cfgfileNMSFromNE(2),
            verfileNMSFromNE(3)
            }        
        MAX-ACCESS  not-accessible
        STATUS      current
        DESCRIPTION    ""
        ::={sysFileDownloadEntry 1}
        
        sysFileServerIP OBJECT-TYPE
        SYNTAX        IpAddress
        MAX-ACCESS  not-accessible
        STATUS      current
        DESCRIPTION    ""
        ::={sysFileDownloadEntry 2}
        
        sysFileDir OBJECT-TYPE
        SYNTAX    DisplayString(SIZE(0..20))    
        MAX-ACCESS  not-accessible
        STATUS      current
        DESCRIPTION    ""
        ::={sysFileDownloadEntry 3}
        
        sysFileName OBJECT-TYPE
        SYNTAX        DisplayString(SIZE(1..20))
        MAX-ACCESS  read-write
        STATUS      current
        DESCRIPTION    ""
        ::={sysFileDownloadEntry 4}
        
    a200MgcTypeTable OBJECT-TYPE
        SYNTAX       SEQUENCE OF A200MgcTypeEntry
        MAX-ACCESS   not-accessible
        STATUS       current
        DESCRIPTION  ""
        ::={a200-mib 44}
        
    a200MgcTypeEntry OBJECT-TYPE
        SYNTAX       A200MgcTypeEntry
        MAX-ACCESS   not-accessible
        STATUS       current
        DESCRIPTION  ""
        INDEX { a200MgcTypeId }
        ::={a200MgcTypeTable 1}

    A200MgcTypeEntry ::=
        SEQUENCE
        {               
            a200MgcTypeId                      Integer32, 
            a200MgcTypeDesc                    DisplayString,     
            a200MgcTypeMulPackage              INTEGER,
            a200MgcTypeMatchType               INTEGER,    
            a200MgcTypeFo_RS                   INTEGER,
            a200MgcTypeQueryStatus             INTEGER,
            a200MgcTypeHeartBeat               Integer32,  
            a200MgcTypeRowStatus               RowStatus,
            a200MgcTypeMaxTransPkg             Integer32,
            a200MgcTypeDmLong                  Integer32,
            a200MgcTypeDmShort                 Integer32, 
            a200MgcTypeDmStart                 Integer32,
            a200MgcTypeWithTime                INTEGER,
            a200MgcTypeWithDelay               Integer32,
            a200MgcTypeProfileName             DisplayString,
            a200MgcTypeUserOut                 Integer32,
            a200MgcTypeAgOut                   Integer32,
            a200MgcTypeHeartId                 Unsigned32,
            a200MgcTypeAgRegOldMT              INTEGER,
            a200MgcTypeCanclerror              INTEGER,
            a200MgcTypeHeartbeatControlMode    INTEGER
        }
    
    a200MgcTypeId OBJECT-TYPE
        SYNTAX       Integer32(1..255)
        MAX-ACCESS   not-accessible
        STATUS       current
        DESCRIPTION  ""
        ::={a200MgcTypeEntry 1}
        
    a200MgcTypeDesc OBJECT-TYPE
        SYNTAX       DisplayString(SIZE(1..17))    
        MAX-ACCESS   read-create
        STATUS       current
        DESCRIPTION  ""
        ::={a200MgcTypeEntry 2}
        
    a200MgcTypeMulPackage OBJECT-TYPE
        SYNTAX       INTEGER
        {
            typeOne(1),
            typeMulti(2)
        }
        MAX-ACCESS   read-create
        STATUS       current
        DESCRIPTION  ""
        ::={a200MgcTypeEntry 3}
        
    a200MgcTypeMatchType OBJECT-TYPE
        SYNTAX       INTEGER
        {
            typeMax(1),
            typeMin(2)
        }
        MAX-ACCESS   read-create
        STATUS       current
        DESCRIPTION  ""
        ::={a200MgcTypeEntry 4}
        
    a200MgcTypeFo_RS OBJECT-TYPE
        SYNTAX       INTEGER
        {
            typeEnable(1),
            typeDisable(2)
        }
        MAX-ACCESS   read-create
        STATUS       current
        DESCRIPTION  ""
        ::={a200MgcTypeEntry 5}
        
    a200MgcTypeQueryStatus OBJECT-TYPE
        SYNTAX       INTEGER
        {
            typeDisable(0),
            typeEnable(1)
        }
        MAX-ACCESS   read-create
        STATUS       current
        DESCRIPTION  ""
        ::={a200MgcTypeEntry 6}
        
    a200MgcTypeHeartBeat OBJECT-TYPE
        SYNTAX       Integer32(0..65535)
        MAX-ACCESS   read-create
        STATUS       current
        DESCRIPTION  ""
        ::={a200MgcTypeEntry 7}
        
    a200MgcTypeRowStatus OBJECT-TYPE
        SYNTAX       RowStatus
        MAX-ACCESS   read-create
        STATUS       current
        DESCRIPTION  ""
        ::={a200MgcTypeEntry 8}
        
    a200MgcTypeMaxTransPkg OBJECT-TYPE
        SYNTAX       Integer32(1..3)
        MAX-ACCESS   read-create
        STATUS       current
        DESCRIPTION    ""
        ::={a200MgcTypeEntry 9}
        
    a200MgcTypeDmLong      OBJECT-TYPE
        SYNTAX       Integer32(0..50)
        MAX-ACCESS   read-create
        STATUS       current
        DESCRIPTION  ""
        ::={a200MgcTypeEntry 10}
        
    a200MgcTypeDmShort      OBJECT-TYPE
        SYNTAX       Integer32(0..50)
        MAX-ACCESS   read-create
        STATUS       current
        DESCRIPTION  ""
        ::={a200MgcTypeEntry 11}
        
    a200MgcTypeDmStart      OBJECT-TYPE
        SYNTAX       Integer32(0..50)
        MAX-ACCESS   read-create
        STATUS       current
        DESCRIPTION  ""
        ::={a200MgcTypeEntry 12}
        
    a200MgcTypeWithTime      OBJECT-TYPE
        SYNTAX       INTEGER
        {
            include(1),
            notinclude(2)
        }
        MAX-ACCESS   read-create
        STATUS       current
        DESCRIPTION  ""
        ::={a200MgcTypeEntry 13}

    a200MgcTypeWithDelay      OBJECT-TYPE
        SYNTAX       Integer32(0..65535)
        MAX-ACCESS   read-create
        STATUS       current
        DESCRIPTION  ""
        ::={a200MgcTypeEntry 14}

    a200MgcTypeProfileName      OBJECT-TYPE
        SYNTAX       DisplayString(SIZE(0..10))
        MAX-ACCESS   read-create
        STATUS       current
        DESCRIPTION  ""
        ::={a200MgcTypeEntry 15}
        
    a200MgcTypeUserOut      OBJECT-TYPE
        SYNTAX       Integer32(900..915)
        MAX-ACCESS   read-create
        STATUS       current
        DESCRIPTION  ""
        ::={a200MgcTypeEntry 16}
        
    a200MgcTypeAgOut      OBJECT-TYPE
        SYNTAX       Integer32(900..915)
        MAX-ACCESS   read-create
        STATUS       current
        DESCRIPTION  ""
        ::={a200MgcTypeEntry 17}
        
    a200MgcTypeHeartId      OBJECT-TYPE
        SYNTAX       Unsigned32
        MAX-ACCESS   read-create
        STATUS       current
        DESCRIPTION  ""
        ::={a200MgcTypeEntry 18}
        
    a200MgcTypeAgRegOldMT      OBJECT-TYPE
        SYNTAX       Integer32(1..2)
        MAX-ACCESS   read-create
        STATUS       current
        DESCRIPTION  ""
        ::={a200MgcTypeEntry 19}
        
    a200MgcTypeCanclerror      OBJECT-TYPE
        SYNTAX       Integer32(1..2)
        MAX-ACCESS   read-create
        STATUS       current
        DESCRIPTION  ""
        ::={a200MgcTypeEntry 20}
        
    a200MgcTypeHeartbeatControlMode      OBJECT-TYPE
        SYNTAX       INTEGER
        {
            byMg(1),
            bySs(2)
        }
        MAX-ACCESS   read-create
        STATUS       current
        DESCRIPTION  
            "Heartbeat control mode."
        ::={a200MgcTypeEntry 21}
        
        a200CircuitStatTable OBJECT-TYPE
        SYNTAX        SEQUENCE OF A200CircuitStatEntry
        MAX-ACCESS    not-accessible
        STATUS      current
        DESCRIPTION    ""
        ::={a200-mib 45}
        
        a200CircuitStatEntry OBJECT-TYPE
        SYNTAX         A200CircuitStatEntry
        MAX-ACCESS    not-accessible
        STATUS      current
        DESCRIPTION    ""
        INDEX { a200CirRack,a200CirShelf,a200CirSlot,a200CircuitType }
        ::={a200CircuitStatTable 1}

      A200CircuitStatEntry ::=
           SEQUENCE{               
                    a200CirRack       INTEGER,  
                    a200CirShelf      INTEGER,   
                    a200CirSlot       INTEGER,
                    a200CircuitType   INTEGER,
                    a200CircuitNum    INTEGER,
                    a200CirBusyNum    INTEGER,
                    a200CirIdleNum    INTEGER,
                    a200CirBlockNum   INTEGER
                }
     a200CirRack OBJECT-TYPE
        SYNTAX        INTEGER(1..1)
        MAX-ACCESS  not-accessible
        STATUS      current
        DESCRIPTION    ""
        ::={a200CircuitStatEntry 1} 
        
     a200CirShelf OBJECT-TYPE
        SYNTAX        INTEGER(0..5)
        MAX-ACCESS  not-accessible
        STATUS      current
        DESCRIPTION    ""
        ::={a200CircuitStatEntry 2}
        
     a200CirSlot OBJECT-TYPE
        SYNTAX        INTEGER(0..16)
        MAX-ACCESS  not-accessible
        STATUS      current
        DESCRIPTION    ""
        ::={a200CircuitStatEntry 3}    
        
     a200CircuitType OBJECT-TYPE
        SYNTAX        INTEGER{typeSlc(1),typeIPS(2)}
        MAX-ACCESS  not-accessible
        STATUS      current
        DESCRIPTION    ""
        ::={a200CircuitStatEntry 4}
        
     a200CircuitNum OBJECT-TYPE
        SYNTAX        INTEGER
        MAX-ACCESS  read-only
        STATUS      current
        DESCRIPTION    ""
        ::={a200CircuitStatEntry 5}
        
    a200CirBusyNum    OBJECT-TYPE
        SYNTAX        INTEGER
        MAX-ACCESS  read-only
        STATUS      current
        DESCRIPTION    ""
        ::={a200CircuitStatEntry 6}
        
    a200CirIdleNum    OBJECT-TYPE
        SYNTAX        INTEGER
        MAX-ACCESS  read-only
        STATUS      current
        DESCRIPTION    ""
        ::={a200CircuitStatEntry 7}        
        
    a200CirBlockNum    OBJECT-TYPE
        SYNTAX        INTEGER
        MAX-ACCESS  read-only
        STATUS      current
        DESCRIPTION    ""
        ::={a200CircuitStatEntry 8}    
        
    a200QovsTable OBJECT-TYPE
        SYNTAX        SEQUENCE OF A200QovsEntry
        MAX-ACCESS    not-accessible
        STATUS      current
        DESCRIPTION    ""
        ::={a200-mib 46}
        
    a200QovsEntry OBJECT-TYPE
        SYNTAX         A200QovsEntry
        MAX-ACCESS    not-accessible
        STATUS      current
        DESCRIPTION    ""
        INDEX { a200QovsId }
        ::={a200QovsTable 1}

    A200QovsEntry ::=
        SEQUENCE{
                 a200QovsId        INTEGER,     
                 a200QovsLoss      INTEGER,       
                 a200QovsDelay     INTEGER,       
                 a200QovsJitter    INTEGER,     
                 a200QovsRowStatus RowStatus
             } 
                
      a200QovsId OBJECT-TYPE
        SYNTAX         INTEGER(1..5)
        MAX-ACCESS  not-accessible
        STATUS      current
        DESCRIPTION    ""
        ::={a200QovsEntry 1}
        
        a200QovsLoss OBJECT-TYPE
        SYNTAX         INTEGER(1..100)
        MAX-ACCESS  read-write
        STATUS      current
        DESCRIPTION    ""
        ::={a200QovsEntry 2}
        
        a200QovsDelay OBJECT-TYPE
        SYNTAX         INTEGER(1..1000)
        MAX-ACCESS  read-write
        STATUS      current
        DESCRIPTION    ""
        ::={a200QovsEntry 3}
        
        a200QovsJitter OBJECT-TYPE
        SYNTAX         INTEGER(1..1000)
        MAX-ACCESS  read-write
        STATUS      current
        DESCRIPTION    ""
        ::={a200QovsEntry 4}
        
        a200QovsRowStatus OBJECT-TYPE
        SYNTAX         RowStatus
        MAX-ACCESS  read-create
        STATUS      current
        DESCRIPTION    ""
        ::={a200QovsEntry 5}
        
        a200BoardManagerTable OBJECT-TYPE
        SYNTAX        SEQUENCE OF A200BoardManagerEntry
        MAX-ACCESS    not-accessible
        STATUS      current
        DESCRIPTION    ""
        ::={a200-mib 47}
        
        a200BoardManagerEntry OBJECT-TYPE
        SYNTAX         A200BoardManagerEntry
        MAX-ACCESS    not-accessible
        STATUS      current
        DESCRIPTION    ""
        INDEX { a200BMRack,a200BMShelf,a200BMSlot }
        ::={a200BoardManagerTable 1}

      A200BoardManagerEntry ::=
           SEQUENCE{
                    a200BMRack       INTEGER,
                    a200BMShelf      INTEGER,
                    a200BMSlot       INTEGER,
                    a200BMOperType   INTEGER
                } 
     
        a200BMRack OBJECT-TYPE
        SYNTAX         INTEGER(1..1)
        MAX-ACCESS  not-accessible
        STATUS      current
        DESCRIPTION    ""
        ::={a200BoardManagerEntry 1}
        
        a200BMShelf OBJECT-TYPE
        SYNTAX         INTEGER(1..5)
        MAX-ACCESS  not-accessible
        STATUS      current
        DESCRIPTION    ""
        ::={a200BoardManagerEntry 2}
        
        a200BMSlot OBJECT-TYPE
        SYNTAX         INTEGER(1..17)
        MAX-ACCESS  not-accessible
        STATUS      current
        DESCRIPTION    ""
        ::={a200BoardManagerEntry 3}
        
        a200BMOperType OBJECT-TYPE
        SYNTAX         INTEGER{typeDisable(0),typeEnable(1)}
        MAX-ACCESS  read-write
        STATUS      current
        DESCRIPTION    ""
        ::={a200BoardManagerEntry 4}
        
        msagResourceStatTable OBJECT-TYPE
        SYNTAX        SEQUENCE OF MsagResourceStatEntry
        MAX-ACCESS    not-accessible
        STATUS      current
        DESCRIPTION    ""
        ::={a200-mib 48}
        
        msagResourceStatEntry OBJECT-TYPE
        SYNTAX         MsagResourceStatEntry
        MAX-ACCESS    not-accessible
        STATUS      current
        DESCRIPTION    ""
        INDEX { msagResType }
        ::={msagResourceStatTable 1}

      MsagResourceStatEntry ::=
           SEQUENCE{
                    msagResType       INTEGER,
                    msagResOKNum      INTEGER,
                    msagResFailNum    INTEGER,
                    msagUsedTime      INTEGER                    
                } 
     
        msagResType OBJECT-TYPE
        SYNTAX         INTEGER{resTone(1),resDTMF(2),resCID(3),resRTP(4)}
        MAX-ACCESS  not-accessible
        STATUS      current
        DESCRIPTION    ""
        ::={msagResourceStatEntry 1}
        
        msagResOKNum OBJECT-TYPE
        SYNTAX         INTEGER
        MAX-ACCESS  read-only
        STATUS      current
        DESCRIPTION    ""
        ::={msagResourceStatEntry 2}
        
        msagResFailNum OBJECT-TYPE
        SYNTAX         INTEGER
        MAX-ACCESS  read-only
        STATUS      current
        DESCRIPTION    ""
        ::={msagResourceStatEntry 3}
        
        msagUsedTime OBJECT-TYPE
        SYNTAX         INTEGER
        MAX-ACCESS  read-only
        STATUS      current
        DESCRIPTION    ""
        ::={msagResourceStatEntry 4}
        
        msagResClear OBJECT-TYPE
        SYNTAX         INTEGER{resClear(0)}
        MAX-ACCESS  read-write
        STATUS      current
        DESCRIPTION    ""
        ::={a200-mib 49}    
        
        a200mgcMD5InfoTable OBJECT-TYPE
        SYNTAX        SEQUENCE OF A200mgcMD5InfoEntry
        MAX-ACCESS    not-accessible
        STATUS      current
        DESCRIPTION    ""
        ::={a200-mib 52}

    rtpParMprbTable OBJECT-TYPE
        SYNTAX        SEQUENCE OF RtpParMprbEntry
        MAX-ACCESS    not-accessible
        STATUS        current
        DESCRIPTION   ""
        ::={a200-mib 61}
        
    rtpParMprbEntry OBJECT-TYPE
        SYNTAX         RtpParMprbEntry
        MAX-ACCESS     not-accessible
        STATUS         current
        DESCRIPTION    
            ""
        INDEX { rtpParMprbParid }
        ::={rtpParMprbTable 1}

    RtpParMprbEntry ::= SEQUENCE
        { 
            rtpParMprbParid                  INTEGER,
            rtpParMprbVADValue               INTEGER,
            rtpParMprbG723Rate               INTEGER,
            rtpParMprbDCFilter               INTEGER,
            rtpParMprbSilenceToPCM           INTEGER,
            rtpParMprbPcmLaw                 INTEGER,
            rtpParMprbPackGainG711Red        INTEGER,
            rtpParMprbPktToPcmGain           INTEGER,
            rtpParMprbPcmToPktGain           INTEGER,
            rtpParMprbFaxMode                INTEGER,
            rtpParMprbModemMode              INTEGER,
            rtpParMprbEcmEnable              INTEGER,
            rtpParMprbPaxPage                INTEGER,
            rtpParMprbT30MSG                 INTEGER,
            rtpParMprbSpeedLimit             INTEGER,
            rtpParMprbTcfProcudure           INTEGER,
            rtpParMprbEcEnable               INTEGER,
            rtpParMprbEcTailLen              INTEGER,
            rtpParMprbEcTxf                  INTEGER,
            rtpParMprbNlpAggress             INTEGER,
            rtpParMprbFskLevel               INTEGER,
            rtpParMprbMinDelay               INTEGER,
            rtpParMprbMaxDelay               INTEGER,
            rtpParMprbNomDelay               INTEGER,
            rtpParMprbDtmfRelayMode          INTEGER,
            rtpParMprbDtmfPayload            INTEGER,
            rtpParMprbDtmfRedundant          INTEGER,
            rtpParMprbNoRtpTime              INTEGER,
            rtpParMprbFaxSwTime              INTEGER,
            rtpParMprbElectricDtmfCid        INTEGER,
            rtpParMprbEchoCancelControlMode  INTEGER,
            rtpParMprbLowSpeedModemEcEnable  INTEGER,
            rtpParMprbHighSpeedModemEcEnable INTEGER,
            rtpParMprbFaxModemPacketTime     Integer32,
            rtpParMprbFaxPktToPcmGain        Integer32,
            rtpParMprbFaxPcmToPktGain        Integer32,
            rtpParMprbModemPktToPcmGain      Integer32,
            rtpParMprbModemPcmToPktGain      Integer32,
            rtpParMprbRtpPackageStatsEnable  INTEGER
      }
                
    rtpParMprbParid  OBJECT-TYPE
        SYNTAX      INTEGER(1..254)
        MAX-ACCESS  not-accessible
        STATUS      current
        DESCRIPTION ""
        ::={rtpParMprbEntry 1}
        
    rtpParMprbVADValue  OBJECT-TYPE
        SYNTAX      INTEGER
            {
                disable(0),
                defaultScheme(1),
                reserved(2)
            }
        MAX-ACCESS  read-write
        STATUS      current
        DESCRIPTION ""
        ::={rtpParMprbEntry 2}

    rtpParMprbG723Rate  OBJECT-TYPE
        SYNTAX      INTEGER
            {
                lowRate_5300bps(0),
                highRate_6300bps(1)
            }
        MAX-ACCESS  read-write
        STATUS      current
        DESCRIPTION ""
        ::={rtpParMprbEntry 3}
        
    rtpParMprbDCFilter  OBJECT-TYPE
        SYNTAX      INTEGER
            {
                enableDc(0),
                disableDc(1)
            }
        MAX-ACCESS  read-write
        STATUS      current
        DESCRIPTION ""
        ::={rtpParMprbEntry 4}
        
    rtpParMprbSilenceToPCM  OBJECT-TYPE
        SYNTAX      INTEGER
            {
                comfortNoise(0),
                silence(1)
            }
        MAX-ACCESS  read-write
        STATUS      current
        DESCRIPTION ""
        ::={rtpParMprbEntry 5}
        
    rtpParMprbPcmLaw  OBJECT-TYPE
        SYNTAX      INTEGER
            {
                a_Law(0),
                mu_Law(1)
            }
        MAX-ACCESS  read-write
        STATUS      current
        DESCRIPTION ""
        ::={rtpParMprbEntry 6}
        
    rtpParMprbPackGainG711Red  OBJECT-TYPE
        SYNTAX      INTEGER(0..3)
        MAX-ACCESS  read-write
        STATUS      current
        DESCRIPTION ""
        ::={rtpParMprbEntry 7}        
        
    rtpParMprbPktToPcmGain  OBJECT-TYPE
        SYNTAX      INTEGER(-20..20)
        MAX-ACCESS  read-write
        STATUS      current
        DESCRIPTION ""
        ::={rtpParMprbEntry 8}
        
    rtpParMprbPcmToPktGain  OBJECT-TYPE
        SYNTAX      INTEGER(-20..20)
        MAX-ACCESS  read-write
        STATUS      current
        DESCRIPTION ""
        ::={rtpParMprbEntry 9}
        
    rtpParMprbFaxMode  OBJECT-TYPE
        SYNTAX      INTEGER
            {
                faxRobust(0),
                t38Fax(1),
                t30Transparent(2),
                ssControlFax(11)
            }
        MAX-ACCESS  read-write
        STATUS      current
        DESCRIPTION ""
        ::={rtpParMprbEntry 10}
        
    rtpParMprbModemMode  OBJECT-TYPE
        SYNTAX      INTEGER
            {
                modemDelay5s(0),
                transparent(2),
                modemImmediate(3),
                faxImmediate(4),
                cidImmediate(5),
                ipModem(6),
                fullControl(11)
            }
        MAX-ACCESS  read-write
        STATUS      current
        DESCRIPTION ""
        ::={rtpParMprbEntry 11}
        
    rtpParMprbEcmEnable  OBJECT-TYPE
        SYNTAX      INTEGER
            {
                preventEcm(0),
                allowEcm(1)
            }
        MAX-ACCESS  read-write
        STATUS      current
        DESCRIPTION ""
        ::={rtpParMprbEntry 12}
        
    rtpParMprbPaxPage  OBJECT-TYPE
        SYNTAX      INTEGER(0..3)
        MAX-ACCESS  read-write
        STATUS      current
        DESCRIPTION ""
        ::={rtpParMprbEntry 13}
        
    rtpParMprbT30MSG  OBJECT-TYPE
        SYNTAX      INTEGER(0..7)
        MAX-ACCESS  read-write
        STATUS      current
        DESCRIPTION ""
        ::={rtpParMprbEntry 14}
        
    rtpParMprbSpeedLimit  OBJECT-TYPE
        SYNTAX      INTEGER
            {
                rate2400bps(1),
                rate4800bps(2),
                rate7200bps(3),
                rate9600bps(4),
                rate12000bps(5),
                rate14400bps(6)
            }
        MAX-ACCESS  read-write
        STATUS      current
        DESCRIPTION ""
        ::={rtpParMprbEntry 15}
        
    rtpParMprbTcfProcudure  OBJECT-TYPE
        SYNTAX      INTEGER
            {
                procedure2(0),
                procedure1(1)
            }
        MAX-ACCESS  read-write
        STATUS      current
        DESCRIPTION ""
        ::={rtpParMprbEntry 16}
        
    rtpParMprbEcEnable  OBJECT-TYPE
        SYNTAX      INTEGER
            {
                disable(0),
                enable(1)
            }
        MAX-ACCESS  read-write
        STATUS      current
        DESCRIPTION ""
        ::={rtpParMprbEntry 17}
        
    rtpParMprbEcTailLen  OBJECT-TYPE
        SYNTAX      INTEGER
            {
                tail8ms(0),
                tail16ms(1),
                tail24ms(2),
                tail32ms(3),
                tail64ms(7),
                tail128ms(15)
            }
        MAX-ACCESS  read-write
        STATUS      current
        DESCRIPTION ""
        ::={rtpParMprbEntry 18}
        
    rtpParMprbEcTxf  OBJECT-TYPE
        SYNTAX      INTEGER
            {
                not_linear(0),
                fixed_transmit(1)
            }
        MAX-ACCESS  read-write
        STATUS      current
        DESCRIPTION ""
        ::={rtpParMprbEntry 19}
        
    rtpParMprbNlpAggress  OBJECT-TYPE
        SYNTAX      INTEGER(-32767..32767)
        MAX-ACCESS  read-write
        STATUS      current
        DESCRIPTION ""
        ::={rtpParMprbEntry 20}
        
    rtpParMprbFskLevel  OBJECT-TYPE
        SYNTAX      INTEGER(62..212)
        MAX-ACCESS  read-write
        STATUS      current
        DESCRIPTION ""
        ::={rtpParMprbEntry 21}
        
    rtpParMprbMinDelay  OBJECT-TYPE
        SYNTAX      INTEGER(0..200)
        MAX-ACCESS  read-write
        STATUS      current
        DESCRIPTION ""
        ::={rtpParMprbEntry 22}

    rtpParMprbMaxDelay  OBJECT-TYPE
        SYNTAX      INTEGER(0..200)
        MAX-ACCESS  read-write
        STATUS      current
        DESCRIPTION ""
        ::={rtpParMprbEntry 23}

    rtpParMprbNomDelay  OBJECT-TYPE
        SYNTAX      INTEGER(0..200)
        MAX-ACCESS  read-write
        STATUS      current
        DESCRIPTION ""
        ::={rtpParMprbEntry 24}

    rtpParMprbDtmfRelayMode  OBJECT-TYPE
        SYNTAX      INTEGER
            {
                no_DTMF(0),
                voice_CODING(1),
                red_RFC2833(2),
                aal2_IETF(4),
                nRed_RFC2833(6)
            }
        MAX-ACCESS  read-write
        STATUS      current
        DESCRIPTION ""
        ::={rtpParMprbEntry 25}

    rtpParMprbDtmfPayload  OBJECT-TYPE
        SYNTAX      INTEGER(0..255)
        MAX-ACCESS  read-write
        STATUS      current
        DESCRIPTION ""
        ::={rtpParMprbEntry 26}
    
    rtpParMprbDtmfRedundant  OBJECT-TYPE
        SYNTAX      INTEGER(0..255)
        MAX-ACCESS  read-write
        STATUS      current
        DESCRIPTION ""
        ::={rtpParMprbEntry 27}

    rtpParMprbNoRtpTime  OBJECT-TYPE
        SYNTAX      INTEGER(0..65535)
        MAX-ACCESS  read-write
        STATUS      current
        DESCRIPTION ""
        ::={rtpParMprbEntry 28}

    rtpParMprbFaxSwTime  OBJECT-TYPE
        SYNTAX      INTEGER(0..65535)
        MAX-ACCESS  read-write
        STATUS      current
        DESCRIPTION ""
        ::={rtpParMprbEntry 29}

    rtpParMprbElectricDtmfCid  OBJECT-TYPE
        SYNTAX      INTEGER(100..630)
        MAX-ACCESS  read-write
        STATUS      current
        DESCRIPTION ""
        ::={rtpParMprbEntry 30}
    
    rtpParMprbEchoCancelControlMode  OBJECT-TYPE
        SYNTAX      INTEGER
            {
                byMg(1),
                bySs(2)
            }
        MAX-ACCESS  read-write
        STATUS      current
        DESCRIPTION 
            "Echo cancellation control mode.
             byMg(1) - Echo cancellation is controlled by 
                       rtpParMprbLowSpeedModemEcEnable and 
                       rtpParMprbHighSpeedModemEcEnable.
             bySs(2) - Echo cancellation is controlled by SS.
            "
        ::={rtpParMprbEntry 31}
        
    rtpParMprbLowSpeedModemEcEnable  OBJECT-TYPE
        SYNTAX      INTEGER
            {
                enabled(1),
                disabled(2)
            }
        MAX-ACCESS  read-write
        STATUS      current
        DESCRIPTION 
            "Enable/disable fax and low speed modem echo cancellation."
        ::={rtpParMprbEntry 32}
        
    rtpParMprbHighSpeedModemEcEnable  OBJECT-TYPE
        SYNTAX      INTEGER
            {
                enabled(1),
                disabled(2)
            }
        MAX-ACCESS  read-write
        STATUS      current
        DESCRIPTION 
            "Enable/disable high speed modem echo cancellation."
        ::={rtpParMprbEntry 33}
    
    rtpParMprbFaxModemPacketTime  OBJECT-TYPE
        SYNTAX      Integer32(0..255)
        UNITS       "ms"
        MAX-ACCESS  read-write
        STATUS      current
        DESCRIPTION 
            "The packet time when MG uses auto-negotiation fax or modem."
        DEFVAL      { 20 }
        ::={rtpParMprbEntry 34}
        
    rtpParMprbFaxPktToPcmGain  OBJECT-TYPE
        SYNTAX      Integer32(-20..20)
        UNITS       "dB"
        MAX-ACCESS  read-write
        STATUS      current
        DESCRIPTION 
            "Fax packet to PCM gain."
        DEFVAL      { 0 }
        ::={rtpParMprbEntry 35}
        
    rtpParMprbFaxPcmToPktGain  OBJECT-TYPE
        SYNTAX      Integer32(-20..20)
        UNITS       "dB"
        MAX-ACCESS  read-write
        STATUS      current
        DESCRIPTION 
            "Fax PCM to packet gain."
        DEFVAL      { 0 }
        ::={rtpParMprbEntry 36}
        
    rtpParMprbModemPktToPcmGain  OBJECT-TYPE
        SYNTAX      Integer32(-20..20)
        UNITS       "dB"
        MAX-ACCESS  read-write
        STATUS      current
        DESCRIPTION 
            "Modem packet to PCM gain."
        DEFVAL      { 0 }
        ::={rtpParMprbEntry 37}
    
    rtpParMprbModemPcmToPktGain  OBJECT-TYPE
        SYNTAX      Integer32(-20..20)
        UNITS       "dB"
        MAX-ACCESS  read-write
        STATUS      current
        DESCRIPTION 
            "Modem PCM to packet gain."
        DEFVAL      { 0 }
        ::={rtpParMprbEntry 38}
        
    rtpParMprbRtpPackageStatsEnable OBJECT-TYPE
        SYNTAX      INTEGER
            {
                enabled(1),
                disabled(2)
            }
        MAX-ACCESS  read-write
        STATUS      current
        DESCRIPTION 
            "Enable/disable RTP package statistics."
        ::={rtpParMprbEntry 39}
                                                        
    a200MediaIPOperTable OBJECT-TYPE
        SYNTAX        SEQUENCE OF A200MediaIPOPerEntry
        MAX-ACCESS    not-accessible
        STATUS      current
        DESCRIPTION    ""
        ::={a200-mib 62}
        
    a200MediaIPOPerEntry OBJECT-TYPE
        SYNTAX    A200MediaIPOPerEntry
        MAX-ACCESS    not-accessible
        STATUS      current
        DESCRIPTION    ""
        INDEX { a200MediaIPMgid }
        ::={a200MediaIPOperTable 1}
        
        A200MediaIPOPerEntry ::=
       SEQUENCE{
             a200MediaIPMgid         INTEGER,
                    a200MediaIPOldIp        IpAddress, 
                    a200MediaIPNewIp           IpAddress,     
                    a200MediaIPNewMask      IpAddress                          
                }
         a200MediaIPMgid  OBJECT-TYPE
        SYNTAX        INTEGER(1..255)
        MAX-ACCESS  not-accessible
        STATUS      current
        DESCRIPTION    ""
        ::={a200MediaIPOPerEntry 1}
                    
        a200MediaIPOldIp  OBJECT-TYPE
        SYNTAX        IpAddress
        MAX-ACCESS  read-write
        STATUS      current
        DESCRIPTION    ""
        ::={a200MediaIPOPerEntry 2}
 
         a200MediaIPNewIp  OBJECT-TYPE
        SYNTAX        IpAddress
        MAX-ACCESS  read-write
        STATUS      current
        DESCRIPTION    ""
        ::={a200MediaIPOPerEntry 3}
    
        a200MediaIPNewMask  OBJECT-TYPE
        SYNTAX        IpAddress
        MAX-ACCESS  read-write
        STATUS      current
        DESCRIPTION    ""
        ::={a200MediaIPOPerEntry 4}
          
        a200DigitMapOperTable OBJECT-TYPE
        SYNTAX        SEQUENCE OF A200DigitMapOPerEntry
        MAX-ACCESS    not-accessible
        STATUS      current
        DESCRIPTION    ""
        ::={a200-mib 63}
        
        a200DigitMapOPerEntry OBJECT-TYPE
        SYNTAX    A200DigitMapOPerEntry
        MAX-ACCESS    not-accessible
        STATUS      current
        DESCRIPTION    ""
        INDEX {a200DigitMapOPerDas}
        ::={a200DigitMapOperTable 1}
        
        A200DigitMapOPerEntry ::=
        SEQUENCE{
            a200DigitMapOPerMgid         INTEGER,
            a200DigitMapOPerSrvType      INTEGER, 
            a200DigitMapOPerDas          INTEGER,     
            a200DigitMapOPerDgtName      DisplayString,
            a200DigitMapOPerDgtMap       DisplayString,
            a200DigitMapOPerRowStatus    RowStatus                      
        }
         a200DigitMapOPerMgid  OBJECT-TYPE
        SYNTAX        INTEGER(0..3)
        MAX-ACCESS  read-create
        STATUS      current
        DESCRIPTION    ""
        ::={a200DigitMapOPerEntry 1}
                    
        a200DigitMapOPerSrvType  OBJECT-TYPE
        SYNTAX    INTEGER{h248(0),selfchange(1),sip(2),urgencymap(3)}
        MAX-ACCESS  read-create
        STATUS      current
        DESCRIPTION    ""
        ::={a200DigitMapOPerEntry 2}
 
         a200DigitMapOPerDas  OBJECT-TYPE
        SYNTAX        INTEGER(1..255)
        MAX-ACCESS  not-accessible
        STATUS      current
        DESCRIPTION    ""
        ::={a200DigitMapOPerEntry 3}
    
        a200DigitMapOPerDgtName  OBJECT-TYPE
        SYNTAX        DisplayString(SIZE(1..20))
        MAX-ACCESS  read-create
        STATUS      current
        DESCRIPTION    ""
        ::={a200DigitMapOPerEntry 4}

        a200DigitMapOPerDgtMap  OBJECT-TYPE
        SYNTAX        DisplayString(SIZE(1..250))
        MAX-ACCESS  read-create
        STATUS      current
        DESCRIPTION    ""
        ::={a200DigitMapOPerEntry 5}

        a200DigitMapOPerRowStatus  OBJECT-TYPE
        SYNTAX        RowStatus
        MAX-ACCESS  read-create
        STATUS      current
        DESCRIPTION    ""
        ::={a200DigitMapOPerEntry 6}
                            
        a200mgcMD5InfoEntry OBJECT-TYPE
        SYNTAX         A200mgcMD5InfoEntry
        MAX-ACCESS    not-accessible
        STATUS      current
        DESCRIPTION    ""
        INDEX { a200mgcMD5infoId }
        ::={a200mgcMD5InfoTable 1}

      A200mgcMD5InfoEntry ::=
           SEQUENCE{
                    a200mgcMD5infoId   INTEGER,
                    a200mgcMD5ki       DisplayString,
                    a200mgcMGinfo      DisplayString,
                    a200mgcMD5G        INTEGER,
                    a200mgcMD5Plength  INTEGER,
                    a200mgcMD5P        DisplayString,
                    a200mgcMD5RowStatus RowStatus                    
                }
        a200mgcMD5infoId OBJECT-TYPE
        SYNTAX         INTEGER(1..10)
        MAX-ACCESS  not-accessible
        STATUS      current
        DESCRIPTION    ""
        ::={a200mgcMD5InfoEntry 1}
        
        a200mgcMD5ki OBJECT-TYPE
        SYNTAX          DisplayString(SIZE(1..16))
        MAX-ACCESS  read-create
        STATUS      current
        DESCRIPTION    ""
        ::={a200mgcMD5InfoEntry 2}
        
        a200mgcMGinfo OBJECT-TYPE
        SYNTAX          DisplayString(SIZE(1..16))
        MAX-ACCESS  read-create
        STATUS      current
        DESCRIPTION    ""
        ::={a200mgcMD5InfoEntry 3}
        
        a200mgcMD5G OBJECT-TYPE
        SYNTAX          INTEGER(0..10)
        MAX-ACCESS  read-create
        STATUS      current
        DESCRIPTION    ""
        ::={a200mgcMD5InfoEntry 4}
        
        a200mgcMD5Plength OBJECT-TYPE
        SYNTAX          INTEGER(1..192)
        MAX-ACCESS  read-create
        STATUS      current
        DESCRIPTION    ""
        ::={a200mgcMD5InfoEntry 5}
        
        a200mgcMD5P OBJECT-TYPE
        SYNTAX          DisplayString(SIZE(1..192))
        MAX-ACCESS  read-create
        STATUS      current
        DESCRIPTION    ""
        ::={a200mgcMD5InfoEntry 6}
        
        a200mgcMD5RowStatus OBJECT-TYPE
        SYNTAX          RowStatus
        MAX-ACCESS  read-create
        STATUS      current
        DESCRIPTION    ""
        ::={a200mgcMD5InfoEntry 7}             
                     
  a200VoipRouteTable OBJECT-TYPE
    SYNTAX        SEQUENCE OF A200VoipRouteEntry
    MAX-ACCESS    not-accessible
    STATUS      current
    DESCRIPTION    ""
    ::={a200-mib 65}
        
  a200VoipRouteEntry OBJECT-TYPE
    SYNTAX          A200VoipRouteEntry
    MAX-ACCESS    not-accessible
    STATUS        current
    DESCRIPTION    ""
    INDEX{
      a200VoipRouteRackno,
      a200VoipRouteShelfno,
      a200VoipRouteSlotno,
      a200VoipRoutePhyport,
      a200VoipRoutePortip,
      a200VoipRouteSrcip,
      a200VoipRouteDestip
    }
    ::={a200VoipRouteTable 1}

  A200VoipRouteEntry ::=
    SEQUENCE{
        a200VoipRouteRackno      INTEGER,
        a200VoipRouteShelfno     INTEGER,
        a200VoipRouteSlotno      INTEGER,
        a200VoipRoutePhyport     INTEGER,
        a200VoipRoutePortip      IpAddress,
        a200VoipRouteSrcip       IpAddress,
        a200VoipRouteDestip      IpAddress,
        a200VoipRouteSrcmask     IpAddress,
        a200VoipRouteDestmask    IpAddress,
        a200VoipRouteMgID        INTEGER,
        a200VoipRouteType        INTEGER,
        a200VoipRouteNexthop     IpAddress,
        a200VoipRouteNexthopMac  MacAddress,
        a200VoipRouteArpTime     INTEGER,
        a200VoipRouteRowStatus   RowStatus
    }

  a200VoipRouteRackno OBJECT-TYPE
    SYNTAX         INTEGER(1..3)
    MAX-ACCESS  not-accessible
    STATUS      current
    DESCRIPTION    ""
    ::={a200VoipRouteEntry 1}

  a200VoipRouteShelfno OBJECT-TYPE
    SYNTAX         INTEGER(0..4)
    MAX-ACCESS  not-accessible
    STATUS      current
    DESCRIPTION    ""
    ::={a200VoipRouteEntry 2}

  a200VoipRouteSlotno OBJECT-TYPE
    SYNTAX         INTEGER(1..23)
    MAX-ACCESS  not-accessible
    STATUS      current
    DESCRIPTION    ""
    ::={a200VoipRouteEntry 3}

  a200VoipRoutePhyport OBJECT-TYPE
    SYNTAX         INTEGER(5..5)
    MAX-ACCESS  not-accessible
    STATUS      current
    DESCRIPTION    ""
    ::={a200VoipRouteEntry 4}

  a200VoipRoutePortip OBJECT-TYPE
    SYNTAX         IpAddress
    MAX-ACCESS  not-accessible
    STATUS      current
    DESCRIPTION    ""
    ::={a200VoipRouteEntry 5}

  a200VoipRouteSrcip OBJECT-TYPE
    SYNTAX         IpAddress
    MAX-ACCESS  not-accessible
    STATUS      current
    DESCRIPTION    ""
    ::={a200VoipRouteEntry 6}

  a200VoipRouteDestip OBJECT-TYPE
    SYNTAX          IpAddress
    MAX-ACCESS  not-accessible
    STATUS        current
    DESCRIPTION    ""
    ::={a200VoipRouteEntry 7}

  a200VoipRouteSrcmask OBJECT-TYPE
    SYNTAX          IpAddress
    MAX-ACCESS  read-only
    STATUS        current
    DESCRIPTION    ""
    ::={a200VoipRouteEntry 8}

  a200VoipRouteDestmask OBJECT-TYPE
    SYNTAX          IpAddress
    MAX-ACCESS  read-create
    STATUS        current
    DESCRIPTION    ""
    ::={a200VoipRouteEntry 9}

  a200VoipRouteMgID OBJECT-TYPE
    SYNTAX          INTEGER(1..255)
    MAX-ACCESS  read-create
    STATUS      current
    DESCRIPTION    ""
    ::={a200VoipRouteEntry 10}

  a200VoipRouteType OBJECT-TYPE
    SYNTAX          INTEGER(1..1)
    MAX-ACCESS  read-create
    STATUS      current
    DESCRIPTION    ""
    ::={a200VoipRouteEntry 11}

  a200VoipRouteNexthop OBJECT-TYPE
    SYNTAX          IpAddress
    MAX-ACCESS  read-create
    STATUS      current
    DESCRIPTION    ""
    ::={a200VoipRouteEntry 12}

  a200VoipRouteNexthopMac OBJECT-TYPE
    SYNTAX          MacAddress
    MAX-ACCESS  read-create
    STATUS        current
    DESCRIPTION    ""
    ::={a200VoipRouteEntry 13}

  a200VoipRouteArpTime OBJECT-TYPE
    SYNTAX         INTEGER(5..720)
    MAX-ACCESS  read-create
    STATUS      current
    DESCRIPTION    ""
    ::={a200VoipRouteEntry 14}

  a200VoipRouteRowStatus OBJECT-TYPE
    SYNTAX          RowStatus
    MAX-ACCESS  read-create
    STATUS        current
    DESCRIPTION    ""
    ::={a200VoipRouteEntry 15}
    
        

--------------------------------------       
-------- voip statistic start --------
     
   a200VoipStatistic OBJECT IDENTIFIER ::={a200-mib 66}
   
   zxVoipStatisticGlobal OBJECT IDENTIFIER ::={a200VoipStatistic 1}      

-- packet statistic
   
   zxVoipPacketStatistic OBJECT IDENTIFIER ::={a200VoipStatistic 2}   
      
   zxVoipStatisticPacketSend  OBJECT-TYPE
     SYNTAX                Unsigned32
     MAX-ACCESS            read-only
     STATUS                current
     DESCRIPTION           ""
     ::={zxVoipPacketStatistic 1}
      
   zxVoipStatisticPacketReceive  OBJECT-TYPE
     SYNTAX                Unsigned32
     MAX-ACCESS            read-only
     STATUS                current
     DESCRIPTION           ""
     ::={zxVoipPacketStatistic 2}  
      
   zxVoipStatisticPacketLost  OBJECT-TYPE
     SYNTAX                Unsigned32
     MAX-ACCESS            read-only
     STATUS                current
     DESCRIPTION           ""
     ::={zxVoipPacketStatistic 3}   
     
   zxVoipStatisticPacketResend  OBJECT-TYPE
     SYNTAX                Unsigned32
     MAX-ACCESS            read-only
     STATUS                current
     DESCRIPTION           ""
     ::={zxVoipPacketStatistic 4}  
      
   zxVoipStatisticPacketError  OBJECT-TYPE
     SYNTAX                Unsigned32
     MAX-ACCESS            read-only
     STATUS                current
     DESCRIPTION           ""
     ::={zxVoipPacketStatistic 5}   
     
   zxVoipStatisticPacketUnknown  OBJECT-TYPE
     SYNTAX                Unsigned32
     MAX-ACCESS            read-only
     STATUS                current
     DESCRIPTION           ""
     ::={zxVoipPacketStatistic 6}         
     
               
-- call statistic
       
   zxVoipCallStatistic OBJECT IDENTIFIER ::={a200VoipStatistic 3}  
   
   zxVoipCallStatisticGlobal OBJECT IDENTIFIER ::={zxVoipCallStatistic 1}   
   
    zxVoipCurCallDuration  OBJECT-TYPE
        SYNTAX      INTEGER
        UNITS       "seconds"
        MAX-ACCESS  read-only
        STATUS      current
        DESCRIPTION
            "The current call duration."
        ::= { zxVoipCallStatisticGlobal 1 }   
        
    zxVoipTotalCallDuration  OBJECT-TYPE
        SYNTAX      INTEGER
        UNITS       "seconds"
        MAX-ACCESS  read-only
        STATUS      current
        DESCRIPTION
            "The total call duration."
        ::= { zxVoipCallStatisticGlobal 2 }   
       
      zxVoipCallTimes  OBJECT-TYPE
        SYNTAX      INTEGER
        MAX-ACCESS  read-only
        STATUS      current
        DESCRIPTION
            "The total call duration."
        ::= { zxVoipCallStatisticGlobal 3 }               
   
   zxVoipCallPortStatisticTable OBJECT-TYPE    
       SYNTAX       SEQUENCE OF ZxVoipCallPortStatisticEntry
       MAX-ACCESS   not-accessible
       STATUS       current
       DESCRIPTION 
           ""
       ::={zxVoipCallStatistic 2}     
   
    zxVoipCallPortStatisticEntry  OBJECT-TYPE
        SYNTAX      ZxVoipCallPortStatisticEntry
        MAX-ACCESS  not-accessible
        STATUS      current
        DESCRIPTION ""
        INDEX  { zxVoipCallPortStatisticRack, zxVoipCallPortStatisticShelf,
                 zxVoipCallPortStatisticSlot, zxVoipCallPortStatisticUserIndex }
        ::= { zxVoipCallPortStatisticTable 1 }
        
    ZxVoipCallPortStatisticEntry ::= SEQUENCE {
        zxVoipCallPortStatisticRack      INTEGER,
        zxVoipCallPortStatisticShelf     INTEGER,
        zxVoipCallPortStatisticSlot      INTEGER,
        zxVoipCallPortStatisticUserIndex INTEGER,
        zxVoipPortCurCallDuration        INTEGER,      
        zxVoipPortTotalCallDuration      INTEGER,
        zxVoipPortCallTimes              INTEGER
    }
    
    zxVoipCallPortStatisticRack  OBJECT-TYPE
        SYNTAX      INTEGER
        MAX-ACCESS  not-accessible
        STATUS      current
        DESCRIPTION
            "The rack index, should be 1 for MAP."
        ::= { zxVoipCallPortStatisticEntry 1 }   
           
    zxVoipCallPortStatisticShelf  OBJECT-TYPE
        SYNTAX      INTEGER
        MAX-ACCESS  not-accessible
        STATUS      current
        DESCRIPTION
            "The shelf index, should be 3 for MAP."
        ::= { zxVoipCallPortStatisticEntry 2 }   
        
    zxVoipCallPortStatisticSlot  OBJECT-TYPE
        SYNTAX      INTEGER
        MAX-ACCESS  not-accessible
        STATUS      current
        DESCRIPTION
            "The slot index, it's the actual slot no."
        ::= { zxVoipCallPortStatisticEntry 3 }   
        
    zxVoipCallPortStatisticUserIndex  OBJECT-TYPE
        SYNTAX      INTEGER
        MAX-ACCESS  not-accessible
        STATUS      current
        DESCRIPTION
            "The port index, start from 0 for MAP."
        ::= { zxVoipCallPortStatisticEntry 4 }        
       
    zxVoipPortCurCallDuration  OBJECT-TYPE
        SYNTAX      INTEGER
        UNITS       "seconds"
        MAX-ACCESS  read-only
        STATUS      current
        DESCRIPTION
            "The current call duration."
        ::= { zxVoipCallPortStatisticEntry 5 }   
        
    zxVoipPortTotalCallDuration  OBJECT-TYPE
        SYNTAX      INTEGER
        UNITS       "seconds"
        MAX-ACCESS  read-only
        STATUS      current
        DESCRIPTION
            "The total call duration."
        ::= { zxVoipCallPortStatisticEntry 6 }   
       
      zxVoipPortCallTimes  OBJECT-TYPE
        SYNTAX      INTEGER
        MAX-ACCESS  read-only
        STATUS      current
        DESCRIPTION
            "The total call duration."
        ::= { zxVoipCallPortStatisticEntry 7 }            
          
     
   zxVoipVoiceFlowStatisticTable OBJECT-TYPE    
        SYNTAX      SEQUENCE OF ZxVoipVoiceFlowStatisticEntry
        MAX-ACCESS  not-accessible
        STATUS      current
        DESCRIPTION 
            ""
        ::={a200VoipStatistic 4}     
   
    zxVoipVoiceFlowStatisticEntry  OBJECT-TYPE
        SYNTAX      ZxVoipVoiceFlowStatisticEntry
        MAX-ACCESS  not-accessible
        STATUS      current
        DESCRIPTION ""
        INDEX  { zxVoiceFlowStatisticRack, zxVoiceFlowStatisticShelf,
                 zxVoiceFlowStatisticSlot, zxVoiceFlowStatisticUserIndex }
        ::= { zxVoipVoiceFlowStatisticTable 1 }
        
    ZxVoipVoiceFlowStatisticEntry ::= SEQUENCE {
        zxVoiceFlowStatisticRack                     INTEGER,
        zxVoiceFlowStatisticShelf                    INTEGER,
        zxVoiceFlowStatisticSlot                     INTEGER,
        zxVoiceFlowStatisticUserIndex                INTEGER,
        zxVoiceFlowStatisticSendPakcageSpeed         INTEGER,
        zxVoiceFlowStatisticReceivePakcageSpeed      INTEGER,
        zxVoiceFlowStatisticSendPakcageLossRate      INTEGER,
        zxVoiceFlowStatisticReceivePakcageLossRate   INTEGER,
        zxVoiceFlowStatisticSendJitter               INTEGER,
        zxVoiceFlowStatisticReceiveJitter            INTEGER,
        zxVoiceFlowStatisticDelay                    INTEGER,
        zxVoiceFlowStatisticSendPackageNum           INTEGER,
        zxVoiceFlowStatisticReceivePackageNum        INTEGER,
        zxVoiceFlowStatisticRecordTime               DisplayString
    }
    
    zxVoiceFlowStatisticRack  OBJECT-TYPE
        SYNTAX      INTEGER
        MAX-ACCESS  not-accessible
        STATUS      current
        DESCRIPTION
            "The rack index, should be 1 for MAP."
        ::= { zxVoipVoiceFlowStatisticEntry 1 }   
           
    zxVoiceFlowStatisticShelf  OBJECT-TYPE
        SYNTAX      INTEGER
        MAX-ACCESS  not-accessible
        STATUS      current
        DESCRIPTION
            "The shelf index, should be 3 for MAP."
        ::= { zxVoipVoiceFlowStatisticEntry 2 }   
        
    zxVoiceFlowStatisticSlot  OBJECT-TYPE
        SYNTAX      INTEGER
        MAX-ACCESS  not-accessible
        STATUS      current
        DESCRIPTION
            "The slot index, it's the actual slot no."
        ::= { zxVoipVoiceFlowStatisticEntry 3 }   
        
    zxVoiceFlowStatisticUserIndex  OBJECT-TYPE
        SYNTAX      INTEGER
        MAX-ACCESS  not-accessible
        STATUS      current
        DESCRIPTION
            "The port index, start from 0 for MAP."
        ::= { zxVoipVoiceFlowStatisticEntry 4 }     
        
   zxVoiceFlowStatisticSendPakcageSpeed OBJECT-TYPE
        SYNTAX      INTEGER
        MAX-ACCESS  read-only
        STATUS      current
        DESCRIPTION    
            ""
        ::={zxVoipVoiceFlowStatisticEntry 5}
        
     zxVoiceFlowStatisticReceivePakcageSpeed OBJECT-TYPE
        SYNTAX      INTEGER
        MAX-ACCESS  read-only
        STATUS      current
        DESCRIPTION    
            ""
        ::={zxVoipVoiceFlowStatisticEntry 6}        
        
     zxVoiceFlowStatisticSendPakcageLossRate OBJECT-TYPE
        SYNTAX      INTEGER(0..100)
        MAX-ACCESS  read-only
        STATUS      current
        DESCRIPTION    ""
        ::={zxVoipVoiceFlowStatisticEntry 7}        
       
     zxVoiceFlowStatisticReceivePakcageLossRate OBJECT-TYPE
        SYNTAX      INTEGER(0..100)
        MAX-ACCESS  read-only
        STATUS      current
        DESCRIPTION    
            ""
        ::={zxVoipVoiceFlowStatisticEntry 8}    
               
     zxVoiceFlowStatisticSendJitter OBJECT-TYPE
        SYNTAX      INTEGER
        MAX-ACCESS  read-only
        STATUS      current
        DESCRIPTION    
            ""
        ::={zxVoipVoiceFlowStatisticEntry 9}        
       
     zxVoiceFlowStatisticReceiveJitter OBJECT-TYPE
        SYNTAX      INTEGER
        MAX-ACCESS  read-only
        STATUS      current
        DESCRIPTION    
            ""
        ::={zxVoipVoiceFlowStatisticEntry 10}           
       
     zxVoiceFlowStatisticDelay OBJECT-TYPE
        SYNTAX      INTEGER
        MAX-ACCESS  read-only
        STATUS      current
        DESCRIPTION    
            ""
        ::={zxVoipVoiceFlowStatisticEntry 11}    
           
     zxVoiceFlowStatisticSendPackageNum OBJECT-TYPE
        SYNTAX      INTEGER
        MAX-ACCESS  read-only
        STATUS      current
        
        DESCRIPTION    
            ""
        ::={zxVoipVoiceFlowStatisticEntry 12}        
       
     zxVoiceFlowStatisticReceivePackageNum OBJECT-TYPE
        SYNTAX      INTEGER
        MAX-ACCESS  read-only
        STATUS      current
        DESCRIPTION    ""
        ::={zxVoipVoiceFlowStatisticEntry 13}  
       
     zxVoiceFlowStatisticRecordTime      OBJECT-TYPE     
        SYNTAX      DisplayString  ( SIZE ( 1 .. 20  ) )
        MAX-ACCESS  read-only
        STATUS      current
        DESCRIPTION     
            "Time Stamp of the updated session record.For example:
             yyyy-mm-dd HH:MM:SS.(2001-01-01 02:22:33)."
        ::= { zxVoipVoiceFlowStatisticEntry 14 }             
       
--------  voip statistic end  --------
--------------------------------------


--------------------------------------       
---------- voip parameters -----------
     
    a200VoipObjects OBJECT IDENTIFIER ::={a200-mib 67}

    zxVoipGlobalObjects OBJECT IDENTIFIER ::={a200VoipObjects 1}     
     
    zxVoipHeartbeatEnable  OBJECT-TYPE
        SYNTAX       INTEGER 
        {
            enable(1), 
            disable(2) 
        }
        MAX-ACCESS   read-write
        STATUS       current
        DESCRIPTION 
            "Enable/disable the heartbeat."             
        DEFVAL      { enable }
        ::={zxVoipGlobalObjects 2}   
        
    zxVoipDtmfGain  OBJECT-TYPE
        SYNTAX       Integer32(-20..20)
        MAX-ACCESS   read-write
        STATUS       current
        DESCRIPTION 
            "DTMF gain"
        ::={zxVoipGlobalObjects 3}
         
    zxVoipVoiceDelay  OBJECT-TYPE
        SYNTAX       Integer32(0..3)
        MAX-ACCESS   read-write
        STATUS       current
        DESCRIPTION    
            "Voice delay"
        ::={zxVoipGlobalObjects 4}
         
    zxVoiceFramesPerRtp  OBJECT-TYPE
        SYNTAX       Integer32(10..20)
        MAX-ACCESS   read-write
        STATUS       current
        DESCRIPTION    
            "Voice frames number per rtp packet"
        ::={zxVoipGlobalObjects 5}
         
    zxVoiceFlashTime  OBJECT-TYPE
        SYNTAX       Integer32(90..380)
        UNITS        "ms"
        MAX-ACCESS   read-write
        STATUS       current   
        DESCRIPTION    
            "Flash time"
        DEFVAL      { 90 }           
        ::={zxVoipGlobalObjects 6}
         
    zxVoiceHookoffTime  OBJECT-TYPE
        SYNTAX       Integer32(100..300)
        UNITS        "ms"
        MAX-ACCESS   read-write
        STATUS       current
        DESCRIPTION    
            "Hookoff time"
        DEFVAL      { 300 }           
        ::={zxVoipGlobalObjects 7}
         
    zxVoiceNoAnswerTime  OBJECT-TYPE
        SYNTAX       Integer32(0..65535)
        UNITS        "seconds"
        MAX-ACCESS   read-write
        STATUS       current
        DESCRIPTION    
            "No answer time"
        DEFVAL      { 60 }
        ::={zxVoipGlobalObjects 8}
         
    zxVoiceBusyTime  OBJECT-TYPE
        SYNTAX       Integer32(0..65535)
        UNITS        "seconds"
        MAX-ACCESS   read-write
        STATUS       current
        DESCRIPTION    
            "Busy time"            
        DEFVAL      { 70 }
        ::={zxVoipGlobalObjects 9}
         
    zxVoiceHowltoneTime  OBJECT-TYPE
        SYNTAX       Integer32(0..65535)
        UNITS        "seconds"
        MAX-ACCESS   read-write
        STATUS       current
        DESCRIPTION    
            "Howltone time"           
        DEFVAL      { 60 }
        ::={zxVoipGlobalObjects 10}
          
    zxVoipProtocolType  OBJECT-TYPE           
        SYNTAX       BITS 
        {
            h248(0),
            mgcp(1),
            sip(2),
            isdn(3)
        }        
        MAX-ACCESS   read-write
        STATUS       current
        DESCRIPTION  
            "The enabled voip protocol type."          
        DEFVAL      { h248 }
        ::={zxVoipGlobalObjects 11}
        
    zxVoipCapabilities OBJECT-TYPE
        SYNTAX      BITS 
        {
            heartbeatControlMode(0)
        }
        MAX-ACCESS  read-only
        STATUS      current
        DESCRIPTION
            "The voice global management capabilities of this equipment.
             The bit value 1 means the function represented by this bit is
             supported by this equipment.            
             bit 1: value 1 means support a200MgcTypeHeartbeatControlMode in 
                    a200MgcTypeTable.
             NOTE: No recommended to display it in NMS."
        ::= {zxVoipGlobalObjects 12}
                  
-- voip port 
    
   zxVoipPortTable  OBJECT-TYPE    
     SYNTAX  SEQUENCE OF ZxVoipPortEntry
     MAX-ACCESS not-accessible
     STATUS current
     DESCRIPTION ""
     ::={a200VoipObjects 2}     
   
    zxVoipPortEntry  OBJECT-TYPE
        SYNTAX      ZxVoipPortEntry
        MAX-ACCESS  not-accessible
        STATUS      current
        DESCRIPTION ""
        INDEX  { zxVoipPortRack, zxVoipPortShelf,
                 zxVoipPortSlot, zxVoipPortUserIndex }
        ::= { zxVoipPortTable 1 }
        
    ZxVoipPortEntry ::= SEQUENCE {
        zxVoipPortRack              INTEGER,
        zxVoipPortShelf             INTEGER,
        zxVoipPortSlot              INTEGER,
        zxVoipPortUserIndex         INTEGER,
        zxVoipPortType              INTEGER,
        zxVoipPortRegisterEnable    INTEGER,     
        zxVoipPortRegisterStatus    INTEGER        
    }    

    zxVoipPortRack  OBJECT-TYPE
        SYNTAX      INTEGER
        MAX-ACCESS  not-accessible
        STATUS      current
        DESCRIPTION
            "The rack index, should be 1 for MAP."
        ::= { zxVoipPortEntry 1 }   
           
    zxVoipPortShelf  OBJECT-TYPE
        SYNTAX      INTEGER
        MAX-ACCESS  not-accessible
        STATUS      current
        DESCRIPTION
            "The shelf index, should be 3 for MAP."
        ::= { zxVoipPortEntry 2 }   
        
    zxVoipPortSlot  OBJECT-TYPE
        SYNTAX      INTEGER
        MAX-ACCESS  not-accessible
        STATUS      current
        DESCRIPTION
            "The slot index, it's the actual slot no."
        ::= { zxVoipPortEntry 3 }   
        
    zxVoipPortUserIndex  OBJECT-TYPE
        SYNTAX      INTEGER
        MAX-ACCESS  not-accessible
        STATUS      current
        DESCRIPTION
            "The port index, start from 0 for MAP."
        ::= { zxVoipPortEntry 4 }         
         
    zxVoipPortType  OBJECT-TYPE
        SYNTAX      INTEGER {fxs(1),fxo(2)} 
            MAX-ACCESS  read-only
        STATUS      current
        DESCRIPTION
            "The port index."
        ::= { zxVoipPortEntry 5 }   
        
    zxVoipPortRegisterEnable  OBJECT-TYPE
        SYNTAX      INTEGER { enable(1), disable(2) }
            MAX-ACCESS  read-write
        STATUS      current
        DESCRIPTION
            "enable or disable port register."
        ::= { zxVoipPortEntry 6 }                  
        
    zxVoipPortRegisterStatus  OBJECT-TYPE
        SYNTAX      INTEGER {registered(1), unregistered(2)}
            MAX-ACCESS  read-only
        STATUS      current
        DESCRIPTION
            "The register status."
        ::= { zxVoipPortEntry 7 } 
        
--------------------------------------------------------------------------------
-- SIP User Table
--------------------------------------------------------------------------------

    a200SipObjects OBJECT IDENTIFIER ::={a200-mib 68}

    zxMsagSipUserTable OBJECT-TYPE
        SYNTAX   SEQUENCE OF ZxMsagSipUserEntry
        MAX-ACCESS   not-accessible
        STATUS   current
        DESCRIPTION  "Sip user table"
        ::={a200SipObjects 1}
    
    zxMsagSipUserEntry OBJECT-TYPE
        SYNTAX    ZxMsagSipUserEntry
        MAX-ACCESS   not-accessible
        STATUS   current
        DESCRIPTION  "Sip user entry"
        INDEX {zxMsagSipUserRack, zxMsagSipUserShelf,
            zxMsagSipUserSlot, zxMsagSipUserIndex,zxMsagSipUserOperType}
        ::={zxMsagSipUserTable 1}
   
    ZxMsagSipUserEntry ::=
        SEQUENCE{
            zxMsagSipUserRack              INTEGER,
            zxMsagSipUserShelf             INTEGER, 
            zxMsagSipUserSlot              INTEGER,     
            zxMsagSipUserIndex             INTEGER, 
            zxMsagSipUserOperNum           INTEGER,
            zxMsagSipUserOperType          INTEGER, 
            zxMsagSipUserSipDigit          DisplayString,
            zxMsagSipUserAuthusername      DisplayString,
            zxMsagSipUserId                DisplayString,   
            zxMsagSipUserType              INTEGER,
            zxMsagSipUserBeginNo           INTEGER,
            zxMsagSipUserDigitLen          INTEGER,   
            zxMsagSipUserPassword          DisplayString,     
            zxMsagSipUserDstngRing         INTEGER,
            zxMsagSipUserHotlineType       INTEGER,
            zxMsagSipUserHotlineNum        DisplayString,   
            zxMsagSipUserDigitMap          DisplayString,   
            zxMsagSipUserGroupId           INTEGER, 
            zxMsagSipUserRowStatus         RowStatus
        }
    
    zxMsagSipUserRack  OBJECT-TYPE
        SYNTAX       INTEGER(1..1)
        MAX-ACCESS   not-accessible
        STATUS   current
        DESCRIPTION  "Rack of sip user"
        DEFVAL{1}
        ::={zxMsagSipUserEntry 1}
       
    zxMsagSipUserShelf  OBJECT-TYPE
        SYNTAX       INTEGER(3..3)
        MAX-ACCESS  not-accessible
        STATUS   current
        DESCRIPTION  "Shelf of sip user"
        DEFVAL{1}
        ::={zxMsagSipUserEntry 2}
    
    zxMsagSipUserSlot  OBJECT-TYPE
        SYNTAX       INTEGER(1..4)
        MAX-ACCESS   not-accessible
        STATUS   current
        DESCRIPTION  "Slot of sip user"
        DEFVAL{3}
        ::={zxMsagSipUserEntry 3}
    
    zxMsagSipUserIndex  OBJECT-TYPE
        SYNTAX       INTEGER(0..47)
        MAX-ACCESS  not-accessible
        STATUS   current
        DESCRIPTION  "Index of sip user"
        DEFVAL{1}
        ::={zxMsagSipUserEntry 4}
    
    zxMsagSipUserOperType  OBJECT-TYPE
        SYNTAX      INTEGER{sipuser(1),sipuserid(2)}
        MAX-ACCESS  not-accessible
        STATUS   current
        DESCRIPTION  "Operation type"
        ::={zxMsagSipUserEntry 5}  

    zxMsagSipUserOperNum  OBJECT-TYPE
        SYNTAX       INTEGER(1..48)
        MAX-ACCESS  read-create
        STATUS   current
        DESCRIPTION  "Sip user operaton number"
        DEFVAL{32}
        ::={zxMsagSipUserEntry 6}
    
    zxMsagSipUserSipDigit  OBJECT-TYPE
        SYNTAX       DisplayString(SIZE(1..32))
        MAX-ACCESS  read-create
        STATUS   current
        DESCRIPTION  "Sip user digit"
        ::={zxMsagSipUserEntry 7}
    
    zxMsagSipUserAuthusername  OBJECT-TYPE
        SYNTAX   DisplayString(SIZE(0..64))
        MAX-ACCESS  read-create
        STATUS   current
        DESCRIPTION  "Sip user name"
        ::={zxMsagSipUserEntry 8}
    
    zxMsagSipUserId   OBJECT-TYPE
        SYNTAX   DisplayString(SIZE(1..64))
        MAX-ACCESS  read-create
        STATUS   current
        DESCRIPTION  "Sip user id"
        ::={zxMsagSipUserEntry 9}
    
    zxMsagSipUserType  OBJECT-TYPE
        SYNTAX      INTEGER{type1(1),type2(2),type3(3)}
        MAX-ACCESS  read-create
        STATUS   current
        DESCRIPTION  "   Type 1:USER00100100000-USER00100100031,
        type 2:USER0-USER31
        type 3:User000-USER031"
        DEFVAL{1}
        ::={zxMsagSipUserEntry 10}
    
    zxMsagSipUserBeginNo   OBJECT-TYPE
        SYNTAX       INTEGER(0..65535)
        MAX-ACCESS  read-create
        STATUS   current
        DESCRIPTION  "Sip user begin no"
        DEFVAL{0}
        ::={zxMsagSipUserEntry 11}
    
    zxMsagSipUserDigitLen  OBJECT-TYPE
        SYNTAX       INTEGER(0..64)
        MAX-ACCESS  read-create
        STATUS   current
        DESCRIPTION  "Sip user digit length"
        DEFVAL{3}
        ::={zxMsagSipUserEntry 12}
    
    zxMsagSipUserPassword  OBJECT-TYPE
        SYNTAX       DisplayString(SIZE(0..16))
        MAX-ACCESS  read-create
        STATUS   current
        DESCRIPTION  "User password"
        ::={zxMsagSipUserEntry 13}
    
    zxMsagSipUserDstngRing  OBJECT-TYPE
        SYNTAX       INTEGER(0..15)
        MAX-ACCESS  read-create
        STATUS   current
        DESCRIPTION  "Ring type"
        DEFVAL{15}
        ::={zxMsagSipUserEntry 14}
    
    zxMsagSipUserHotlineType  OBJECT-TYPE
        SYNTAX       INTEGER{
                      noneHotline(1),
                      instantHotline(2),
                      delayHotline(3)
                      }
        MAX-ACCESS  read-create
        STATUS   current
        DESCRIPTION  "Hotline type"
        DEFVAL{1}    
        ::={zxMsagSipUserEntry 15}
    
    zxMsagSipUserHotlineNum  OBJECT-TYPE
        SYNTAX       DisplayString(SIZE(0..16))
        MAX-ACCESS  read-create
        STATUS   current
        DESCRIPTION  "Hotline number"
        ::={zxMsagSipUserEntry 16}
    
    zxMsagSipUserDigitMap  OBJECT-TYPE
        SYNTAX       DisplayString(SIZE(0..20))
        MAX-ACCESS  read-create
        STATUS   current
        DESCRIPTION  "Digital map name"
        ::={zxMsagSipUserEntry 17}

    zxMsagSipUserGroupId  OBJECT-TYPE
        SYNTAX       INTEGER(1..500)
        MAX-ACCESS  read-create
        STATUS   current
        DESCRIPTION  "Sip user group id"        
        ::={zxMsagSipUserEntry 18}
    
    zxMsagSipUserRowStatus  OBJECT-TYPE
        SYNTAX       RowStatus
        MAX-ACCESS  read-create
        STATUS   current
        DESCRIPTION  "Row status"
        ::={zxMsagSipUserEntry 50}       
  
------------------------------------------------------------------------------
-- E1 Trunk Table
------------------------------------------------------------------------------

    a200TrunkObjects OBJECT IDENTIFIER ::={a200-mib 69}

    a200TrunkTable OBJECT-TYPE
        SYNTAX      SEQUENCE OF A200TrunkEntry
        MAX-ACCESS  not-accessible
        STATUS      current
        DESCRIPTION 
            "The table a200TrunkTable contains status of trunk user.             
             trunk means ISDN(30B+D) in there.
            "
        ::={a200TrunkObjects 1}

    a200TrunkEntry OBJECT-TYPE
        SYNTAX      A200TrunkEntry
        MAX-ACCESS  not-accessible
        STATUS      current
        DESCRIPTION 
            "An entry in a200TrunkTable."
        INDEX 
        { 
            a200TrunkRack,
            a200TrunkShelf,
            a200TrunkSlot,
            a200TrunkE1No, 
            a200TrunkTimeSlot
        }
        ::={a200TrunkTable 1}

    A200TrunkEntry ::=
        SEQUENCE
        {
            a200TrunkRack       Integer32,
            a200TrunkShelf      Integer32,
            a200TrunkSlot       Integer32,
            a200TrunkE1No       Integer32,
            a200TrunkTimeSlot   Integer32,
            a200TrunkStatus     BITS          
        }

     a200TrunkRack    OBJECT-TYPE
         SYNTAX       Integer32
         MAX-ACCESS   not-accessible
         STATUS       current
         DESCRIPTION 
             "Rack of trunk user."
         ::= { a200TrunkEntry 1 }

     a200TrunkShelf   OBJECT-TYPE
         SYNTAX       Integer32
         MAX-ACCESS   not-accessible
         STATUS       current
         DESCRIPTION 
             "Shelf of trunk user."
         ::= { a200TrunkEntry 2 }

     a200TrunkSlot    OBJECT-TYPE
         SYNTAX       Integer32
         MAX-ACCESS   not-accessible
         STATUS       current
         DESCRIPTION 
             "Slot of trunk user."
         ::= { a200TrunkEntry 3 }

     a200TrunkE1No    OBJECT-TYPE
         SYNTAX       Integer32
         MAX-ACCESS   not-accessible
         STATUS       current
         DESCRIPTION 
             "E1 Port No of trunk user."
         ::= { a200TrunkEntry 4 }

     a200TrunkTimeSlot    OBJECT-TYPE
         SYNTAX      Integer32
         MAX-ACCESS  not-accessible
         STATUS      current
         DESCRIPTION 
             "Timeslot No of trunk user."
         ::= { a200TrunkEntry 5 }

     a200TrunkStatus     OBJECT-TYPE
         SYNTAX      BITS 
         {
             commOff(0),
             powerOff(1),
             fault(2),
             manualBlock(3),
             unused1(4),
             unused2(5),
             testing(6),
             h248(7),
             seizure(8),
             call(9),
             spc(10)
         }
         MAX-ACCESS  read-only
         STATUS      current
         DESCRIPTION 
             "Status of trunk user.
              commOff     (0)  - value 1 means communication break off.

              powerOff    (1)  - value 1 means power off.
                             
              fault       (2)  - value 1 means fault.

              manualBlock (3)  - value 1 means block manually.

              unused1     (4)  - unused.

              unused2     (5)  - unused.

              testing     (6)  - value 1 means testing.

              h248        (7)  - value 1 means this timeslot is used by 
                                 IUA(ISDN Q.921-User Adaptation Layer) user.
                                     
              seizure     (8)  - value 1 means busy.
                                           
              call        (9)  - value 1 means this timeslot is used by v5 
                                 user.

              spc         (10) - spc(Signaling Point Code) :value 1 means this 
                                 timeslot is used by signaling.                          
             "
         ::= { a200TrunkEntry 6 }   
     
---------- voip parameters -----------
--------------------------------------    
    
-- End of System-Control Related Operation MIB

-- Sip Related Definition Begin
-- added by li.bin11
    a200sip OBJECT IDENTIFIER ::= { a200-mib 64 }
  
-- a200CtlPortTable implemented above already

-- sip proxy server Table Begin
    a200sipproxysvrTable   OBJECT-TYPE
    SYNTAX  SEQUENCE OF A200SipProxySvrEntry
    MAX-ACCESS not-accessible
    STATUS current
    DESCRIPTION ""
    ::={a200sip 1}
    
    a200sipproxysvrentry   OBJECT-TYPE
    SYNTAX  A200SipProxySvrEntry
    MAX-ACCESS  not-accessible
    STATUS  current
    DESCRIPTION ""
    INDEX {a200sipproxysvrindex}
    ::={a200sipproxysvrTable 1}
    
    A200SipProxySvrEntry ::=
    SEQUENCE{
        a200sipproxysvrindex         INTEGER,
        a200sipproxysvrip            IpAddress,
        a200sipproxysvrRowStatus     RowStatus,
        a200sipproxysvrPort          INTEGER,
        a200sipproxysvrDomainName    DisplayString,
        a200sipproxysvrNamingType    INTEGER
    } 
    
    a200sipproxysvrindex OBJECT-TYPE
    SYNTAX      INTEGER(1..4)
    MAX-ACCESS  not-accessible
    STATUS      current
    DESCRIPTION ""
    ::={a200sipproxysvrentry 1}
    
    a200sipproxysvrip OBJECT-TYPE
    SYNTAX      IpAddress
    MAX-ACCESS  read-create
    STATUS      current
    DESCRIPTION ""
    ::={a200sipproxysvrentry 2}
    
    a200sipproxysvrRowStatus OBJECT-TYPE
    SYNTAX      RowStatus
    MAX-ACCESS  read-create
    STATUS      current
    DESCRIPTION "insert,delete"
    ::={a200sipproxysvrentry 3}
    
    a200sipproxysvrPort OBJECT-TYPE
    SYNTAX      INTEGER(0..65535)
    MAX-ACCESS  read-create
    STATUS      current
    DESCRIPTION "SIP proxy server port"
    DEFVAL      { 5060 }
    ::={a200sipproxysvrentry 4}
    a200sipproxysvrDomainName OBJECT-TYPE
    SYNTAX      DisplayString(0..64)
    MAX-ACCESS  read-create
    STATUS      current
    DESCRIPTION "SIP proxy server domain name."
    ::={a200sipproxysvrentry 5}
    
    a200sipproxysvrNamingType  OBJECT-TYPE
    SYNTAX      INTEGER{useIp(1),useDomainName(2)}
    MAX-ACCESS  read-create
    STATUS      current
    DESCRIPTION "Sip proxy server naming type."
    DEFVAL      { useIp }
    ::={a200sipproxysvrentry 6}
    
--sip proxy server Table End

--sipuser Table Begin
    a200sipuserTable OBJECT-TYPE
    SYNTAX        SEQUENCE OF A200SipUserEntry
    MAX-ACCESS    not-accessible
    STATUS      current
    DESCRIPTION    ""
    ::={a200sip 2}
    
    a200sipuserentry OBJECT-TYPE
    SYNTAX      A200SipUserEntry
    MAX-ACCESS    not-accessible
    STATUS      current
    DESCRIPTION    ""
    INDEX {a200sipuserrack, a200sipusershelf, 
            a200sipuserslot, a200sipuserindex}
    ::={a200sipuserTable 1}
    
    A200SipUserEntry ::=
    SEQUENCE{
        a200sipuserrack              INTEGER,
        a200sipusershelf             INTEGER, 
        a200sipuserslot              INTEGER,     
        a200sipuserindex             INTEGER,    
        a200sipusernum               INTEGER,
        a200sipusersipdigit          DisplayString,            
        a200sipuserpassword          DisplayString,
        a200sipuserdstngring         INTEGER,
        a200sipuserhotlinetype       INTEGER,
        a200sipuserhotlinenum        DisplayString,
        a200sipuserdgtmapname        DisplayString,
    a200sipuserauthusername      DisplayString,
    a200sipuserauthtype          INTEGER,
    a200sipuserauthbegno         INTEGER,
    a200sipuserauthdigitlen      INTEGER,   
        a200sipuseridnum             INTEGER,
        a200sipusertmidfix           OCTET STRING,
        a200sipuseridtype            INTEGER,
        a200sipuseriddigitlen        INTEGER,
        a200sipuseridbeginno         INTEGER,
        a200sipuserid                DisplayString,
        a200SipUserRowStatus         RowStatus
    }
    
    a200sipuserrack  OBJECT-TYPE
    SYNTAX        INTEGER(1..1)
    MAX-ACCESS  not-accessible
    STATUS      current
    DESCRIPTION    ""
    ::={a200sipuserentry 1}
                
    a200sipusershelf  OBJECT-TYPE
    SYNTAX        INTEGER(3..3)
    MAX-ACCESS  not-accessible
    STATUS      current
    DESCRIPTION    ""
    ::={a200sipuserentry 2}

    a200sipuserslot  OBJECT-TYPE
    SYNTAX        INTEGER(1..4)
    MAX-ACCESS  not-accessible
    STATUS      current
    DESCRIPTION    ""
    ::={a200sipuserentry 3}

    a200sipuserindex  OBJECT-TYPE
    SYNTAX        INTEGER(0..47)
    MAX-ACCESS  not-accessible
    STATUS      current
    DESCRIPTION    ""
    ::={a200sipuserentry 4}
    
    a200sipusernum  OBJECT-TYPE
    SYNTAX        INTEGER(1..48)
    MAX-ACCESS  read-create
    STATUS      current
    DESCRIPTION    "used for add&del sipuser"
    ::={a200sipuserentry 5}

    a200sipusersipdigit  OBJECT-TYPE
    SYNTAX        DisplayString(SIZE(1..16))
    MAX-ACCESS  read-create
    STATUS      current
    DESCRIPTION    ""
    ::={a200sipuserentry 6}
            
    a200sipuserpassword  OBJECT-TYPE
    SYNTAX        DisplayString(SIZE(1..16))
    MAX-ACCESS  read-create
    STATUS      current
    DESCRIPTION    ""
    ::={a200sipuserentry 7}
    
    a200sipuserdstngring  OBJECT-TYPE
    SYNTAX        INTEGER(0..15)
    MAX-ACCESS  read-create
    STATUS      current
    DESCRIPTION    ""
    ::={a200sipuserentry 8}
    
    a200sipuserhotlinetype  OBJECT-TYPE
    SYNTAX        INTEGER(0..2)
    MAX-ACCESS  read-create
    STATUS      current
    DESCRIPTION    ""
    ::={a200sipuserentry 9}
    
    a200sipuserhotlinenum  OBJECT-TYPE
    SYNTAX        DisplayString(SIZE(1..16))
    MAX-ACCESS  read-create
    STATUS      current
    DESCRIPTION    ""
    ::={a200sipuserentry 10}
    
    a200sipuserdgtmapname  OBJECT-TYPE
    SYNTAX        DisplayString(SIZE(1..20))
    MAX-ACCESS  read-create
    STATUS      current
    DESCRIPTION    ""
    ::={a200sipuserentry 11}
    
    a200sipuserauthusername  OBJECT-TYPE
    SYNTAX        DisplayString(SIZE(0..32))
    MAX-ACCESS  read-create
    STATUS      current
    DESCRIPTION    ""
    ::={a200sipuserentry 12}

    a200sipuserauthtype  OBJECT-TYPE
    SYNTAX        INTEGER{type1(1),type2(2),type3(3)}
    MAX-ACCESS  read-create
    STATUS      current
    DESCRIPTION    "Type 1:USER00100100000-USER00100100047,
       type 2:USER0-USER47
       type 3:User000-USER047"
    ::={a200sipuserentry 13}

    a200sipuserauthbegno  OBJECT-TYPE
    SYNTAX        INTEGER(0..65535)
    MAX-ACCESS  read-create
    STATUS      current
    DESCRIPTION    "Sip user begin no"
    ::={a200sipuserentry 14}
    
    a200sipuserauthdigitlen  OBJECT-TYPE
    SYNTAX        INTEGER(0..64)
    MAX-ACCESS  read-create
    STATUS      current
    DESCRIPTION    "Sip username digit length"
    ::={a200sipuserentry 15}
    
    a200sipuseridnum  OBJECT-TYPE
    SYNTAX        INTEGER(1..48)
    MAX-ACCESS  read-create
    STATUS      current
    DESCRIPTION    "used for add&del sipuserid"
    ::={a200sipuserentry 16}
    
    a200sipusertmidfix  OBJECT-TYPE
    SYNTAX        OCTET STRING(SIZE(0..63))
    MAX-ACCESS  read-create
    STATUS      current
    DESCRIPTION    ""
    ::={a200sipuserentry 17}
    
    a200sipuseridtype  OBJECT-TYPE
    SYNTAX        INTEGER{type1(1),type2(2),type3(3)}
    MAX-ACCESS  read-create
    STATUS      current
    DESCRIPTION    "Type1:SIP00100100000-SIP00100100047,type2:SIP0-SIP47,type3:SIP000-SIP047"
    ::={a200sipuserentry 18}
    
    a200sipuseriddigitlen  OBJECT-TYPE
    SYNTAX        INTEGER(2..63)
    MAX-ACCESS  read-create
    STATUS      current
    DESCRIPTION    ""
    ::={a200sipuserentry 19}
    
    a200sipuseridbeginno  OBJECT-TYPE
    SYNTAX        INTEGER(0..65535)
    MAX-ACCESS  read-create
    STATUS      current
    DESCRIPTION    ""
    ::={a200sipuserentry 20}
    
    a200sipuserid  OBJECT-TYPE
    SYNTAX        DisplayString(SIZE(0..63))
    MAX-ACCESS  read-only
    STATUS      current
    DESCRIPTION    ""
    ::={a200sipuserentry 21}       
    
    a200SipUserRowStatus  OBJECT-TYPE
    SYNTAX        RowStatus
    MAX-ACCESS  read-create
    STATUS      current
    DESCRIPTION    "insert,delete"
    ::={a200sipuserentry 50}
--sipuser Table End

-- End of Sip



------------ MSAG5200_2.0.2_Alarm.mib (trap)--------

   zxNetwork            OBJECT IDENTIFIER ::= { zte 1010 }
   zxAn                 OBJECT IDENTIFIER ::= { zxNetwork  3 }
   zxA10                OBJECT IDENTIFIER ::= { zxAn 1 }
   zxSu30               OBJECT IDENTIFIER ::= { zxA10 1 }

    sysSrcMib           MODULE-IDENTITY
          LAST-UPDATED    "0404210000Z"  -- Apr. 21, 2004
        ORGANIZATION    "Zhongxing Telcom Co. Ltd."
        CONTACT-INFO    "Zhongxing Telcom Co. Ltd.
                         E-mail: info@mail.zte.com.cn
                         http  : www.zte.com.cn or www.zhongxing.com"
        DESCRIPTION     "System Resource MIB definition."
        REVISION        "0404210000Z"  -- Apr. 21, 2004
        DESCRIPTION     "Initial MIB creation."
        
        ::= { zxSu30 6 }

    sysConfigClkSrcList OBJECT-TYPE
        SYNTAX          Integer32
        MAX-ACCESS      read-write
        STATUS          current
        DESCRIPTION
            ""
        ::= { sysSrcMib 20 }
    
    sysCurrentClkSrcList    OBJECT-TYPE
        SYNTAX              Integer32
        MAX-ACCESS          read-only
        STATUS              current
        DESCRIPTION
            ""
        ::= { sysSrcMib 21 }
    
    sysAvailableClkSrcList  OBJECT-TYPE
        SYNTAX              Integer32
        MAX-ACCESS          read-only
        STATUS              current
        DESCRIPTION
            ""
        ::= { sysSrcMib 22 }
     
   sysMceOpenFlag   OBJECT-TYPE
        SYNTAX      Integer32
        MAX-ACCESS  read-write
        STATUS      current
        DESCRIPTION
            ""
        ::= { sysSrcMib 23 }
     
   sysClkSrcRank   OBJECT-TYPE
        SYNTAX      OCTET STRING
        MAX-ACCESS  read-write
        STATUS      current
        DESCRIPTION
            ""
        ::= { sysSrcMib 24 } 
        
    
   msagTrap OBJECT IDENTIFIER ::= { zxSu30 100 }
   msagTrapId  OBJECT IDENTIFIER ::= { msagTrap 1 }
   
    msagMpStartAlarm  OBJECT-TYPE
          SYNTAX      INTEGER
          MAX-ACCESS  read-write
          STATUS      current
          DESCRIPTION
           ""
        ::= { msagTrapId 150 }
    msagMpCpuAlarm  OBJECT-TYPE
          SYNTAX      INTEGER
          MAX-ACCESS  read-write
          STATUS      current
          DESCRIPTION
           ""
        ::= { msagTrapId 151 }
    msagMpDiskAlarm  OBJECT-TYPE
          SYNTAX      INTEGER
          MAX-ACCESS  read-write
          STATUS      current
          DESCRIPTION
           ""
        ::= { msagTrapId 152 }
    msagMpDataLoadAlarm  OBJECT-TYPE
          SYNTAX      INTEGER
          MAX-ACCESS  read-write
          STATUS      current
          DESCRIPTION
           ""
        ::= { msagTrapId 153 }
    msagMpDataSynAlarm  OBJECT-TYPE
          SYNTAX      INTEGER
          MAX-ACCESS  read-write
          STATUS      current
          DESCRIPTION
           ""
        ::= { msagTrapId 154 }
    msagCommMateAlarm  OBJECT-TYPE
          SYNTAX      INTEGER
          MAX-ACCESS  read-write
          STATUS      current
          DESCRIPTION
           ""
        ::= { msagTrapId 155 }
    msagH248MemArrangeAlarm  OBJECT-TYPE
          SYNTAX      INTEGER
          MAX-ACCESS  read-write
          STATUS      current
          DESCRIPTION
           ""
        ::= { msagTrapId 156 }
    msagH248LinkAlarm  OBJECT-TYPE
          SYNTAX      INTEGER
          MAX-ACCESS  read-write
          STATUS      current
          DESCRIPTION
           ""
        ::= { msagTrapId 157 }
    msagH248LinkAbnormalAlarm  OBJECT-TYPE
          SYNTAX      INTEGER
          MAX-ACCESS  read-write
          STATUS      current
          DESCRIPTION
           ""
        ::= { msagTrapId 158 }
    msagPcmAlarm  OBJECT-TYPE
          SYNTAX      INTEGER
          MAX-ACCESS  read-write
          STATUS      current
          DESCRIPTION
           ""
        ::= { msagTrapId 159 }
    msagCallMemArrangeAlarm  OBJECT-TYPE
          SYNTAX      INTEGER
          MAX-ACCESS  read-write
          STATUS      current
          DESCRIPTION
           ""
        ::= { msagTrapId 160 }
    msagUnitOusAlarm  OBJECT-TYPE
          SYNTAX      INTEGER
          MAX-ACCESS  read-write
          STATUS      current
          DESCRIPTION
           ""
        ::= { msagTrapId 161 }
    msagPortOusAlarm  OBJECT-TYPE
          SYNTAX      INTEGER
          MAX-ACCESS  read-write
          STATUS      current
          DESCRIPTION
           ""
        ::= { msagTrapId 162 }
    msagSunitOusAlarm  OBJECT-TYPE
          SYNTAX      INTEGER
          MAX-ACCESS  read-write
          STATUS      current
          DESCRIPTION
           ""
        ::= { msagTrapId 163 }
    msagPortTypeAlarm  OBJECT-TYPE
          SYNTAX      INTEGER
          MAX-ACCESS  read-write
          STATUS      current
          DESCRIPTION
           ""
        ::= { msagTrapId 164 }
    msagSunitTypeAlarm  OBJECT-TYPE
          SYNTAX      INTEGER
          MAX-ACCESS  read-write
          STATUS      current
          DESCRIPTION
           ""
        ::= { msagTrapId 165 }
    msagPortSetStateAlarm  OBJECT-TYPE
          SYNTAX      INTEGER
          MAX-ACCESS  read-write
          STATUS      current
          DESCRIPTION
           ""
        ::= { msagTrapId 166 }
    msagNoTnetAlarm  OBJECT-TYPE
          SYNTAX      INTEGER
          MAX-ACCESS  read-write
          STATUS      current
          DESCRIPTION
           ""
        ::= { msagTrapId 167 }
    msagPpwrPowerAlarm  OBJECT-TYPE
          SYNTAX      INTEGER
          MAX-ACCESS  read-write
          STATUS      current
          DESCRIPTION
           ""
        ::= { msagTrapId 168 }
    msagCpuOverloadAlarm  OBJECT-TYPE
          SYNTAX      INTEGER
          MAX-ACCESS  read-write
          STATUS      current
          DESCRIPTION
           ""
        ::= { msagTrapId 169 }
    msagPpwrFanAlarm  OBJECT-TYPE
          SYNTAX      INTEGER
          MAX-ACCESS  read-write
          STATUS      current
          DESCRIPTION
           ""
        ::= { msagTrapId 170 }
    msagPcmSlipInform  OBJECT-TYPE
          SYNTAX      INTEGER
          MAX-ACCESS  read-write
          STATUS      current
          DESCRIPTION
           ""
        ::= { msagTrapId 171 }
    msagLapdLinkInform  OBJECT-TYPE
          SYNTAX      INTEGER
          MAX-ACCESS  read-write
          STATUS      current
          DESCRIPTION
           ""
        ::= { msagTrapId 172 }
    msagFileErrInform  OBJECT-TYPE
          SYNTAX      INTEGER
          MAX-ACCESS  read-write
          STATUS      current
          DESCRIPTION
           ""
        ::= { msagTrapId 173 }
    msagPpAutoLoadFail  OBJECT-TYPE
          SYNTAX      INTEGER
          MAX-ACCESS  read-write
          STATUS      current
          DESCRIPTION
           ""
        ::= { msagTrapId 174 }
    msagPortChgoverInform  OBJECT-TYPE
          SYNTAX      INTEGER
          MAX-ACCESS  read-write
          STATUS      current
          DESCRIPTION
           ""
        ::= { msagTrapId 175 }
    msagPortMainInform  OBJECT-TYPE
          SYNTAX      INTEGER
          MAX-ACCESS  read-write
          STATUS      current
          DESCRIPTION
           ""
        ::= { msagTrapId 176 }
    msagPortStbInform  OBJECT-TYPE
          SYNTAX      INTEGER
          MAX-ACCESS  read-write
          STATUS      current
          DESCRIPTION
           ""
        ::= { msagTrapId 177 }
    msagToneLoadSuccInform  OBJECT-TYPE
          SYNTAX      INTEGER
          MAX-ACCESS  read-write
          STATUS      current
          DESCRIPTION
           ""
        ::= { msagTrapId 178 }
    msagToneLoadFailInform  OBJECT-TYPE
          SYNTAX      INTEGER
          MAX-ACCESS  read-write
          STATUS      current
          DESCRIPTION
           ""
        ::= { msagTrapId 179 }
    msagAdslLinkdownInform  OBJECT-TYPE
          SYNTAX      INTEGER
          MAX-ACCESS  read-write
          STATUS      current
          DESCRIPTION
           ""
        ::= { msagTrapId 180 }
    msagAdslLinkupInform  OBJECT-TYPE
          SYNTAX      INTEGER
          MAX-ACCESS  read-write
          STATUS      current
          DESCRIPTION
           ""
        ::= { msagTrapId 181 }
    msagAdslAtucRateInform  OBJECT-TYPE
          SYNTAX      INTEGER
          MAX-ACCESS  read-write
          STATUS      current
          DESCRIPTION
           ""
        ::= { msagTrapId 182 }
    msagAdslAturRateInform  OBJECT-TYPE
          SYNTAX      INTEGER
          MAX-ACCESS  read-write
          STATUS      current
          DESCRIPTION
           ""
        ::= { msagTrapId 183 }
    msagAdslAtucLofsInform  OBJECT-TYPE
          SYNTAX      INTEGER
          MAX-ACCESS  read-write
          STATUS      current
          DESCRIPTION
           ""
        ::= { msagTrapId 184 }
    msagAdslAtucLossInform  OBJECT-TYPE
          SYNTAX      INTEGER
          MAX-ACCESS  read-write
          STATUS      current
          DESCRIPTION
           ""
        ::= { msagTrapId 185 }
    msagAdslAtucLprsInform  OBJECT-TYPE
          SYNTAX      INTEGER
          MAX-ACCESS  read-write
          STATUS      current
          DESCRIPTION
           ""
        ::= { msagTrapId 186 }
    msagAdslAtucEssInform  OBJECT-TYPE
          SYNTAX      INTEGER
          MAX-ACCESS  read-write
          STATUS      current
          DESCRIPTION
           ""
        ::= { msagTrapId 187 }
    msagAdslAturLofsInform  OBJECT-TYPE
          SYNTAX      INTEGER
          MAX-ACCESS  read-write
          STATUS      current
          DESCRIPTION
           ""
        ::= { msagTrapId 188 }
    msagAdslAturLossInform  OBJECT-TYPE
          SYNTAX      INTEGER
          MAX-ACCESS  read-write
          STATUS      current
          DESCRIPTION
           ""
        ::= { msagTrapId 189 }
    msagAdslAturLprsInform  OBJECT-TYPE
          SYNTAX      INTEGER
          MAX-ACCESS  read-write
          STATUS      current
          DESCRIPTION
           ""
        ::= { msagTrapId 190 }
    msagAdslAturEssInform  OBJECT-TYPE
          SYNTAX      INTEGER
          MAX-ACCESS  read-write
          STATUS      current
          DESCRIPTION
           ""
        ::= { msagTrapId 191 }
    msagIpsResourceAlarm  OBJECT-TYPE
          SYNTAX      INTEGER
          MAX-ACCESS  read-write
          STATUS      current
          DESCRIPTION
           ""
        ::= { msagTrapId 192 }
    msagServiceQosPoorAlarm  OBJECT-TYPE
          SYNTAX      INTEGER
          MAX-ACCESS  read-write
          STATUS      current
          DESCRIPTION
           ""
        ::= { msagTrapId 193 }
    msagEnableBoardInform  OBJECT-TYPE
          SYNTAX      INTEGER
          MAX-ACCESS  read-write
          STATUS      current
          DESCRIPTION
           ""
        ::= { msagTrapId 194 }
    msagSubcpuHdlccommAlarm  OBJECT-TYPE
          SYNTAX      INTEGER
          MAX-ACCESS  read-write
          STATUS      current
          DESCRIPTION
           ""
        ::= { msagTrapId 195 }
    msagUnittypeeAlarm  OBJECT-TYPE
          SYNTAX      INTEGER
          MAX-ACCESS  read-write
          STATUS      current
          DESCRIPTION
           ""
        ::= { msagTrapId 196 }
    msagMainCpuTooBusyAlarm  OBJECT-TYPE
          SYNTAX      INTEGER
          MAX-ACCESS  read-write
          STATUS      current
          DESCRIPTION
           ""
        ::= { msagTrapId 197 }
    msagSlaveCpuTooBusyAlarm  OBJECT-TYPE
          SYNTAX      INTEGER
          MAX-ACCESS  read-write
          STATUS      current
          DESCRIPTION
           ""
        ::= { msagTrapId 198 }
    msagSlaveCpuWorkerrAlarm  OBJECT-TYPE
          SYNTAX      INTEGER
          MAX-ACCESS  read-write
          STATUS      current
          DESCRIPTION
           ""
        ::= { msagTrapId 199 }
    msagCnicWorkerrAlarm  OBJECT-TYPE
          SYNTAX      INTEGER
          MAX-ACCESS  read-write
          STATUS      current
          DESCRIPTION
           ""
        ::= { msagTrapId 200 }
    msagMpChgoverInform  OBJECT-TYPE
          SYNTAX      INTEGER
          MAX-ACCESS  read-write
          STATUS      current
          DESCRIPTION
           ""
        ::= { msagTrapId 201 }
    msagSfChgoverInform  OBJECT-TYPE
          SYNTAX      INTEGER
          MAX-ACCESS  read-write
          STATUS      current
          DESCRIPTION
           ""
        ::= { msagTrapId 202 }
    msagBoardStateChgInform  OBJECT-TYPE
          SYNTAX      INTEGER
          MAX-ACCESS  read-write
          STATUS      current
          DESCRIPTION
           ""
        ::= { msagTrapId 203 }
    msagIsdnSctpInform  OBJECT-TYPE
          SYNTAX      INTEGER
          MAX-ACCESS  read-write
          STATUS      current
          DESCRIPTION
           ""
        ::= { msagTrapId 204 }
    msagIsdnSctpAlarm  OBJECT-TYPE
          SYNTAX      INTEGER
          MAX-ACCESS  read-write
          STATUS      current
          DESCRIPTION
           ""
        ::= { msagTrapId 205 }
    msagIsdnIuaInform  OBJECT-TYPE
          SYNTAX      INTEGER
          MAX-ACCESS  read-write
          STATUS      current
          DESCRIPTION
           ""
        ::= { msagTrapId 206 }
    msagIsdnIuaAlarm  OBJECT-TYPE
          SYNTAX      INTEGER
          MAX-ACCESS  read-write
          STATUS      current
          DESCRIPTION
           ""
        ::= { msagTrapId 207 }  
    msagV5ProtoAlarm  OBJECT-TYPE
          SYNTAX      INTEGER
          MAX-ACCESS  read-write
          STATUS      current
          DESCRIPTION
           ""
        ::= { msagTrapId 208 }
        
   msagV5LinkAlarm  OBJECT-TYPE
          SYNTAX      INTEGER
          MAX-ACCESS  read-write
          STATUS      current
          DESCRIPTION
           ""
        ::= { msagTrapId 209 }     
    
    msagIPSChannelFaultAlarm  OBJECT-TYPE
          SYNTAX      INTEGER
          MAX-ACCESS  read-write
          STATUS      current
          DESCRIPTION
           ""
        ::= { msagTrapId 215 }
        
    msagH248ErrorCodeInform  OBJECT-TYPE
          SYNTAX      INTEGER
          MAX-ACCESS  read-write
          STATUS      current
          DESCRIPTION
           ""
        ::= { msagTrapId 213 }    
    
    msagSLCCommoffAlarm  OBJECT-TYPE
          SYNTAX      INTEGER
          MAX-ACCESS  read-write
          STATUS      current
          DESCRIPTION
           ""
        ::= { msagTrapId 219 }

    msagSlcFreqOffOnHookAlarm  NOTIFICATION-TYPE
          OBJECTS     
              { 
                  msagTrapRack,
                  msagTrapShelf,
                  msagTrapSlot,
                  msagTrapUnitNo,
                  msagTrapSunitNo,
                  msagTrapPortNum
              }
          STATUS      current
          DESCRIPTION
              "The trap means on-hook or off-hook is too frequently , and over
               threshold." 
        ::= { msagTrapId 220 }

    msagSlcGroundedAlarm  NOTIFICATION-TYPE
          OBJECTS     
              { 
                  msagTrapRack,
                  msagTrapShelf,
                  msagTrapSlot,
                  msagTrapUnitNo,
                  msagTrapSunitNo,
                  msagTrapPortNum
              }
          STATUS      current
          DESCRIPTION
              "The trap means subscriber line grounded"
        ::= { msagTrapId 221 }
                
    msagFELinkDownAlarm  OBJECT-TYPE
          SYNTAX      INTEGER
          MAX-ACCESS  read-write
          STATUS      current
          DESCRIPTION
           ""
        ::= { msagTrapId 1019 }
            
        
   msagMgcpLinkAlarm NOTIFICATION-TYPE
        OBJECTS { msagTrapReason,msagTrapLinkState,msagTrapMgcNo }
        STATUS  current
        DESCRIPTION
            "Mgcp link down."
       ::= { msagTrapId 1200 }             
           
   msagSlcAcAlarm NOTIFICATION-TYPE
        OBJECTS 
            { 
              msagTrapRack,
              msagTrapShelf,
              msagTrapSlot,
              msagTrapUnitNo,
              msagTrapSunitNo,
              msagTrapPortNum
            }
        STATUS  current
        DESCRIPTION
            "Circuit AC Voltage Alarm."
       ::= { msagTrapId 1201 }     
   
   msagSlcDcAlarm NOTIFICATION-TYPE
        OBJECTS 
            { 
              msagTrapRack,
              msagTrapShelf,
              msagTrapSlot,
              msagTrapUnitNo,
              msagTrapSunitNo,
              msagTrapPortNum
            }
        STATUS  current
        DESCRIPTION
            "Circuit DC Voltage Alarm."
       ::= { msagTrapId 1202 }  
   
     msagTrapRestoreId  OBJECT IDENTIFIER ::= { msagTrap 10 }
   
    msagMpStartRestore  OBJECT-TYPE
          SYNTAX      INTEGER
          MAX-ACCESS  read-write
          STATUS      current
          DESCRIPTION
           ""
        ::= { msagTrapRestoreId 150 }
    msagMpCpuRestore  OBJECT-TYPE
          SYNTAX      INTEGER
          MAX-ACCESS  read-write
          STATUS      current
          DESCRIPTION
           ""
        ::= { msagTrapRestoreId 151 }
    msagMpDiskRestore  OBJECT-TYPE
          SYNTAX      INTEGER
          MAX-ACCESS  read-write
          STATUS      current
          DESCRIPTION
           ""
        ::= { msagTrapRestoreId 152 }
    msagMpDataLoadRestore  OBJECT-TYPE
          SYNTAX      INTEGER
          MAX-ACCESS  read-write
          STATUS      current
          DESCRIPTION
           ""
        ::= { msagTrapRestoreId 153 }
    msagMpDataSynRestore  OBJECT-TYPE
          SYNTAX      INTEGER
          MAX-ACCESS  read-write
          STATUS      current
          DESCRIPTION
           ""
        ::= { msagTrapRestoreId 154 }
    msagCommMateRestore  OBJECT-TYPE
          SYNTAX      INTEGER
          MAX-ACCESS  read-write
          STATUS      current
          DESCRIPTION
           ""
        ::= { msagTrapRestoreId 155 }
    msagH248MemArrangeRestore  OBJECT-TYPE
          SYNTAX      INTEGER
          MAX-ACCESS  read-write
          STATUS      current
          DESCRIPTION
           ""
        ::= { msagTrapRestoreId 156 }
    msagH248LinkRestore  OBJECT-TYPE
          SYNTAX      INTEGER
          MAX-ACCESS  read-write
          STATUS      current
          DESCRIPTION
           ""
        ::= { msagTrapRestoreId 157 }
    msagH248LinkAbnormalRestore  OBJECT-TYPE
          SYNTAX      INTEGER
          MAX-ACCESS  read-write
          STATUS      current
          DESCRIPTION
           ""
        ::= { msagTrapRestoreId 158 }
    msagPcmRestore  OBJECT-TYPE
          SYNTAX      INTEGER
          MAX-ACCESS  read-write
          STATUS      current
          DESCRIPTION
           ""
        ::= { msagTrapRestoreId 159 }
    msagCallMemArrangeRestore  OBJECT-TYPE
          SYNTAX      INTEGER
          MAX-ACCESS  read-write
          STATUS      current
          DESCRIPTION
           ""
        ::= { msagTrapRestoreId 160 }
    msagUnitOusRestore  OBJECT-TYPE
          SYNTAX      INTEGER
          MAX-ACCESS  read-write
          STATUS      current
          DESCRIPTION
           ""
        ::= { msagTrapRestoreId 161 }
    msagPortOusRestore  OBJECT-TYPE
          SYNTAX      INTEGER
          MAX-ACCESS  read-write
          STATUS      current
          DESCRIPTION
           ""
        ::= { msagTrapRestoreId 162 }
    msagSunitOusRestore  OBJECT-TYPE
          SYNTAX      INTEGER
          MAX-ACCESS  read-write
          STATUS      current
          DESCRIPTION
           ""
        ::= { msagTrapRestoreId 163 }
    msagPortTypeRestore  OBJECT-TYPE
          SYNTAX      INTEGER
          MAX-ACCESS  read-write
          STATUS      current
          DESCRIPTION
           ""
        ::= { msagTrapRestoreId 164 }
    msagSunitTypeRestore  OBJECT-TYPE
          SYNTAX      INTEGER
          MAX-ACCESS  read-write
          STATUS      current
          DESCRIPTION
           ""
        ::= { msagTrapId 165 }
    msagPortSetStateRestore  OBJECT-TYPE
          SYNTAX      INTEGER
          MAX-ACCESS  read-write
          STATUS      current
          DESCRIPTION
           ""
        ::= { msagTrapRestoreId 166 }
    msagNoTnetRestore  OBJECT-TYPE
          SYNTAX      INTEGER
          MAX-ACCESS  read-write
          STATUS      current
          DESCRIPTION
           ""
        ::= { msagTrapRestoreId 167 }
    msagPpwrPowerRestore  OBJECT-TYPE
          SYNTAX      INTEGER
          MAX-ACCESS  read-write
          STATUS      current
          DESCRIPTION
           ""
        ::= { msagTrapRestoreId 168 }
    msagCpuOverloadRestore  OBJECT-TYPE
          SYNTAX      INTEGER
          MAX-ACCESS  read-write
          STATUS      current
          DESCRIPTION
           ""
        ::= { msagTrapRestoreId 169 }
    msagPpwrFanRestore  OBJECT-TYPE
          SYNTAX      INTEGER
          MAX-ACCESS  read-write
          STATUS      current
          DESCRIPTION
           ""
        ::= { msagTrapRestoreId 170 }
    msagPcmSlipInformRestore  OBJECT-TYPE
          SYNTAX      INTEGER
          MAX-ACCESS  read-write
          STATUS      current
          DESCRIPTION
           ""
        ::= { msagTrapRestoreId 171 }
    msagLapdLinkInformRestore  OBJECT-TYPE
          SYNTAX      INTEGER
          MAX-ACCESS  read-write
          STATUS      current
          DESCRIPTION
           ""
        ::= { msagTrapRestoreId 172 }
    msagFileErrInformRestore  OBJECT-TYPE
          SYNTAX      INTEGER
          MAX-ACCESS  read-write
          STATUS      current
          DESCRIPTION
           ""
        ::= { msagTrapRestoreId 173 }
    msagPpAutoLoadFailRestore  OBJECT-TYPE
          SYNTAX      INTEGER
          MAX-ACCESS  read-write
          STATUS      current
          DESCRIPTION
           ""
        ::= { msagTrapRestoreId 174 }
    msagPortChgoverInformRestore  OBJECT-TYPE
          SYNTAX      INTEGER
          MAX-ACCESS  read-write
          STATUS      current
          DESCRIPTION
           ""
        ::= { msagTrapRestoreId 175 }
    msagPortMainInformRestore  OBJECT-TYPE
          SYNTAX      INTEGER
          MAX-ACCESS  read-write
          STATUS      current
          DESCRIPTION
           ""
        ::= { msagTrapRestoreId 176 }
    msagPortStbInformRestore  OBJECT-TYPE
          SYNTAX      INTEGER
          MAX-ACCESS  read-write
          STATUS      current
          DESCRIPTION
           ""
        ::= { msagTrapRestoreId 177 }
    msagToneLoadSuccInformRestore  OBJECT-TYPE
          SYNTAX      INTEGER
          MAX-ACCESS  read-write
          STATUS      current
          DESCRIPTION
           ""
        ::= { msagTrapRestoreId 178 }
    msagToneLoadFailInformRestore  OBJECT-TYPE
          SYNTAX      INTEGER
          MAX-ACCESS  read-write
          STATUS      current
          DESCRIPTION
           ""
        ::= { msagTrapRestoreId 179 }
    msagAdslLinkdownInformRestore  OBJECT-TYPE
          SYNTAX      INTEGER
          MAX-ACCESS  read-write
          STATUS      current
          DESCRIPTION
           ""
        ::= { msagTrapRestoreId 180 }
    msagAdslLinkupInformRestore  OBJECT-TYPE
          SYNTAX      INTEGER
          MAX-ACCESS  read-write
          STATUS      current
          DESCRIPTION
           ""
        ::= { msagTrapRestoreId 181 }
    msagAdslAtucRateInformRestore  OBJECT-TYPE
          SYNTAX      INTEGER
          MAX-ACCESS  read-write
          STATUS      current
          DESCRIPTION
           ""
        ::= { msagTrapRestoreId 182 }
    msagAdslAturRateInformRestore  OBJECT-TYPE
          SYNTAX      INTEGER
          MAX-ACCESS  read-write
          STATUS      current
          DESCRIPTION
           ""
        ::= { msagTrapRestoreId 183 }
    msagAdslAtucLofsInformRestore  OBJECT-TYPE
          SYNTAX      INTEGER
          MAX-ACCESS  read-write
          STATUS      current
          DESCRIPTION
           ""
        ::= { msagTrapRestoreId 184 }
    msagAdslAtucLossInformRestore  OBJECT-TYPE
          SYNTAX      INTEGER
          MAX-ACCESS  read-write
          STATUS      current
          DESCRIPTION
           ""
        ::= { msagTrapRestoreId 185 }
    msagAdslAtucLprsInformRestore  OBJECT-TYPE
          SYNTAX      INTEGER
          MAX-ACCESS  read-write
          STATUS      current
          DESCRIPTION
           ""
        ::= { msagTrapRestoreId 186 }
    msagAdslAtucEssInformRestore  OBJECT-TYPE
          SYNTAX      INTEGER
          MAX-ACCESS  read-write
          STATUS      current
          DESCRIPTION
           ""
        ::= { msagTrapRestoreId 187 }
    msagAdslAturLofsInformRestore  OBJECT-TYPE
          SYNTAX      INTEGER
          MAX-ACCESS  read-write
          STATUS      current
          DESCRIPTION
           ""
        ::= { msagTrapRestoreId 188 }
    msagAdslAturLossInformRestore  OBJECT-TYPE
          SYNTAX      INTEGER
          MAX-ACCESS  read-write
          STATUS      current
          DESCRIPTION
           ""
        ::= { msagTrapRestoreId 189 }
    msagAdslAturLprsInformRestore  OBJECT-TYPE
          SYNTAX      INTEGER
          MAX-ACCESS  read-write
          STATUS      current
          DESCRIPTION
           ""
        ::= { msagTrapRestoreId 190 }
    msagAdslAturEssInformRestore  OBJECT-TYPE
          SYNTAX      INTEGER
          MAX-ACCESS  read-write
          STATUS      current
          DESCRIPTION
           ""
        ::= { msagTrapRestoreId 191 }
    msagIpsResourceRestore  OBJECT-TYPE
          SYNTAX      INTEGER
          MAX-ACCESS  read-write
          STATUS      current
          DESCRIPTION
           ""
        ::= { msagTrapRestoreId 192 }
    msagServiceQosPoorRestore  OBJECT-TYPE
          SYNTAX      INTEGER
          MAX-ACCESS  read-write
          STATUS      current
          DESCRIPTION
           ""
        ::= { msagTrapRestoreId 193 }
    msagEnableBoardInformRestore  OBJECT-TYPE
          SYNTAX      INTEGER
          MAX-ACCESS  read-write
          STATUS      current
          DESCRIPTION
           ""
        ::= { msagTrapRestoreId 194 }
    msagSubcpuHdlccommRestore  OBJECT-TYPE
          SYNTAX      INTEGER
          MAX-ACCESS  read-write
          STATUS      current
          DESCRIPTION
           ""
        ::= { msagTrapRestoreId 195 }
    msagUnittypeeRestore  OBJECT-TYPE
          SYNTAX      INTEGER
          MAX-ACCESS  read-write
          STATUS      current
          DESCRIPTION
           ""
        ::= { msagTrapRestoreId 196 }
    msagMainCpuTooBusyRestore  OBJECT-TYPE
          SYNTAX      INTEGER
          MAX-ACCESS  read-write
          STATUS      current
          DESCRIPTION
           ""
        ::= { msagTrapRestoreId 197 }
    msagSlaveCpuTooBusyRestore  OBJECT-TYPE
          SYNTAX      INTEGER
          MAX-ACCESS  read-write
          STATUS      current
          DESCRIPTION
           ""
        ::= { msagTrapRestoreId 198 }
    msagSlaveCpuWorkerrRestore  OBJECT-TYPE
          SYNTAX      INTEGER
          MAX-ACCESS  read-write
          STATUS      current
          DESCRIPTION
           ""
        ::= { msagTrapRestoreId 199 }
    msagCnicWorkerrRestore  OBJECT-TYPE
          SYNTAX      INTEGER
          MAX-ACCESS  read-write
          STATUS      current
          DESCRIPTION
           ""
        ::= { msagTrapRestoreId 200 }
    msagMpChgoverInformRestore  OBJECT-TYPE
          SYNTAX      INTEGER
          MAX-ACCESS  read-write
          STATUS      current
          DESCRIPTION
           ""
        ::= { msagTrapRestoreId 201 }
    msagSfChgoverInformRestore  OBJECT-TYPE
          SYNTAX      INTEGER
          MAX-ACCESS  read-write
          STATUS      current
          DESCRIPTION
           ""
        ::= { msagTrapRestoreId 202 }
    msagBoardStateChgInformRestore  OBJECT-TYPE
          SYNTAX      INTEGER
          MAX-ACCESS  read-write
          STATUS      current
          DESCRIPTION
           ""
        ::= { msagTrapRestoreId 203 }
    msagIsdnSctpInformRestore  OBJECT-TYPE
          SYNTAX      INTEGER
          MAX-ACCESS  read-write
          STATUS      current
          DESCRIPTION
           ""
        ::= { msagTrapRestoreId 204 }
    msagIsdnSctpRestore  OBJECT-TYPE
          SYNTAX      INTEGER
          MAX-ACCESS  read-write
          STATUS      current
          DESCRIPTION
           ""
        ::= { msagTrapRestoreId 205 }
    msagIsdnIuaInformRestore  OBJECT-TYPE
          SYNTAX      INTEGER
          MAX-ACCESS  read-write
          STATUS      current
          DESCRIPTION
           ""
        ::= { msagTrapRestoreId 206 }
    msagIsdnIuaRestore  OBJECT-TYPE
          SYNTAX      INTEGER
          MAX-ACCESS  read-write
          STATUS      current
          DESCRIPTION
           ""
        ::= { msagTrapRestoreId 207 }  
    msagV5ProtoRestore  OBJECT-TYPE
          SYNTAX      INTEGER
          MAX-ACCESS  read-write
          STATUS      current
          DESCRIPTION
           ""
        ::= { msagTrapRestoreId 208 }
    msagV5LinkRestore  OBJECT-TYPE
          SYNTAX      INTEGER
          MAX-ACCESS  read-write
          STATUS      current
          DESCRIPTION
           ""
        ::= { msagTrapRestoreId 209 }
           
    msagIPSChannelFaultRestore  OBJECT-TYPE
          SYNTAX      INTEGER
          MAX-ACCESS  read-write
          STATUS      current
          DESCRIPTION
           ""
        ::= { msagTrapRestoreId 215 }
   
    msagSLCCommoffRestore  OBJECT-TYPE
          SYNTAX      INTEGER
          MAX-ACCESS  read-write
          STATUS      current
          DESCRIPTION
           ""
        ::= { msagTrapRestoreId 219 }

    msagSlcFreqOffOnHookAlarmRestore  NOTIFICATION-TYPE
          OBJECTS     
              { 
                  msagTrapRack,
                  msagTrapShelf,
                  msagTrapSlot,
                  msagTrapUnitNo,
                  msagTrapSunitNo,
                  msagTrapPortNum
              }
          STATUS      current
          DESCRIPTION
              "That means on-hook or off-hook is normal." 
        ::= { msagTrapRestoreId 220 }

    msagSlcGroundedRestore  NOTIFICATION-TYPE
          OBJECTS     
              { 
                  msagTrapRack,
                  msagTrapShelf,
                  msagTrapSlot,
                  msagTrapUnitNo,
                  msagTrapSunitNo,
                  msagTrapPortNum
              }
          STATUS      current
          DESCRIPTION
              "The trap means subscriber line normal" 
        ::= { msagTrapRestoreId 221 }
        
   msagFELinkDownRestore  OBJECT-TYPE
          SYNTAX      INTEGER
          MAX-ACCESS  read-write
          STATUS      current
          DESCRIPTION
           "FE link down restore"
        ::= { msagTrapRestoreId 1019 }        
       
   msagMgcpLinkRestore NOTIFICATION-TYPE
        OBJECTS { msagTrapReason,msagTrapLinkState,msagTrapMgcNo }
        STATUS  current
        DESCRIPTION
            "Mgcp link Restore."
       ::= { msagTrapRestoreId 1200 } 
   
   msagSlcAcRestore NOTIFICATION-TYPE
        OBJECTS 
            { 
              msagTrapRack,
              msagTrapShelf,
              msagTrapSlot,
              msagTrapUnitNo,
              msagTrapSunitNo,
              msagTrapPortNum
            }
        STATUS  current
        DESCRIPTION
            "Circuit AC Voltage Alarm Restore."
       ::= { msagTrapRestoreId 1201 } 
       
   msagSlcDcRestore NOTIFICATION-TYPE
        OBJECTS 
            { 
              msagTrapRack,
              msagTrapShelf,
              msagTrapSlot,
              msagTrapUnitNo,
              msagTrapSunitNo,
              msagTrapPortNum
            }
        STATUS  current
        DESCRIPTION
            "Circuit DC Voltage Alarm Restore."
       ::= { msagTrapRestoreId 1202 } 
                        
   msagTrapObjectMib OBJECT IDENTIFIER ::= { msagTrap 2 }
        
   msagTrapRack    OBJECT-TYPE
          SYNTAX         INTEGER(0..255)
          MAX-ACCESS  read-write
          STATUS      current
          DESCRIPTION
           " "
        ::= { msagTrapObjectMib    1 }
    msagTrapShelf    OBJECT-TYPE
          SYNTAX         INTEGER(0..255)
          MAX-ACCESS  read-write
          STATUS      current
          DESCRIPTION
           " "
        ::= { msagTrapObjectMib    2 }
    msagTrapSlot    OBJECT-TYPE
          SYNTAX         INTEGER(0..255)
          MAX-ACCESS  read-write
          STATUS      current
          DESCRIPTION
           " "
        ::= { msagTrapObjectMib    3 }
    msagTrapMainBackState    OBJECT-TYPE
          SYNTAX         INTEGER(0..255)
          MAX-ACCESS  read-write
          STATUS      current
          DESCRIPTION
           " "
        ::= { msagTrapObjectMib    4 }
    msagTrapReason    OBJECT-TYPE
          SYNTAX         INTEGER(0..65535)
          MAX-ACCESS  read-write
          STATUS      current
          DESCRIPTION
           " "
        ::= { msagTrapObjectMib    5 }
    msagTrapMpPos    OBJECT-TYPE
          SYNTAX         INTEGER(0..255)
          MAX-ACCESS  read-write
          STATUS      current
          DESCRIPTION
           " "
        ::= { msagTrapObjectMib    6 }
    msagTrapDiscAllSpace    OBJECT-TYPE
          SYNTAX         INTEGER(0..255)
          MAX-ACCESS  read-write
          STATUS      current
          DESCRIPTION
           " "
        ::= { msagTrapObjectMib    7 }
    msagTrapDiscLeftSpace    OBJECT-TYPE
          SYNTAX         INTEGER(0..255)
          MAX-ACCESS  read-write
          STATUS      current
          DESCRIPTION
           " "
        ::= { msagTrapObjectMib    8 }
    msagTrapLinkState    OBJECT-TYPE
          SYNTAX         INTEGER(0..255)
          MAX-ACCESS  read-write
          STATUS      current
          DESCRIPTION
           " "
        ::= { msagTrapObjectMib    9 }
    msagTrapMgcNo    OBJECT-TYPE
          SYNTAX         INTEGER(0..255)
          MAX-ACCESS  read-write
          STATUS      current
          DESCRIPTION
           " "
        ::= { msagTrapObjectMib    10 }
    msagTrapUpDownId    OBJECT-TYPE
          SYNTAX         Unsigned32
          MAX-ACCESS  read-write
          STATUS      current
          DESCRIPTION
           " "
        ::= { msagTrapObjectMib    11 }
    msagTrapUnitNo    OBJECT-TYPE
          SYNTAX         INTEGER(0..255)
          MAX-ACCESS  read-write
          STATUS      current
          DESCRIPTION
           " "
        ::= { msagTrapObjectMib    12 }
    msagTrapUnitType    OBJECT-TYPE
          SYNTAX         INTEGER(0..255)
          MAX-ACCESS  read-write
          STATUS      current
          DESCRIPTION
           " "
        ::= { msagTrapObjectMib    13 }
    msagTrapPortNum    OBJECT-TYPE
          SYNTAX         INTEGER(0..65535)
          MAX-ACCESS  read-write
          STATUS      current
          DESCRIPTION
           " "
        ::= { msagTrapObjectMib    14 }
    msagTrapPortType    OBJECT-TYPE
          SYNTAX         INTEGER(0..255)
          MAX-ACCESS  read-write
          STATUS      current
          DESCRIPTION
           " "
        ::= { msagTrapObjectMib    15 }
    msagTrapSunitNo    OBJECT-TYPE
          SYNTAX         INTEGER(0..255)
          MAX-ACCESS  read-write
          STATUS      current
          DESCRIPTION
           " "
        ::= { msagTrapObjectMib    16 }
    msagTrapSunitType    OBJECT-TYPE
          SYNTAX         INTEGER(0..255)
          MAX-ACCESS  read-write
          STATUS      current
          DESCRIPTION
           " "
        ::= { msagTrapObjectMib    17 }
    msagTrapBoardType    OBJECT-TYPE
          SYNTAX         INTEGER(0..255)
          MAX-ACCESS  read-write
          STATUS      current
          DESCRIPTION
           " "
        ::= { msagTrapObjectMib    18 }
    msagTrapCardType    OBJECT-TYPE
          SYNTAX         INTEGER(0..255)
          MAX-ACCESS  read-write
          STATUS      current
          DESCRIPTION
           " "
        ::= { msagTrapObjectMib    19 }
    msagTrapPortState    OBJECT-TYPE
          SYNTAX         INTEGER(0..255)
          MAX-ACCESS  read-write
          STATUS      current
          DESCRIPTION
           " "
        ::= { msagTrapObjectMib    20 }
    msagTrapFanIndex    OBJECT-TYPE
          SYNTAX         INTEGER(0..255)
          MAX-ACCESS  read-write
          STATUS      current
          DESCRIPTION
           " "
        ::= { msagTrapObjectMib    21 }
    msagTrapReasionValue    OBJECT-TYPE
          SYNTAX         INTEGER(0..255)
          MAX-ACCESS  read-write
          STATUS      current
          DESCRIPTION
           " "
        ::= { msagTrapObjectMib    22 }
    msagTrapProcessId    OBJECT-TYPE
          SYNTAX         INTEGER(0..65535)
          MAX-ACCESS  read-write
          STATUS      current
          DESCRIPTION
           " "
        ::= { msagTrapObjectMib    23 }
    msagTrapLinkId    OBJECT-TYPE
          SYNTAX         Unsigned32
          MAX-ACCESS  read-write
          STATUS      current
          DESCRIPTION
           " "
        ::= { msagTrapObjectMib    24 }
    msagTrapLinkManageState    OBJECT-TYPE
          SYNTAX         Unsigned32
          MAX-ACCESS  read-write
          STATUS      current
          DESCRIPTION
           " "
        ::= { msagTrapObjectMib    25 }
    msagTrapLinkOperState    OBJECT-TYPE
          SYNTAX         Unsigned32
          MAX-ACCESS  read-write
          STATUS      current
          DESCRIPTION
           " "
        ::= { msagTrapObjectMib    26 }
    msagTrapCurrTransSpeed    OBJECT-TYPE
          SYNTAX         Unsigned32
          MAX-ACCESS  read-write
          STATUS      current
          DESCRIPTION
           " "
        ::= { msagTrapObjectMib    27 }
    msagTrapLastTransSpeed    OBJECT-TYPE
          SYNTAX         Unsigned32
          MAX-ACCESS  read-write
          STATUS      current
          DESCRIPTION
           " "
        ::= { msagTrapObjectMib    28 }
    msagTrapFrameLostNum    OBJECT-TYPE
          SYNTAX         Unsigned32
          MAX-ACCESS  read-write
          STATUS      current
          DESCRIPTION
           " "
        ::= { msagTrapObjectMib    29 }
    msagTrapFrameLostThreshold    OBJECT-TYPE
          SYNTAX         Unsigned32
          MAX-ACCESS  read-write
          STATUS      current
          DESCRIPTION
           " "
        ::= { msagTrapObjectMib    30 }
    msagTrapSignalLostNum    OBJECT-TYPE
          SYNTAX         Unsigned32
          MAX-ACCESS  read-write
          STATUS      current
          DESCRIPTION
           " "
        ::= { msagTrapObjectMib    31 }
    msagTrapSignalLostThreshold    OBJECT-TYPE
          SYNTAX         Unsigned32
          MAX-ACCESS  read-write
          STATUS      current
          DESCRIPTION
           " "
        ::= { msagTrapObjectMib    32 }
    msagTrapPowerLostNum    OBJECT-TYPE
          SYNTAX         Unsigned32
          MAX-ACCESS  read-write
          STATUS      current
          DESCRIPTION
           " "
        ::= { msagTrapObjectMib    33 }
    msagTrapPowerLostThreshold    OBJECT-TYPE
          SYNTAX         Unsigned32
          MAX-ACCESS  read-write
          STATUS      current
          DESCRIPTION
           " "
        ::= { msagTrapObjectMib    34 }
    msagTrapBETime    OBJECT-TYPE
          SYNTAX         Unsigned32
          MAX-ACCESS  read-write
          STATUS      current
          DESCRIPTION
           " "
        ::= { msagTrapObjectMib    35 }
    msagTrapBeTimeThreshold    OBJECT-TYPE
          SYNTAX         Unsigned32
          MAX-ACCESS  read-write
          STATUS      current
          DESCRIPTION
           " "
        ::= { msagTrapObjectMib    36 }
    msagTrapAlarmType    OBJECT-TYPE
          SYNTAX         INTEGER(0..255)
          MAX-ACCESS  read-write
          STATUS      current
          DESCRIPTION
           " "
        ::= { msagTrapObjectMib    37 }
    msagTrapQosThreshold    OBJECT-TYPE
          SYNTAX         Unsigned32
          MAX-ACCESS  read-write
          STATUS      current
          DESCRIPTION
           " "
        ::= { msagTrapObjectMib    38 }
    msagTrapNewSnmpState    OBJECT-TYPE
          SYNTAX         INTEGER(0..255)
          MAX-ACCESS  read-write
          STATUS      current
          DESCRIPTION
           " "
        ::= { msagTrapObjectMib    39 }
    msagTrapOldSnmpState    OBJECT-TYPE
          SYNTAX         INTEGER(0..255)
          MAX-ACCESS  read-write
          STATUS      current
          DESCRIPTION
           " "
        ::= { msagTrapObjectMib    40 }
    msagTrapNewState    OBJECT-TYPE
          SYNTAX         Unsigned32
          MAX-ACCESS  read-write
          STATUS      current
          DESCRIPTION
           " "
        ::= { msagTrapObjectMib    41 }
    msagTrapOldState    OBJECT-TYPE
          SYNTAX         Unsigned32
          MAX-ACCESS  read-write
          STATUS      current
          DESCRIPTION
           " "
        ::= { msagTrapObjectMib    42 }
    msagTrapParaLinkId    OBJECT-TYPE
          SYNTAX         INTEGER(0..65535)
          MAX-ACCESS  read-write
          STATUS      current
          DESCRIPTION
           " "
        ::= { msagTrapObjectMib    43 }
    msagTrapIpAddress    OBJECT-TYPE
          SYNTAX         Unsigned32
          MAX-ACCESS  read-write
          STATUS      current
          DESCRIPTION
           " "
        ::= { msagTrapObjectMib    44 }
    msagTrapSLN    OBJECT-TYPE
          SYNTAX         Unsigned32
          MAX-ACCESS  read-write
          STATUS      current
          DESCRIPTION
           " "
        ::= { msagTrapObjectMib    45 }  
   msagTrapV5InterId    OBJECT-TYPE
          SYNTAX      Unsigned32
          MAX-ACCESS  read-write
          STATUS      current
          DESCRIPTION
            ""
        ::= { msagTrapObjectMib    46 }
    msagTrapDLProType    OBJECT-TYPE
          SYNTAX      INTEGER(0..65535)
          MAX-ACCESS  read-write
          STATUS      current
          DESCRIPTION
            ""
        ::= { msagTrapObjectMib    47 }
    msagTrapCurEvent    OBJECT-TYPE
          SYNTAX      INTEGER(0..65535)
          MAX-ACCESS  read-write
          STATUS      current
          DESCRIPTION
            ""
        ::= { msagTrapObjectMib    48 }
    msagTrapCurState    OBJECT-TYPE
          SYNTAX      INTEGER(0..65535)
          MAX-ACCESS  read-write
          STATUS      current
          DESCRIPTION
            ""
        ::= { msagTrapObjectMib    49 }
    msagTrapLinkNo    OBJECT-TYPE
          SYNTAX      INTEGER(0..255)
          MAX-ACCESS  read-write
          STATUS      current
          DESCRIPTION
            ""
        ::= { msagTrapObjectMib    50 }
        
    msagTrapErrcode    OBJECT-TYPE
          SYNTAX      INTEGER
          MAX-ACCESS  read-write
          STATUS      current
          DESCRIPTION
            ""
        ::= { msagTrapObjectMib    55 }
        
    msagTrapFlag    OBJECT-TYPE
          SYNTAX      INTEGER
          MAX-ACCESS  read-write
          STATUS      current
          DESCRIPTION
            ""
        ::= { msagTrapObjectMib    56 }
              
    msagTrapDesc    OBJECT-TYPE
          SYNTAX      DisplayString(SIZE (0..255))
          MAX-ACCESS  read-write
          STATUS      current
          DESCRIPTION
            ""
        ::= { msagTrapObjectMib    500 }
        
        
   msagTrapLevel    OBJECT-TYPE
          SYNTAX      DisplayString(SIZE (0..255))
          MAX-ACCESS  read-write
          STATUS      current
          DESCRIPTION
            ""
        ::= { msagTrapObjectMib    501 }
        
        
   msagTrapCause    OBJECT-TYPE
          SYNTAX      DisplayString(SIZE (0..255))
          MAX-ACCESS  read-write
          STATUS      current
          DESCRIPTION
            ""
        ::= { msagTrapObjectMib    502 }
        
        
   msagTrapParaDesc    OBJECT-TYPE
          SYNTAX      DisplayString(SIZE (0..500))
          MAX-ACCESS  read-write
          STATUS      current
          DESCRIPTION
            ""
        ::= { msagTrapObjectMib    503 }
        
        
END
