IANAifType-MIB DEFINITIONS ::= BEGIN

   IMPORTS
       MODULE-IDENTITY, mib-2              FROM SNMPv2-SMI
       TEXTUAL-CONVENTION                  FROM SNMPv2-TC;
--       mib-2                               FROM RFC1213-MIB;

   ianaifType MODULE-IDENTITY
       LAST-UPDATED "9311082155Z"
       ORGANIZATION "IANA"
       CONTACT-INFO

                  "        Internet Assigned Numbers Authority

                   Postal: USC/Information Sciences Institute
                           4676 Admiralty Way, Marina del Rey, CA 90292

                   Tel:    +1  310 822 1511
                   E-Mail: iana@isi.edu"
       DESCRIPTION
               "The MIB module which defines the IANAifType textual
               convention, and thus the enumerated values of the
               ifType object defined in MIB-II's ifTable."
       ::= { mib-2 30 }


   IANAifType ::= TEXTUAL-CONVENTION
       STATUS       current
       DESCRIPTION
               "This data type is used as the syntax of the ifType
               object in the (updated) definition of MIB-II's
               ifTable.
               The definition of this textual convention with the
               addition of newly assigned values is published
               periodically by the IANA, in either the Assigned
               Numbers RFC, or some derivative of it specific to
               Internet Network Management number assignments.  (The
               latest arrangements can be obtained by contacting the
               IANA.)

               Requests for new values should be made to IANA via
               email (iana@isi.edu).

               The relationship between the assignment of ifType
               values and of OIDs to particular media-specific MIBs
               is solely the purview of IANA and is subject to change
               without notice.  Quite often, a media-specific MIB's
               OID-subtree assignment within MIB-II's 'transmission'
               subtree will be the same as its ifType value.
               However, in some circumstances this will not be the
               case, and implementors must not pre-assume any
               specific relationship between ifType values and
               transmission subtree OIDs."
       SYNTAX  INTEGER {
                   other(1),          -- none of the following
                   regular1822(2),
                   hdh1822(3),
                   ddnX25(4),
                   rfc877x25(5),
                   ethernetCsmacd(6),
                   iso88023Csmacd(7),
                   iso88024TokenBus(8),
                   iso88025TokenRing(9),
                   iso88026Man(10),
                   starLan(11),
                   proteon10Mbit(12),
                   proteon80Mbit(13),
                   hyperchannel(14),
                   fddi(15),
                   lapb(16),
                   sdlc(17),
                   ds1(18),           -- DS1/E1 (RFC 1406)
                   e1(19),            -- obsolete
                   basicISDN(20),
                   primaryISDN(21),
                   propPointToPointSerial(22), -- proprietary serial
                   ppp(23),
                   softwareLoopback(24),
                   eon(25),            -- CLNP over IP (RFC 1070)
                   ethernet3Mbit(26),
                   nsip(27),           -- XNS over IP
                   slip(28),           -- generic SLIP
                   ultra(29),          -- ULTRA technologies
                   ds3(30),            -- T-3
                   sip(31),            -- SMDS
                   frameRelay(32),    -- DTE only
                   rs232(33),
                   para(34),           -- parallel-port
                   arcnet(35),         -- arcnet
                   arcnetPlus(36),     -- arcnet plus
                   atm(37),            -- ATM cells
                   miox25(38),
                   sonet(39),          -- SONET or SDH
                   x25ple(40),
                   iso88022llc(41),
                   localTalk(42),
                   smdsDxi(43),
                   frameRelayService(44),  -- Frame relay DCE
                   v35(45),
                   hssi(46),
                   hippi(47),
                   modem(48),          -- Generic modem
                   aal5(49),           -- AAL5 over ATM
                   sonetPath(50),
                   sonetVT(51),
                   smdsIcip(52),       -- SMDS InterCarrier Interface
                   propVirtual(53),    -- proprietary virtual/internal
                   propMultiplexor(54), -- proprietary multiplexing
				   --
				   -- According to RFC2662 4.1
				   -- 
				   adsl(94),			-- Asymmetric Digital Subscriber Loop
		           adslInterleave(124), -- ADSL Interleaved Channel
				   adslFast(125),        -- ADSL Fast Channel
				   --
				   -- IMA
				   --
				   atmIma(107)
				   --
               }

   END

SNMPv2-MIB DEFINITIONS ::= BEGIN

IMPORTS
    MODULE-IDENTITY, OBJECT-TYPE, NOTIFICATION-TYPE,
    TimeTicks, Counter32, snmpModules, mib-2
        FROM SNMPv2-SMI
    DisplayString, TestAndIncr, TimeStamp
        FROM SNMPv2-TC
    MODULE-COMPLIANCE, OBJECT-GROUP, NOTIFICATION-GROUP
        FROM SNMPv2-CONF;

snmpMIB MODULE-IDENTITY
    LAST-UPDATED "9511090000Z"
    ORGANIZATION "IETF SNMPv2 Working Group"
    CONTACT-INFO
            "        Marshall T. Rose

             Postal: Dover Beach Consulting, Inc.
                     420 Whisman Court
                     Mountain View, CA  94043-2186
                     US

                Tel: +1 415 968 1052

             E-mail: mrose@dbc.mtview.ca.us"
    DESCRIPTION
            "The MIB module for SNMPv2 entities."
    REVISION      "9304010000Z"
    DESCRIPTION
            "The initial revision of this MIB module was published as
            RFC 1450."
    ::= { snmpModules 1 }


snmpMIBObjects OBJECT IDENTIFIER ::= { snmpMIB 1 }

--  ::= { snmpMIBObjects 1 }        this OID is obsolete
--  ::= { snmpMIBObjects 2 }        this OID is obsolete
--  ::= { snmpMIBObjects 3 }        this OID is obsolete


-- the System group
--
-- a collection of objects common to all managed systems.

system   OBJECT IDENTIFIER ::= { mib-2 1 }

sysDescr OBJECT-TYPE
    SYNTAX      DisplayString (SIZE (0..255))
    MAX-ACCESS  read-only
    STATUS      current
    DESCRIPTION
            "A textual description of the entity.  This value should
            include the full name and version identification of the
            system's hardware type, software operating-system, and
            networking software."
    ::= { system 1 }

sysObjectID OBJECT-TYPE
    SYNTAX      OBJECT IDENTIFIER
    MAX-ACCESS  read-only
    STATUS      current
    DESCRIPTION
            "The vendor's authoritative identification of the network
            management subsystem contained in the entity.  This value is
            allocated within the SMI enterprises subtree (1.3.6.1.4.1)
            and provides an easy and unambiguous means for determining
            `what kind of box' is being managed.  For example, if vendor
            `Flintstones, Inc.' was assigned the subtree
            1.3.6.1.4.1.4242, it could assign the identifier
            1.3.6.1.4.1.4242.1.1 to its `Fred Router'."
    ::= { system 2 }

sysUpTime OBJECT-TYPE
    SYNTAX      TimeTicks
    MAX-ACCESS  read-only
    STATUS      current
    DESCRIPTION
            "The time (in hundredths of a second) since the network
            management portion of the system was last re-initialized."
    ::= { system 3 }

sysContact OBJECT-TYPE
    SYNTAX      DisplayString (SIZE (0..255))
    MAX-ACCESS  read-write
    STATUS      current
    DESCRIPTION
            "The textual identification of the contact person for this
            managed node, together with information on how to contact
            this person.  If no contact information is known, the value
            is the zero-length string."
    ::= { system 4 }

sysName OBJECT-TYPE
    SYNTAX      DisplayString (SIZE (0..255))
    MAX-ACCESS  read-write
    STATUS      current
    DESCRIPTION
            "An administratively-assigned name for this managed node.
            By convention, this is the node's fully-qualified domain
            name.  If the name is unknown, the value is the zero-length
            string."
    ::= { system 5 }

sysLocation OBJECT-TYPE
    SYNTAX      DisplayString (SIZE (0..255))
    MAX-ACCESS  read-write
    STATUS      current
    DESCRIPTION
            "The physical location of this node (e.g., `telephone
            closet, 3rd floor').  If the location is unknown, the value
            is the zero-length string."
    ::= { system 6 }

sysServices OBJECT-TYPE
    SYNTAX      INTEGER (0..127)
    MAX-ACCESS  read-only
    STATUS      current
    DESCRIPTION
            "A value which indicates the set of services that this
            entity may potentially offers.  The value is a sum.  This
            sum initially takes the value zero, Then, for each layer, L,
            in the range 1 through 7, that this node performs
            transactions for, 2 raised to (L - 1) is added to the sum.
            For example, a node which performs only routing functions
            would have a value of 4 (2^(3-1)).  In contrast, a node
            which is a host offering application services would have a
            value of 72 (2^(4-1) + 2^(7-1)).  Note that in the context
            of the Internet suite of protocols, values should be
            calculated accordingly:

                 layer      functionality
                   1        physical (e.g., repeaters)
                   2        datalink/subnetwork (e.g., bridges)
                   3        internet (e.g., supports the IP)
                   4        end-to-end  (e.g., supports the TCP)
                   7        applications (e.g., supports the SMTP)

            For systems including OSI protocols, layers 5 and 6 may also
            be counted."
    ::= { system 7 }


-- object resource information
--
-- a collection of objects which describe the SNMPv2 entity's
-- (statically and dynamically configurable) support of
-- various MIB modules.

sysORLastChange OBJECT-TYPE
    SYNTAX     TimeStamp
    MAX-ACCESS read-only
    STATUS     current
    DESCRIPTION
            "The value of sysUpTime at the time of the most recent
            change in state or value of any instance of sysORID."
    ::= { system 8 }

sysORTable OBJECT-TYPE
    SYNTAX     SEQUENCE OF SysOREntry
    MAX-ACCESS not-accessible
    STATUS     current
    DESCRIPTION
            "The (conceptual) table listing the capabilities of the
            local SNMPv2 entity acting in an agent role with respect to
            various MIB modules.  SNMPv2 entities having dynamically-
            configurable support of MIB modules will have a
            dynamically-varying number of conceptual rows."
    ::= { system 9 }

sysOREntry OBJECT-TYPE
    SYNTAX     SysOREntry
    MAX-ACCESS not-accessible
    STATUS     current
    DESCRIPTION
            "An entry (conceptual row) in the sysORTable."
    INDEX      { sysORIndex }
    ::= { sysORTable 1 }

SysOREntry ::= SEQUENCE {
    sysORIndex     INTEGER,
    sysORID        OBJECT IDENTIFIER,
    sysORDescr     DisplayString,
    sysORUpTime    TimeStamp
}

sysORIndex OBJECT-TYPE
    SYNTAX     INTEGER (1..2147483647)
    MAX-ACCESS not-accessible
    STATUS     current
    DESCRIPTION
            "The auxiliary variable used for identifying instances of
            the columnar objects in the sysORTable."
    ::= { sysOREntry 1 }

sysORID OBJECT-TYPE
    SYNTAX     OBJECT IDENTIFIER
    MAX-ACCESS read-only
    STATUS     current
    DESCRIPTION
            "An authoritative identification of a capabilities statement
            with respect to various MIB modules supported by the local
            SNMPv2 entity acting in an agent role."
    ::= { sysOREntry 2 }

sysORDescr OBJECT-TYPE
    SYNTAX     DisplayString
    MAX-ACCESS read-only
    STATUS     current
    DESCRIPTION
            "A textual description of the capabilities identified by the
            corresponding instance of sysORID."
    ::= { sysOREntry 3 }

sysORUpTime OBJECT-TYPE
    SYNTAX     TimeStamp
    MAX-ACCESS read-only
    STATUS     current
    DESCRIPTION
            "The value of sysUpTime at the time this conceptual row was
            last instanciated."
    ::= { sysOREntry 4 }


-- the SNMP group
--
-- a collection of objects providing basic instrumentation and
-- control of an SNMP entity.

snmp     OBJECT IDENTIFIER ::= { mib-2 11 }

snmpInPkts OBJECT-TYPE
    SYNTAX     Counter32
    MAX-ACCESS read-only
    STATUS     current
    DESCRIPTION
            "The total number of messages delivered to the SNMP entity
            from the transport service."
    ::= { snmp 1 }

snmpInBadVersions OBJECT-TYPE
    SYNTAX     Counter32
    MAX-ACCESS read-only
    STATUS     current
    DESCRIPTION
            "The total number of SNMP messages which were delivered to
            the SNMP entity and were for an unsupported SNMP version."
    ::= { snmp 3 }

snmpInBadCommunityNames OBJECT-TYPE
    SYNTAX     Counter32
    MAX-ACCESS read-only
    STATUS     current
    DESCRIPTION
            "The total number of SNMP messages delivered to the SNMP
            entity which used a SNMP community name not known to said
            entity."
    ::= { snmp 4 }

snmpInBadCommunityUses OBJECT-TYPE
    SYNTAX     Counter32
    MAX-ACCESS read-only
    STATUS     current
    DESCRIPTION
            "The total number of SNMP messages delivered to the SNMP
            entity which represented an SNMP operation which was not
            allowed by the SNMP community named in the message."
    ::= { snmp 5 }

snmpInASNParseErrs OBJECT-TYPE
    SYNTAX     Counter32
    MAX-ACCESS read-only
    STATUS     current
    DESCRIPTION
            "The total number of ASN.1 or BER errors encountered by the
            SNMP entity when decoding received SNMP messages."
    ::= { snmp 6 }

snmpEnableAuthenTraps OBJECT-TYPE
    SYNTAX      INTEGER { enabled(1), disabled(2) }
    MAX-ACCESS  read-write
    STATUS      current
    DESCRIPTION
            "Indicates whether the SNMP entity is permitted to generate
            authenticationFailure traps.  The value of this object
            overrides any configuration information; as such, it
            provides a means whereby all authenticationFailure traps may
            be disabled.

            Note that it is strongly recommended that this object be
            stored in non-volatile memory so that it remains constant
            across re-initializations of the network management system."
    ::= { snmp 30 }

snmpSilentDrops OBJECT-TYPE
    SYNTAX     Counter32
    MAX-ACCESS read-only
    STATUS     current
    DESCRIPTION
            "The total number of GetRequest-PDUs, GetNextRequest-PDUs,
            GetBulkRequest-PDUs, SetRequest-PDUs, and InformRequest-PDUs
            delivered to the SNMP entity which were silently dropped
            because the size of a reply containing an alternate
            Response-PDU with an empty variable-bindings field was
            greater than either a local constraint or the maximum
            message size associated with the originator of the request."
    ::= { snmp 31 }

snmpProxyDrops OBJECT-TYPE
    SYNTAX     Counter32
    MAX-ACCESS read-only
    STATUS     current
    DESCRIPTION
            "The total number of GetRequest-PDUs, GetNextRequest-PDUs,
            GetBulkRequest-PDUs, SetRequest-PDUs, and InformRequest-PDUs
            delivered to the SNMP entity which were silently dropped
            because the transmission of the (possibly translated)
            message to a proxy target failed in a manner (other than a
            time-out) such that no Response-PDU could be returned."
    ::= { snmp 32 }


-- information for notifications
--
-- a collection of objects which allow the SNMPv2 entity, when
-- acting in an agent role, to be configured to generate
-- SNMPv2-Trap-PDUs.

snmpTrap       OBJECT IDENTIFIER ::= { snmpMIBObjects 4 }


snmpTrapOID OBJECT-TYPE
    SYNTAX     OBJECT IDENTIFIER
    MAX-ACCESS accessible-for-notify
    STATUS     current
    DESCRIPTION
            "The authoritative identification of the notification
            currently being sent.  This variable occurs as the second
            varbind in every SNMPv2-Trap-PDU and InformRequest-PDU."
    ::= { snmpTrap 1 }

--  ::= { snmpTrap 2 }   this OID is obsolete

snmpTrapEnterprise OBJECT-TYPE
    SYNTAX     OBJECT IDENTIFIER
    MAX-ACCESS accessible-for-notify
    STATUS     current
    DESCRIPTION
            "The authoritative identification of the enterprise
            associated with the trap currently being sent.  When a
            SNMPv2 proxy agent is mapping an RFC1157 Trap-PDU into a
            SNMPv2-Trap-PDU, this variable occurs as the last varbind."
    ::= { snmpTrap 3 }

--  ::= { snmpTrap 4 }   this OID is obsolete


-- well-known traps

snmpTraps      OBJECT IDENTIFIER ::= { snmpMIBObjects 5 }

coldStart NOTIFICATION-TYPE
    STATUS  current
    DESCRIPTION
            "A coldStart trap signifies that the SNMPv2 entity, acting
            in an agent role, is reinitializing itself and that its
            configuration may have been altered."
    ::= { snmpTraps 1 }

warmStart NOTIFICATION-TYPE
    STATUS  current
    DESCRIPTION
            "A warmStart trap signifies that the SNMPv2 entity, acting
            in an agent role, is reinitializing itself such that its
            configuration is unaltered."
    ::= { snmpTraps 2 }

-- Note the linkDown NOTIFICATION-TYPE ::= { snmpTraps 3 }
-- and the linkUp NOTIFICATION-TYPE ::= { snmpTraps 4 }
-- are defined in RFC 1573

authenticationFailure NOTIFICATION-TYPE
    STATUS  current
    DESCRIPTION
            "An authenticationFailure trap signifies that the SNMPv2
            entity, acting in an agent role, has received a protocol
            message that is not properly authenticated.  While all
            implementations of the SNMPv2 must be capable of generating
            this trap, the snmpEnableAuthenTraps object indicates
            whether this trap will be generated."
    ::= { snmpTraps 5 }

-- Note the egpNeighborLoss NOTIFICATION-TYPE ::= { snmpTraps 6 }
-- is defined in RFC 1213
-- the set group
--
-- a collection of objects which allow several cooperating
-- SNMPv2 entities, all acting in a manager role, to
-- coordinate their use of the SNMPv2 set operation.

snmpSet        OBJECT IDENTIFIER ::= { snmpMIBObjects 6 }


snmpSetSerialNo OBJECT-TYPE
    SYNTAX     TestAndIncr
    MAX-ACCESS read-write
    STATUS     current
    DESCRIPTION
            "An advisory lock used to allow several cooperating SNMPv2
            entities, all acting in a manager role, to coordinate their
            use of the SNMPv2 set operation.

            This object is used for coarse-grain coordination.  To
            achieve fine-grain coordination, one or more similar objects
            might be defined within each MIB group, as appropriate."
    ::= { snmpSet 1 }


-- conformance information

snmpMIBConformance
               OBJECT IDENTIFIER ::= { snmpMIB 2 }

snmpMIBCompliances
               OBJECT IDENTIFIER ::= { snmpMIBConformance 1 }
snmpMIBGroups  OBJECT IDENTIFIER ::= { snmpMIBConformance 2 }


-- compliance statements

--    ::= { snmpMIBCompliances 1 }      this OID is obsolete

snmpBasicCompliance MODULE-COMPLIANCE
    STATUS  current
    DESCRIPTION
            "The compliance statement for SNMPv2 entities which
            implement the SNMPv2 MIB."
    MODULE  -- this module
        MANDATORY-GROUPS { snmpGroup, snmpSetGroup, systemGroup,
                           snmpBasicNotificationsGroup }

        GROUP   snmpCommunityGroup
        DESCRIPTION
            "This group is mandatory for SNMPv2 entities which
            support community-based authentication."

    ::= { snmpMIBCompliances 2 }


-- units of conformance

--  ::= { snmpMIBGroups 1 }           this OID is obsolete
--  ::= { snmpMIBGroups 2 }           this OID is obsolete
--  ::= { snmpMIBGroups 3 }           this OID is obsolete
--  ::= { snmpMIBGroups 4 }           this OID is obsolete

snmpGroup OBJECT-GROUP
    OBJECTS { snmpInPkts,
              snmpInBadVersions,
              snmpInASNParseErrs,
              snmpSilentDrops,
              snmpProxyDrops,
              snmpEnableAuthenTraps }
    STATUS  current
    DESCRIPTION
            "A collection of objects providing basic instrumentation and
            control of an SNMPv2 entity."
    ::= { snmpMIBGroups 8 }

snmpCommunityGroup OBJECT-GROUP
    OBJECTS { snmpInBadCommunityNames,
              snmpInBadCommunityUses }
    STATUS  current
    DESCRIPTION
            "A collection of objects providing basic instrumentation of
            a SNMPv2 entity which supports community-based
            authentication."
    ::= { snmpMIBGroups 9 }

snmpSetGroup OBJECT-GROUP
    OBJECTS { snmpSetSerialNo }
    STATUS  current
    DESCRIPTION
            "A collection of objects which allow several cooperating
            SNMPv2 entities, all acting in a manager role, to coordinate
            their use of the SNMPv2 set operation."
    ::= { snmpMIBGroups 5 }

systemGroup OBJECT-GROUP
    OBJECTS { sysDescr, sysObjectID, sysUpTime,
              sysContact, sysName, sysLocation,
              sysServices,
              sysORLastChange, sysORID,
              sysORUpTime, sysORDescr }
    STATUS  current
    DESCRIPTION
            "The system group defines objects which are common to all
            managed systems."
    ::= { snmpMIBGroups 6 }

snmpBasicNotificationsGroup NOTIFICATION-GROUP
    NOTIFICATIONS { coldStart, authenticationFailure }
    STATUS        current
    DESCRIPTION
            "The two notifications which an SNMPv2 entity is required to
            implement."
    ::= { snmpMIBGroups 7 }


-- definitions in RFC 1213 made obsolete by the inclusion of a
-- subset of the snmp group in this MIB

snmpOutPkts OBJECT-TYPE
    SYNTAX      Counter32
    MAX-ACCESS  read-only
    STATUS      obsolete
    DESCRIPTION
            "The total number of SNMP Messages which were
            passed from the SNMP protocol entity to the
            transport service."
    ::= { snmp 2 }

-- { snmp 7 } is not used

snmpInTooBigs OBJECT-TYPE
    SYNTAX      Counter32
    MAX-ACCESS  read-only
    STATUS      obsolete
    DESCRIPTION
            "The total number of SNMP PDUs which were
            delivered to the SNMP protocol entity and for
            which the value of the error-status field is
            `tooBig'."
    ::= { snmp 8 }

snmpInNoSuchNames OBJECT-TYPE
    SYNTAX      Counter32
    MAX-ACCESS  read-only
    STATUS      obsolete
    DESCRIPTION
            "The total number of SNMP PDUs which were
            delivered to the SNMP protocol entity and for
            which the value of the error-status field is
            `noSuchName'."
    ::= { snmp 9 }

snmpInBadValues OBJECT-TYPE
    SYNTAX      Counter32
    MAX-ACCESS  read-only
    STATUS      obsolete
    DESCRIPTION
            "The total number of SNMP PDUs which were
            delivered to the SNMP protocol entity and for
            which the value of the error-status field is
            `badValue'."
    ::= { snmp 10 }

snmpInReadOnlys OBJECT-TYPE
    SYNTAX      Counter32
    MAX-ACCESS  read-only
    STATUS      obsolete
    DESCRIPTION
            "The total number valid SNMP PDUs which were
            delivered to the SNMP protocol entity and for
            which the value of the error-status field is
            `readOnly'.  It should be noted that it is a
            protocol error to generate an SNMP PDU which
            contains the value `readOnly' in the error-status
            field, as such this object is provided as a means
            of detecting incorrect implementations of the
            SNMP."
    ::= { snmp 11 }

snmpInGenErrs OBJECT-TYPE
    SYNTAX      Counter32
    MAX-ACCESS  read-only
    STATUS      obsolete
    DESCRIPTION
            "The total number of SNMP PDUs which were
            delivered to the SNMP protocol entity and for
            which the value of the error-status field is
            `genErr'."
    ::= { snmp 12 }

snmpInTotalReqVars OBJECT-TYPE
    SYNTAX      Counter32
    MAX-ACCESS  read-only
    STATUS      obsolete
    DESCRIPTION
            "The total number of MIB objects which have been
            retrieved successfully by the SNMP protocol entity
            as the result of receiving valid SNMP Get-Request
            and Get-Next PDUs."
    ::= { snmp 13 }

snmpInTotalSetVars OBJECT-TYPE
    SYNTAX      Counter32
    MAX-ACCESS  read-only
    STATUS      obsolete
    DESCRIPTION
            "The total number of MIB objects which have been
            altered successfully by the SNMP protocol entity
            as the result of receiving valid SNMP Set-Request
            PDUs."
    ::= { snmp 14 }

snmpInGetRequests OBJECT-TYPE
    SYNTAX      Counter32
    MAX-ACCESS  read-only
    STATUS      obsolete
    DESCRIPTION
            "The total number of SNMP Get-Request PDUs which
            have been accepted and processed by the SNMP
            protocol entity."
    ::= { snmp 15 }

snmpInGetNexts OBJECT-TYPE
    SYNTAX      Counter32
    MAX-ACCESS  read-only
    STATUS      obsolete
    DESCRIPTION
            "The total number of SNMP Get-Next PDUs which have
            been accepted and processed by the SNMP protocol
            entity."
    ::= { snmp 16 }

snmpInSetRequests OBJECT-TYPE
    SYNTAX      Counter32
    MAX-ACCESS  read-only
    STATUS      obsolete
    DESCRIPTION
            "The total number of SNMP Set-Request PDUs which
            have been accepted and processed by the SNMP
            protocol entity."
    ::= { snmp 17 }

snmpInGetResponses OBJECT-TYPE
    SYNTAX      Counter32
    MAX-ACCESS  read-only
    STATUS      obsolete
    DESCRIPTION
            "The total number of SNMP Get-Response PDUs which
            have been accepted and processed by the SNMP
            protocol entity."
    ::= { snmp 18 }

snmpInTraps OBJECT-TYPE
    SYNTAX      Counter32
    MAX-ACCESS  read-only
    STATUS      obsolete
    DESCRIPTION
            "The total number of SNMP Trap PDUs which have
            been accepted and processed by the SNMP protocol
            entity."
    ::= { snmp 19 }

snmpOutTooBigs OBJECT-TYPE
    SYNTAX      Counter32
    MAX-ACCESS  read-only
    STATUS      obsolete
    DESCRIPTION
            "The total number of SNMP PDUs which were
            generated by the SNMP protocol entity and for
            which the value of the error-status field is
            `tooBig.'"
    ::= { snmp 20 }

snmpOutNoSuchNames OBJECT-TYPE
    SYNTAX      Counter32
    MAX-ACCESS  read-only
    STATUS      obsolete
    DESCRIPTION
            "The total number of SNMP PDUs which were
            generated by the SNMP protocol entity and for
            which the value of the error-status is
            `noSuchName'."
    ::= { snmp 21 }

snmpOutBadValues OBJECT-TYPE
    SYNTAX      Counter32
    MAX-ACCESS  read-only
    STATUS      obsolete
    DESCRIPTION
            "The total number of SNMP PDUs which were
            generated by the SNMP protocol entity and for
            which the value of the error-status field is
            `badValue'."
    ::= { snmp 22 }


-- { snmp 23 } is not used

snmpOutGenErrs OBJECT-TYPE
    SYNTAX      Counter32
    MAX-ACCESS  read-only
    STATUS      obsolete
    DESCRIPTION
            "The total number of SNMP PDUs which were
            generated by the SNMP protocol entity and for
            which the value of the error-status field is
            `genErr'."
    ::= { snmp 24 }

snmpOutGetRequests OBJECT-TYPE
    SYNTAX      Counter32
    MAX-ACCESS  read-only
    STATUS      obsolete
    DESCRIPTION
            "The total number of SNMP Get-Request PDUs which
            have been generated by the SNMP protocol entity."
    ::= { snmp 25 }

snmpOutGetNexts OBJECT-TYPE
    SYNTAX      Counter32
    MAX-ACCESS  read-only
    STATUS      obsolete
    DESCRIPTION
            "The total number of SNMP Get-Next PDUs which have
            been generated by the SNMP protocol entity."
    ::= { snmp 26 }

snmpOutSetRequests OBJECT-TYPE
    SYNTAX      Counter32
    MAX-ACCESS  read-only
    STATUS      obsolete
    DESCRIPTION
            "The total number of SNMP Set-Request PDUs which
            have been generated by the SNMP protocol entity."
    ::= { snmp 27 }

snmpOutGetResponses OBJECT-TYPE
    SYNTAX      Counter32
    MAX-ACCESS  read-only
    STATUS      obsolete
    DESCRIPTION
            "The total number of SNMP Get-Response PDUs which
            have been generated by the SNMP protocol entity."
    ::= { snmp 28 }

snmpOutTraps OBJECT-TYPE
    SYNTAX      Counter32
    MAX-ACCESS  read-only
    STATUS      obsolete
    DESCRIPTION
            "The total number of SNMP Trap PDUs which have
            been generated by the SNMP protocol entity."
    ::= { snmp 29 }

snmpObsoleteGroup OBJECT-GROUP
    OBJECTS { snmpOutPkts, snmpInTooBigs, snmpInNoSuchNames,
              snmpInBadValues, snmpInReadOnlys, snmpInGenErrs,
              snmpInTotalReqVars, snmpInTotalSetVars,
              snmpInGetRequests, snmpInGetNexts, snmpInSetRequests,
              snmpInGetResponses, snmpInTraps, snmpOutTooBigs,
              snmpOutNoSuchNames, snmpOutBadValues, snmpOutGenErrs,
              snmpOutGetRequests, snmpOutGetNexts, snmpOutSetRequests,
              snmpOutGetResponses, snmpOutTraps }
    STATUS  obsolete
    DESCRIPTION
            "A collection of objects from RFC 1213 made obsolete by this
            MIB."
    ::= { snmpMIBGroups 10 }

END
   IF-MIB DEFINITIONS ::= BEGIN

   IMPORTS
       MODULE-IDENTITY, OBJECT-TYPE, 
	   NOTIFICATION-TYPE,
	   Counter32, 
	   Gauge32, 
       Integer32, TimeTicks, mib-2					FROM SNMPv2-SMI
       TEXTUAL-CONVENTION, DisplayString, TruthValue,
       PhysAddress, RowStatus						FROM SNMPv2-TC
       IANAifType									FROM IANAifType-MIB
	   snmpTraps									FROM SNMPv2-MIB;

   ifMIB MODULE-IDENTITY
       LAST-UPDATED "9611031355Z"
       ORGANIZATION "IETF Interfaces MIB Working Group"
       CONTACT-INFO
               "   Keith McCloghrie
                   Cisco Systems, Inc.
                   170 West Tasman Drive
                   San Jose, CA  95134-1706
                   US

                   408-526-5260
                   kzm@cisco.com"
       DESCRIPTION
               "The MIB module to describe generic objects for
               network interface sub-layers.  This MIB is an updated
               version of MIB-II's ifTable, and incorporates the
               extensions defined in RFC 1229."
       REVISION      "9602282155Z"
       DESCRIPTION
               "Revisions made by the Interfaces MIB WG."
       REVISION      "9311082155Z"
       DESCRIPTION
               "Initial revision, published as part of RFC 1573."
       ::= { mib-2 31 }


   ifMIBObjects OBJECT IDENTIFIER ::= { ifMIB 1 }

   interfaces   OBJECT IDENTIFIER ::= { mib-2 2 }


--   OwnerString ::= TEXTUAL-CONVENTION
--       DISPLAY-HINT "255a"
--       STATUS       current
--       DESCRIPTION
--               "This data type is used to model an administratively
--               assigned name of the owner of a resource.  This
--               information is taken from the NVT ASCII character set.
--               It is suggested that this name contain one or more of
--               the following: ASCII form of the manager station's
--               transport address, management station name (e.g.,
--               domain name), network management personnel's name,
--               location, or phone number.  In some cases the agent
--               itself will be the owner of an entry.  In these cases,
--               this string shall be set to a string starting with
--               'agent'."
--       SYNTAX       OCTET STRING (SIZE(0..255))

   -- InterfaceIndex contains the semantics of ifIndex and
   -- should be used for any objects defined on other mib
   -- modules that need these semantics.

   InterfaceIndex ::= TEXTUAL-CONVENTION
       DISPLAY-HINT "d"
       STATUS       current
       DESCRIPTION
               "A unique value, greater than zero, for each interface
               or interface sub-layer in the managed system.  It is
               recommended that values are assigned contiguously
               starting from 1.  The value for each interface sub-
               layer must remain constant at least from one re-
               initialization of the entity's network management
               system to the next re-initialization."
       SYNTAX       Integer32 (1..2147483647)


   InterfaceIndexOrZero ::= TEXTUAL-CONVENTION
       DISPLAY-HINT "d"
       STATUS       current
       DESCRIPTION
               "This textual convention is an extension of the
               InterfaceIndex convention.  The latter defines a
               greater than zero value used to identify an interface
               or interface sub-layer in the managed system.  This
               extension permits the additional value of zero.  the
               value zero is object-specific and must therefore be
               defined as part of the description of any object which
               uses this syntax.  Examples of the usage of zero might
               include situations where interface was unknown, or
               when none or all interfaces need to be referenced."
       SYNTAX       Integer32 (0..2147483647)


   ifNumber  OBJECT-TYPE
       SYNTAX      Integer32
       MAX-ACCESS  read-only
       STATUS      current
       DESCRIPTION
               "The number of network interfaces (regardless of their
               current state) present on this system."
       ::= { interfaces 1 }

   ifTableLastChange  OBJECT-TYPE
       SYNTAX      TimeTicks
       MAX-ACCESS  read-only
       STATUS      current
       DESCRIPTION
               "The value of sysUpTime at the time of the last
               creation or deletion of an entry in the ifTable.  If
               the number of entries has been unchanged since the
               last re-initialization of the local network management
               subsystem, then this object contains a zero value."
       ::= { ifMIBObjects 5 }


   -- the Interfaces table

   -- The Interfaces table contains information on the entity's
   -- interfaces.  Each sub-layer below the internetwork-layer
   -- of a network interface is considered to be an interface.

   ifTable OBJECT-TYPE
       SYNTAX      SEQUENCE OF IfEntry
       MAX-ACCESS  not-accessible
       STATUS      current
       DESCRIPTION
               "A list of interface entries.  The number of entries
               is given by the value of ifNumber."
       ::= { interfaces 2 }

   ifEntry OBJECT-TYPE
       SYNTAX      IfEntry
       MAX-ACCESS  not-accessible
       STATUS      current
       DESCRIPTION
               "An entry containing management information applicable
               to a particular interface."
       INDEX   { ifIndex }
       ::= { ifTable 1 }

   IfEntry ::=
       SEQUENCE {
           ifIndex                 InterfaceIndex,
           ifDescr                 DisplayString,
           ifType                  IANAifType,
--           ifMtu                   Integer32,
           ifSpeed                 Gauge32,
           ifPhysAddress           PhysAddress,
           ifAdminStatus           INTEGER,
           ifOperStatus            INTEGER,
           ifLastChange            TimeTicks,
           ifInOctets              Counter32,
--           ifInUcastPkts           Counter32,
--           ifInNUcastPkts          Counter32,  
												-- deprecated
--           ifInDiscards            Counter32,
           ifInErrors              Counter32,
           ifInUnknownProtos       Counter32,
           ifOutOctets             Counter32,
--           ifOutUcastPkts          Counter32,
--           ifOutNUcastPkts         Counter32,  
												-- deprecated
--           ifOutDiscards           Counter32,
           ifOutErrors             Counter32
--           ifOutQLen               Gauge32,    
												-- deprecated
--           ifSpecific              OBJECT IDENTIFIER 
												-- deprecated
       }


   ifIndex OBJECT-TYPE
       SYNTAX      InterfaceIndex
       MAX-ACCESS  read-only
       STATUS      current
       DESCRIPTION
               "A unique value, greater than zero, for each
               interface.  It is recommended that values are assigned
               contiguously starting from 1.  The value for each
               interface sub-layer must remain constant at least from
               one re-initialization of the entity's network
               management system to the next re-initialization."
       ::= { ifEntry 1 }

   ifDescr OBJECT-TYPE
       SYNTAX      DisplayString (SIZE (0..255))
       MAX-ACCESS  read-only
       STATUS      current
       DESCRIPTION
               "A textual string containing information about the
               interface.  This string should include the name of the
               manufacturer, the product name and the version of the
               interface hardware/software."
       ::= { ifEntry 2 }

   ifType OBJECT-TYPE
       SYNTAX      IANAifType
       MAX-ACCESS  read-only
       STATUS      current
       DESCRIPTION
               "The type of interface.  Additional values for ifType
               are assigned by the Internet Assigned Numbers
               Authority (IANA), through updating the syntax of the
               IANAifType textual convention."
       ::= { ifEntry 3 }

--   ifMtu OBJECT-TYPE
--       SYNTAX      Integer32
--       MAX-ACCESS  read-only
--       STATUS      current
--       DESCRIPTION
--               "The size of the largest packet which can be
--               sent/received on the interface, specified in octets.
--               For interfaces that are used for transmitting network
--               datagrams, this is the size of the largest network
--               datagram that can be sent on the interface."
--       ::= { ifEntry 4 }

   ifSpeed OBJECT-TYPE
       SYNTAX      Gauge32
       MAX-ACCESS  read-only
       STATUS      current
       DESCRIPTION
               "An estimate of the interface's current bandwidth in
               bits per second.  For interfaces which do not vary in
               bandwidth or for those where no accurate estimation
               can be made, this object should contain the nominal
               bandwidth.  If the bandwidth of the interface is
               greater than the maximum value reportable by this
               object then this object should report its maximum
               value (4,294,967,295) and ifHighSpeed must be used to
               report the interace's speed.  For a sub-layer which
               has no concept of bandwidth, this object should be
               zero."
       ::= { ifEntry 5 }

   ifPhysAddress OBJECT-TYPE
       SYNTAX      PhysAddress
       MAX-ACCESS  read-only
       STATUS      current
       DESCRIPTION
               "The interface's address at its protocol sub-layer.
               For example, for an 802.x interface, this object
               normally contains a MAC address.  The interface's
               media-specific MIB must define the bit and byte
               ordering and the format of the value of this object.
               For interfaces which do not have such an address
               (e.g., a serial line), this object should contain an
               octet string of zero length."
       ::= { ifEntry 6 }

   ifAdminStatus OBJECT-TYPE
       SYNTAX  INTEGER {
                   up(1),       -- ready to pass packets
                   down(2),
                   testing(3)   -- in some test mode
               }
       MAX-ACCESS  read-write
       STATUS      current
       DESCRIPTION
               "The desired state of the interface.  The testing(3)
               state indicates that no operational packets can be
               passed.  When a managed system initializes, all
               interfaces start with ifAdminStatus in the down(2)
               state.  As a result of either explicit management
               action or per configuration information retained by
               the managed system, ifAdminStatus is then changed to
               either the up(1) or testing(3) states (or remains in
               the down(2) state)."
       ::= { ifEntry 7 }

   ifOperStatus OBJECT-TYPE
       SYNTAX  INTEGER {
                   up(1),        -- ready to pass packets
                   down(2),
                   testing(3),   -- in some test mode
                   unknown(4),   -- status can not be determined
                                 -- for some reason.
                   dormant(5),
                   notPresent(6),    -- some component is missing
                   lowerLayerDown(7) -- down due to state of
                                     -- lower-layer interface(s)
               }
       MAX-ACCESS  read-only
       STATUS      current
       DESCRIPTION
               "The current operational state of the interface.  The
               testing(3) state indicates that no operational packets
               can be passed.  If ifAdminStatus is down(2) then
               ifOperStatus should be down(2).  If ifAdminStatus is
               changed to up(1) then ifOperStatus should change to
               up(1) if the interface is ready to transmit and
               receive network traffic; it should change to
               dormant(5) if the interface is waiting for external
               actions (such as a serial line waiting for an incoming
               connection); it should remain in the down(2) state if
               and only if there is a fault that prevents it from
               going to the up(1) state; it should remain in the
               notPresent(6) state if the interface has missing
               (typically, hardware) components."
       ::= { ifEntry 8 }

   ifLastChange OBJECT-TYPE
       SYNTAX      TimeTicks
       MAX-ACCESS  read-only
       STATUS      current
       DESCRIPTION
               "The value of sysUpTime at the time the interface
               entered its current operational state.  If the current
               state was entered prior to the last re-initialization
               of the local network management subsystem, then this
               object contains a zero value."
       ::= { ifEntry 9 }

   ifInOctets OBJECT-TYPE
       SYNTAX      Counter32
       MAX-ACCESS  read-only
       STATUS      current
       DESCRIPTION
               "The total number of octets received on the interface,
               including framing characters.

               Discontinuities in the value of this counter can occur
               at re-initialization of the management system, and at
               other times as indicated by the value of
               ifCounterDiscontinuityTime."
       ::= { ifEntry 10 }

--   ifInUcastPkts OBJECT-TYPE
--       SYNTAX      Counter32
--       MAX-ACCESS  read-only
--       STATUS      current
--       DESCRIPTION
--               "The number of packets, delivered by this sub-layer to
--               a higher (sub-)layer, which were not addressed to a
--               multicast or broadcast address at this sub-layer.
--
--               Discontinuities in the value of this counter can occur
--               at re-initialization of the management system, and at
--               other times as indicated by the value of
--               ifCounterDiscontinuityTime."
--       ::= { ifEntry 11 }

--   ifInNUcastPkts OBJECT-TYPE
--       SYNTAX  Counter32
--       MAX-ACCESS  read-only
--       STATUS      deprecated
--       DESCRIPTION
--               "The number of packets, delivered by this sub-layer to
--               a higher (sub-)layer, which were addressed to a
--               multicast or broadcast address at this sub-layer.
--
--               Discontinuities in the value of this counter can occur
--               at re-initialization of the management system, and at
--               other times as indicated by the value of
--               ifCounterDiscontinuityTime.
--
--               This object is deprecated in favour of
--               ifInMulticastPkts and ifInBroadcastPkts."
--       ::= { ifEntry 12 }

--   ifInDiscards OBJECT-TYPE
--       SYNTAX      Counter32
--       MAX-ACCESS  read-only
--       STATUS      current
--       DESCRIPTION
--               "The number of inbound packets which were chosen to be
--               discarded even though no errors had been detected to
--               prevent their being deliverable to a higher-layer
--               protocol.  One possible reason for discarding such a
--               packet could be to free up buffer space.
--
--               Discontinuities in the value of this counter can occur
--               at re-initialization of the management system, and at
--               other times as indicated by the value of
--               ifCounterDiscontinuityTime."
--       ::= { ifEntry 13 }

   ifInErrors OBJECT-TYPE
       SYNTAX      Counter32
       MAX-ACCESS  read-only
       STATUS      current
       DESCRIPTION
               "For packet-oriented interfaces, the number of inbound
               packets that contained errors preventing them from
               being deliverable to a higher-layer protocol.  For
               character-oriented or fixed-length interfaces, the
               number of inbound transmission units that contained
               errors preventing them from being deliverable to a
               higher-layer protocol.

               Discontinuities in the value of this counter can occur
               at re-initialization of the management system, and at
               other times as indicated by the value of
               ifCounterDiscontinuityTime."
       ::= { ifEntry 14 }

   ifInUnknownProtos OBJECT-TYPE
       SYNTAX      Counter32
       MAX-ACCESS  read-only
       STATUS      current
       DESCRIPTION
               "For packet-oriented interfaces, the number of packets
               received via the interface which were discarded
               because of an unknown or unsupported protocol.  For
               character-oriented or fixed-length interfaces that
               support protocol multiplexing the number of
               transmission units received via the interface which
               were discarded because of an unknown or unsupported
               protocol.  For any interface that does not support
               protocol multiplexing, this counter will always be 0.

               Discontinuities in the value of this counter can occur
               at re-initialization of the management system, and at
               other times as indicated by the value of
               ifCounterDiscontinuityTime."
       ::= { ifEntry 15 }

   ifOutOctets OBJECT-TYPE
       SYNTAX      Counter32
       MAX-ACCESS  read-only
       STATUS      current
       DESCRIPTION
               "The total number of octets transmitted out of the
               interface, including framing characters.

              Discontinuities in the value of this counter can occur
               at re-initialization of the management system, and at
               other times as indicated by the value of
               ifCounterDiscontinuityTime."
       ::= { ifEntry 16 }

--   ifOutUcastPkts OBJECT-TYPE
--       SYNTAX      Counter32
--       MAX-ACCESS  read-only
--       STATUS      current
--       DESCRIPTION
--               "The total number of packets that higher-level
--               protocols requested be transmitted, and which were not
--               addressed to a multicast or broadcast address at this
--               sub-layer, including those that were discarded or not
--               sent.
--
--               Discontinuities in the value of this counter can occur
--               at re-initialization of the management system, and at
--               other times as indicated by the value of
--               ifCounterDiscontinuityTime."
--       ::= { ifEntry 17 }

--   ifOutNUcastPkts OBJECT-TYPE
--       SYNTAX      Counter32
--       MAX-ACCESS  read-only
--       STATUS      deprecated
--       DESCRIPTION
--               "The total number of packets that higher-level
--               protocols requested be transmitted, and which were
--               addressed to a multicast or broadcast address at this
--               sub-layer, including those that were discarded or not
--               sent.
--
--               Discontinuities in the value of this counter can occur
--               at re-initialization of the management system, and at
--               other times as indicated by the value of
--               ifCounterDiscontinuityTime.
--               This object is deprecated in favour of
--               ifOutMulticastPkts and ifOutBroadcastPkts."
--       ::= { ifEntry 18 }

--   ifOutDiscards OBJECT-TYPE
--       SYNTAX      Counter32
--       MAX-ACCESS  read-only
--       STATUS      current
--       DESCRIPTION
--               "The number of outbound packets which were chosen to
--               be discarded even though no errors had been detected
--               to prevent their being transmitted.  One possible
--               reason for discarding such a packet could be to free
--               up buffer space.
--
--               Discontinuities in the value of this counter can occur
--               at re-initialization of the management system, and at
--               other times as indicated by the value of
--               ifCounterDiscontinuityTime."
--       ::= { ifEntry 19 }

   ifOutErrors OBJECT-TYPE
       SYNTAX      Counter32
       MAX-ACCESS  read-only
       STATUS      current
       DESCRIPTION
               "For packet-oriented interfaces, the number of
               outbound packets that could not be transmitted because
               of errors.  For character-oriented or fixed-length
               interfaces, the number of outbound transmission units
               that could not be transmitted because of errors.

               Discontinuities in the value of this counter can occur
               at re-initialization of the management system, and at
               other times as indicated by the value of
               ifCounterDiscontinuityTime."
       ::= { ifEntry 20 }


--   ifOutQLen OBJECT-TYPE
--       SYNTAX      Gauge32
--       MAX-ACCESS  read-only
--       STATUS      deprecated
--       DESCRIPTION
--               "The length of the output packet queue (in packets)."
--       ::= { ifEntry 21 }

--   ifSpecific OBJECT-TYPE
--       SYNTAX      OBJECT IDENTIFIER
--       MAX-ACCESS  read-only
--       STATUS      deprecated
--       DESCRIPTION
--               "A reference to MIB definitions specific to the
--               particular media being used to realize the interface.
--               It is recommended that this value point to an instance
--               of a MIB object in the media-specific MIB, i.e., that
--               this object have the semantics associated with the
--               InstancePointer textual convention defined in RFC
--               1903.  In fact, it is recommended that the media-
--               specific MIB specify what value ifSpecific should/can
--               take for values of ifType.  If no MIB definitions
--               specific to the particular media are available, the
--               value should be set to the OBJECT IDENTIFIER { 0 0 }."
--       ::= { ifEntry 22 }



   --
   --   Extension to the interface table
   --
   -- This table replaces the ifExtnsTable table.
   --

   ifXTable        OBJECT-TYPE
       SYNTAX      SEQUENCE OF IfXEntry
       MAX-ACCESS  not-accessible
       STATUS      current
       DESCRIPTION
               "A list of interface entries.  The number of entries
               is given by the value of ifNumber.  This table
               contains additional objects for the interface table."
       ::= { ifMIBObjects 1 }

   ifXEntry        OBJECT-TYPE
       SYNTAX      IfXEntry
       MAX-ACCESS  not-accessible
       STATUS      current
       DESCRIPTION
               "An entry containing additional management information
               applicable to a particular interface."
       AUGMENTS    { ifEntry }
       ::= { ifXTable 1 }

   IfXEntry ::=
       SEQUENCE {
           ifName                  DisplayString,
--           ifInMulticastPkts       Counter32,
--           ifInBroadcastPkts       Counter32,
--           ifOutMulticastPkts      Counter32,
--           ifOutBroadcastPkts      Counter32,
--           ifHCInOctets            Counter64,
--           ifHCInUcastPkts         Counter64,
--           ifHCInMulticastPkts     Counter64,
--           ifHCInBroadcastPkts     Counter64,
--           ifHCOutOctets           Counter64,
--           ifHCOutUcastPkts        Counter64,
--           ifHCOutMulticastPkts    Counter64,
--           ifHCOutBroadcastPkts    Counter64,
           ifLinkUpDownTrapEnable  INTEGER,
           ifHighSpeed             Gauge32,
--           ifPromiscuousMode       TruthValue,
           ifConnectorPresent      TruthValue,
           ifAlias                 DisplayString
--           ifCounterDiscontinuityTime TimeStamp
       }


   ifName OBJECT-TYPE
       SYNTAX      DisplayString
       MAX-ACCESS  read-only
       STATUS      current
       DESCRIPTION
               "The textual name of the interface.  The value of this
               object should be the name of the interface as assigned
               by the local device and should be suitable for use in
               commands entered at the device's `console'.  This
               might be a text name, such as `le0' or a simple port
               number, such as `1', depending on the interface naming
               syntax of the device.  If several entries in the
               ifTable together represent a single interface as named
               by the device, then each will have the same value of
               ifName.  Note that for an agent which responds to SNMP
               queries concerning an interface on some other
               (proxied) device, then the value of ifName for such an
               interface is the proxied device's local name for it.

               If there is no local name, or this object is otherwise
               not applicable, then this object contains a zero-
               length string."
       ::= { ifXEntry 1 }

--   ifInMulticastPkts OBJECT-TYPE
--       SYNTAX      Counter32
--       MAX-ACCESS  read-only
--       STATUS      current
--       DESCRIPTION
--               "The number of packets, delivered by this sub-layer to
--               a higher (sub-)layer, which were addressed to a
--               multicast address at this sub-layer.  For a MAC layer
--               protocol, this includes both Group and Functional
--               addresses.
--
--               Discontinuities in the value of this counter can occur
--               at re-initialization of the management system, and at
--               other times as indicated by the value of
--               ifCounterDiscontinuityTime."
--       ::= { ifXEntry 2 }

--   ifInBroadcastPkts OBJECT-TYPE
--       SYNTAX      Counter32
--       MAX-ACCESS  read-only
--       STATUS      current
--       DESCRIPTION
--               "The number of packets, delivered by this sub-layer to
--               a higher (sub-)layer, which were addressed to a
--               broadcast address at this sub-layer.
--
--               Discontinuities in the value of this counter can occur
--               at re-initialization of the management system, and at
--               other times as indicated by the value of
--               ifCounterDiscontinuityTime."
--       ::= { ifXEntry 3 }

--   ifOutMulticastPkts OBJECT-TYPE
--       SYNTAX      Counter32
--       MAX-ACCESS  read-only
--       STATUS      current
--       DESCRIPTION
--               "The total number of packets that higher-level
--               protocols requested be transmitted, and which were
--               addressed to a multicast address at this sub-layer,
--               including those that were discarded or not sent.  For
--               a MAC layer protocol, this includes both Group and
--               Functional addresses.
--
--               Discontinuities in the value of this counter can occur
--               at re-initialization of the management system, and at
--               other times as indicated by the value of
--               ifCounterDiscontinuityTime."
--       ::= { ifXEntry 4 }

--   ifOutBroadcastPkts OBJECT-TYPE
--       SYNTAX      Counter32
--       MAX-ACCESS  read-only
--       STATUS      current
--       DESCRIPTION
--               "The total number of packets that higher-level
--               protocols requested be transmitted, and which were
--               addressed to a broadcast address at this sub-layer,
--               including those that were discarded or not sent.
--
--               Discontinuities in the value of this counter can occur
--               at re-initialization of the management system, and at
--               other times as indicated by the value of
--               ifCounterDiscontinuityTime."
--       ::= { ifXEntry 5 }

   --
   -- High Capacity Counter objects.  These objects are all
   -- 64 bit versions of the "basic" ifTable counters.  These
   -- objects all have the same basic semantics as their 32-bit
   -- counterparts, however, their syntax has been extended
   -- to 64 bits.
   --

--   ifHCInOctets OBJECT-TYPE
--       SYNTAX      Counter64
--       MAX-ACCESS  read-only
--       STATUS      current
--
--       DESCRIPTION
--               "The total number of octets received on the interface,
--               including framing characters.  This object is a 64-bit
--               version of ifInOctets.
--
--               Discontinuities in the value of this counter can occur
--               at re-initialization of the management system, and at
--               other times as indicated by the value of
--               ifCounterDiscontinuityTime."
--       ::= { ifXEntry 6 }

--   ifHCInUcastPkts OBJECT-TYPE
--       SYNTAX      Counter64
--       MAX-ACCESS  read-only
--       STATUS      current
--       DESCRIPTION
--               "The number of packets, delivered by this sub-layer to
--               a higher (sub-)layer, which were not addressed to a
--               multicast or broadcast address at this sub-layer.
--               This object is a 64-bit version of ifInUcastPkts.
--
--               Discontinuities in the value of this counter can occur
--               at re-initialization of the management system, and at
--               other times as indicated by the value of
--               ifCounterDiscontinuityTime."
--       ::= { ifXEntry 7 }

--   ifHCInMulticastPkts OBJECT-TYPE
--       SYNTAX      Counter64
--       MAX-ACCESS  read-only
--       STATUS      current
--       DESCRIPTION
--               "The number of packets, delivered by this sub-layer to
--               a higher (sub-)layer, which were addressed to a
--               multicast address at this sub-layer.  For a MAC layer
--               protocol, this includes both Group and Functional
--               addresses.  This object is a 64-bit version of
--               ifInMulticastPkts.
--
--               Discontinuities in the value of this counter can occur
--               at re-initialization of the management system, and at
--               other times as indicated by the value of
--               ifCounterDiscontinuityTime."
--       ::= { ifXEntry 8 }


--   ifHCInBroadcastPkts OBJECT-TYPE
--       SYNTAX      Counter64
--       MAX-ACCESS  read-only
--       STATUS      current
--       DESCRIPTION
--               "The number of packets, delivered by this sub-layer to
--               a higher (sub-)layer, which were addressed to a
--               broadcast address at this sub-layer.  This object is a
--               64-bit version of ifInBroadcastPkts.
--
--               Discontinuities in the value of this counter can occur
--               at re-initialization of the management system, and at
--               other times as indicated by the value of
--               ifCounterDiscontinuityTime."
--       ::= { ifXEntry 9 }

--   ifHCOutOctets OBJECT-TYPE
--       SYNTAX      Counter64
--       MAX-ACCESS  read-only
--       STATUS      current
--       DESCRIPTION
--               "The total number of octets transmitted out of the
--               interface, including framing characters.  This object
--               is a 64-bit version of ifOutOctets.
--
--               Discontinuities in the value of this counter can occur
--               at re-initialization of the management system, and at
--               other times as indicated by the value of
--               ifCounterDiscontinuityTime."
--       ::= { ifXEntry 10 }

--   ifHCOutUcastPkts OBJECT-TYPE
--       SYNTAX      Counter64
--       MAX-ACCESS  read-only
--       STATUS      current
--       DESCRIPTION
--               "The total number of packets that higher-level
--               protocols requested be transmitted, and which were not
--               addressed to a multicast or broadcast address at this
--               sub-layer, including those that were discarded or not
--               sent.  This object is a 64-bit version of
--               ifOutUcastPkts.
--
--               Discontinuities in the value of this counter can occur
--               at re-initialization of the management system, and at
--               other times as indicated by the value of
--               ifCounterDiscontinuityTime."
--       ::= { ifXEntry 11 }

--   ifHCOutMulticastPkts OBJECT-TYPE
--       SYNTAX      Counter64
--       MAX-ACCESS  read-only
--       STATUS      current
--       DESCRIPTION
--               "The total number of packets that higher-level
--               protocols requested be transmitted, and which were
--               addressed to a multicast address at this sub-layer,
--               including those that were discarded or not sent.  For
--               a MAC layer protocol, this includes both Group and
--               Functional addresses.  This object is a 64-bit version
--               of ifOutMulticastPkts.
--               Discontinuities in the value of this counter can occur
--               at re-initialization of the management system, and at
--               other times as indicated by the value of
--               ifCounterDiscontinuityTime."
--       ::= { ifXEntry 12 }

--   ifHCOutBroadcastPkts OBJECT-TYPE
--       SYNTAX      Counter64
--       MAX-ACCESS  read-only
--       STATUS      current
--       DESCRIPTION
--               "The total number of packets that higher-level
--               protocols requested be transmitted, and which were
--               addressed to a broadcast address at this sub-layer,
--               including those that were discarded or not sent.  This
--               object is a 64-bit version of ifOutBroadcastPkts.
--
--               Discontinuities in the value of this counter can occur
--               at re-initialization of the management system, and at
--               other times as indicated by the value of
--               ifCounterDiscontinuityTime."
--       ::= { ifXEntry 13 }

  ifLinkUpDownTrapEnable  OBJECT-TYPE
       SYNTAX      INTEGER { enabled(1), disabled(2) }
       MAX-ACCESS  read-write
       STATUS      current
       DESCRIPTION
               "Indicates whether linkUp/linkDown traps should be
               generated for this interface.

               By default, this object should have the value
               enabled(1) for interfaces which do not operate on
               'top' of any other interface (as defined in the
               ifStackTable), and disabled(2) otherwise."
       ::= { ifXEntry 14 }

   ifHighSpeed OBJECT-TYPE
       SYNTAX      Gauge32
       MAX-ACCESS  read-only
       STATUS      current
       DESCRIPTION
               "An estimate of the interface's current bandwidth in
               units of 1,000,000 bits per second.  If this object
               reports a value of `n' then the speed of the interface
               is somewhere in the range of `n-500,000' to
               `n+499,999'.  For interfaces which do not vary in
               bandwidth or for those where no accurate estimation
               can be made, this object should contain the nominal
               bandwidth.  For a sub-layer which has no concept of
               bandwidth, this object should be zero."
       ::= { ifXEntry 15 }

--   ifPromiscuousMode  OBJECT-TYPE
--       SYNTAX      TruthValue
--       MAX-ACCESS  read-write
--       STATUS      current
--       DESCRIPTION
--               "This object has a value of false(2) if this interface
--               only accepts packets/frames that are addressed to this
--               station.  This object has a value of true(1) when the
--               station accepts all packets/frames transmitted on the
--               media.  The value true(1) is only legal on certain
--               types of media.  If legal, setting this object to a
--               value of true(1) may require the interface to be reset
--               before becoming effective.
--
--               The value of ifPromiscuousMode does not affect the
--               reception of broadcast and multicast packets/frames by
--               the interface."
--       ::= { ifXEntry 16 }

   ifConnectorPresent   OBJECT-TYPE
       SYNTAX      TruthValue
       MAX-ACCESS  read-only
       STATUS      current
       DESCRIPTION
               "This object has the value 'true(1)' if the interface
               sublayer has a physical connector and the value
               'false(2)' otherwise."
       ::= { ifXEntry 17 }

   ifAlias   OBJECT-TYPE
       SYNTAX      DisplayString (SIZE(0..64))
       MAX-ACCESS  read-write
       STATUS      current
       DESCRIPTION
               "This object is an 'alias' name for the interface as
               specified by a network manager, and provides a non-
               volatile 'handle' for the interface.

               On the first instantiation of an interface, the value
               of ifAlias associated with that interface is the
               zero-length string.  As and when a value is written
               into an instance of ifAlias through a network
               management set operation, then the agent must retain
               the supplied value in the ifAlias instance associated
               with the same interface for as long as that interface
               remains instantiated, including across all re-
               initializations/reboots of the network management
               system, including those which result in a change of
               the interface's ifIndex value.

               An example of the value which a network manager might
               store in this object for a WAN interface is the
               (Telco's) circuit number/identifier of the interface.

               Some agents may support write-access only for
               interfaces having particular values of ifType.  An
               agent which supports write access to this object is
               required to keep the value in non-volatile storage,
               but it may limit the length of new values depending on
               how much storage is already occupied by the current
               values for other interfaces."
       ::= { ifXEntry 18 }

--   ifCounterDiscontinuityTime OBJECT-TYPE
--       SYNTAX      TimeStamp
--       MAX-ACCESS  read-only
--       STATUS      current
--       DESCRIPTION
--               "The value of sysUpTime on the most recent occasion at
--               which any one or more of this interface's counters
--               suffered a discontinuity.  The relevant counters are
--               the specific instances associated with this interface
--               of any Counter32 or Counter64 object contained in the
--               ifTable or ifXTable.  If no such discontinuities have
--               occurred since the last re-initialization of the local
--               management subsystem, then this object contains a zero
--               value."
--       ::= { ifXEntry 19 }


   --           The Interface Stack Group
   --
   -- Implementation of this group is mandatory for all systems
   --

   ifStackTable  OBJECT-TYPE
        SYNTAX        SEQUENCE OF IfStackEntry
        MAX-ACCESS    not-accessible
        STATUS        current
        DESCRIPTION
               "The table containing information on the relationships
               between the multiple sub-layers of network interfaces.
               In particular, it contains information on which sub-
               layers run 'on top of' which other sub-layers, where
               each sub-layer corresponds to a conceptual row in the
               ifTable.  For example, when the sub-layer with ifIndex
               value x runs over the sub-layer with ifIndex value y,
               then this table contains:

                 ifStackStatus.x.y=active

               For each ifIndex value, I, which identifies an active
               interface, there are always at least two instantiated
               rows in this table associated with I.  For one of
               these rows, I is the value of ifStackHigherLayer; for
               the other, I is the value of ifStackLowerLayer.  (If I
               is not involved in multiplexing, then these are the
               only two rows associated with I.)

               For example, two rows exist even for an interface
               which has no others stacked on top or below it:

                 ifStackStatus.0.x=active
                 ifStackStatus.x.0=active "
        ::= { ifMIBObjects 2 }


   ifStackEntry  OBJECT-TYPE
        SYNTAX        IfStackEntry
        MAX-ACCESS    not-accessible
        STATUS        current
        DESCRIPTION
               "Information on a particular relationship between two
               sub-layers, specifying that one sub-layer runs on
               'top' of the other sub-layer.  Each sub-layer
               corresponds to a conceptual row in the ifTable."
        INDEX { ifStackHigherLayer, ifStackLowerLayer }
        ::= { ifStackTable 1 }


   IfStackEntry ::=
       SEQUENCE {
           ifStackHigherLayer  Integer32,
           ifStackLowerLayer   Integer32,
           ifStackStatus       RowStatus
        }

   ifStackHigherLayer  OBJECT-TYPE
        SYNTAX        Integer32
        MAX-ACCESS    not-accessible
        STATUS        current
        DESCRIPTION
               "The value of ifIndex corresponding to the higher
               sub-layer of the relationship, i.e., the sub-layer
               which runs on 'top' of the sub-layer identified by the
               corresponding instance of ifStackLowerLayer.  If there
               is no higher sub-layer (below the internetwork layer),
               then this object has the value 0."
        ::= { ifStackEntry 1 }


   ifStackLowerLayer  OBJECT-TYPE
        SYNTAX        Integer32
        MAX-ACCESS    not-accessible
        STATUS        current
        DESCRIPTION
               "The value of ifIndex corresponding to the lower sub-
               layer of the relationship, i.e., the sub-layer which
               runs 'below' the sub-layer identified by the
               corresponding instance of ifStackHigherLayer.  If
               there is no lower sub-layer, then this object has the
               value 0."
        ::= { ifStackEntry 2 }


   ifStackStatus  OBJECT-TYPE
       SYNTAX         RowStatus
       MAX-ACCESS     read-create
       STATUS         current
       DESCRIPTION
               "The status of the relationship between two sub-
               layers.

               Changing the value of this object from 'active' to
               'notInService' or 'destroy' will likely have
               consequences up and down the interface stack.  Thus,
               write access to this object is likely to be
               inappropriate for some types of interfaces, and many
               implementations will choose not to support write-
               access for any type of interface."
       ::= { ifStackEntry 3 }

--   ifStackLastChange OBJECT-TYPE
--       SYNTAX         TimeTicks
--       MAX-ACCESS     read-only
--       STATUS         current
--       DESCRIPTION
--               "The value of sysUpTime at the time of the last change
--               of the (whole) interface stack.  A change of the
--               interface stack is defined to be any creation,
--               deletion, or change in value of any instance of
--               ifStackStatus.  If the interface stack has been
--               unchanged since the last re-initialization of the
--               local network management subsystem, then this object
--               contains a zero value."
--       ::= { ifMIBObjects 6 }

   --   Generic Receive Address Table
   --
   -- This group of objects is mandatory for all types of
   -- interfaces which can receive packets/frames addressed to
   -- more than one address.
   --
   -- This table replaces the ifExtnsRcvAddr table.  The main
   -- difference is that this table makes use of the RowStatus
   -- textual convention, while ifExtnsRcvAddr did not.

--   ifRcvAddressTable  OBJECT-TYPE
--       SYNTAX      SEQUENCE OF IfRcvAddressEntry
--       MAX-ACCESS  not-accessible
--       STATUS      current
--       DESCRIPTION
--               "This table contains an entry for each address
--               (broadcast, multicast, or uni-cast) for which the
--               system will receive packets/frames on a particular
--               interface, except as follows:
--
--               - for an interface operating in promiscuous mode,
--               entries are only required for those addresses for
--               which the system would receive frames were it not
--               operating in promiscuous mode.
--
--               - for 802.5 functional addresses, only one entry is
--               required, for the address which has the functional
--               address bit ANDed with the bit mask of all functional
--               addresses for which the interface will accept frames.
--
--               A system is normally able to use any unicast address
--               which corresponds to an entry in this table as a
--               source address."
--       ::= { ifMIBObjects 4 }

--
--   ifRcvAddressEntry  OBJECT-TYPE
--       SYNTAX      IfRcvAddressEntry
--       MAX-ACCESS  not-accessible
--       STATUS      current
--       DESCRIPTION
--               "A list of objects identifying an address for which
--               the system will accept packets/frames on the
--               particular interface identified by the index value
--               ifIndex."
--       INDEX  { ifIndex, ifRcvAddressAddress }
--       ::= { ifRcvAddressTable 1 }
--
--   IfRcvAddressEntry ::=
--       SEQUENCE {
--           ifRcvAddressAddress   PhysAddress,
--           ifRcvAddressStatus    RowStatus,
--           ifRcvAddressType      INTEGER
--       }
--
--   ifRcvAddressAddress OBJECT-TYPE
--       SYNTAX      PhysAddress
--       MAX-ACCESS  not-accessible
--       STATUS      current
--       DESCRIPTION
--               "An address for which the system will accept
--               packets/frames on this entry's interface."
--
--       ::= { ifRcvAddressEntry 1 }
--
--   ifRcvAddressStatus OBJECT-TYPE
--       SYNTAX      RowStatus
--       MAX-ACCESS  read-create
--       STATUS      current
--       DESCRIPTION
--               "This object is used to create and delete rows in the
--               ifRcvAddressTable."
--
--       ::= { ifRcvAddressEntry 2 }
--
--   ifRcvAddressType OBJECT-TYPE
--       SYNTAX      INTEGER {
--                       other(1),
--                       volatile(2),
--                       nonVolatile(3)
--                   }
--
--       MAX-ACCESS  read-create
--       STATUS      current
--       DESCRIPTION
--               "This object has the value nonVolatile(3) for those
--               entries in the table which are valid and will not be
--               deleted by the next restart of the managed system.
--               Entries having the value volatile(2) are valid and
--               exist, but have not been saved, so that will not exist
--               after the next restart of the managed system.  Entries
--               having the value other(1) are valid and exist but are
--               not classified as to whether they will continue to
--               exist after the next restart."
--
--       DEFVAL  { volatile }
--       ::= { ifRcvAddressEntry 3 }
--

   -- definition of interface-related traps.

   linkDown NOTIFICATION-TYPE
           OBJECTS { ifIndex, ifAdminStatus, ifOperStatus }
           STATUS  current
           DESCRIPTION
               "A linkDown trap signifies that the SNMPv2 entity,
               acting in an agent role, has detected that the
               ifOperStatus object for one of its communication links
               is about to enter the down state from some other state
               (but not from the notPresent state).  This other state
               is indicated by the included value of ifOperStatus."
       ::= { snmpTraps 3 }

   linkUp NOTIFICATION-TYPE
           OBJECTS { ifIndex, ifAdminStatus, ifOperStatus }
           STATUS  current
           DESCRIPTION
               "A linkDown trap signifies that the SNMPv2 entity,
               acting in an agent role, has detected that the
               ifOperStatus object for one of its communication links
               left the down state and transitioned into some other
               state (but not into the notPresent state).  This other
               state is indicated by the included value of
               ifOperStatus."
       ::= { snmpTraps 4 }

   -- conformance information

--   ifConformance OBJECT IDENTIFIER ::= { ifMIB 2 }

--   ifGroups      OBJECT IDENTIFIER ::= { ifConformance 1 }
--   ifCompliances OBJECT IDENTIFIER ::= { ifConformance 2 }

   -- compliance statements

--   ifCompliance2 MODULE-COMPLIANCE
--       STATUS  current
--       DESCRIPTION
--               "The compliance statement for SNMPv2 entities which
--               have network interfaces."
--
--       MODULE  
				-- this module
--           MANDATORY-GROUPS { ifGeneralInformationGroup, ifStackGroup2,
--                              ifCounterDiscontinuityGroup }
--
--           GROUP       ifFixedLengthGroup
--           DESCRIPTION
--               "This group is mandatory for all network interfaces
--               which are character-oriented or transmit data in
--               fixed-length transmission units."
--
--           GROUP       ifHCFixedLengthGroup
--           DESCRIPTION
--               "This group is mandatory only for those network
--               interfaces which are character-oriented or transmit
--               data in fixed-length transmission units, and for which
--               the value of the corresponding instance of ifSpeed is
--               greater than 20,000,000 bits/second."
--
--           GROUP       ifPacketGroup
--           DESCRIPTION
--               "This group is mandatory for all network interfaces
--               which are packet-oriented."
--
--           GROUP       ifHCPacketGroup
--           DESCRIPTION
--               "This group is mandatory only for those network
--               interfaces which are packet-oriented and for which the
--               value of the corresponding instance of ifSpeed is
--               greater than 650,000,000 bits/second."
--
--           GROUP       ifRcvAddressGroup
--           DESCRIPTION
--               "The applicability of this group MUST be defined by
--               the media-specific MIBs.  Media-specific MIBs must
--               define the exact meaning, use, and semantics of the
--               addresses in this group."
--
--           OBJECT      ifLinkUpDownTrapEnable
--           MIN-ACCESS  read-only
--           DESCRIPTION
--               "Write access is not required."
--
--           OBJECT      ifPromiscuousMode
--           MIN-ACCESS  read-only
--           DESCRIPTION
--               "Write access is not required."
--
--           OBJECT      ifStackStatus
--           SYNTAX      INTEGER { active(1) } 
						-- subset of RowStatus
--           MIN-ACCESS  read-only
--           DESCRIPTION
--               "Write access is not required, and only one of the six
--               enumerated values for the RowStatus textual convention
--               need be supported, specifically: active(1)."
--
--           OBJECT       ifAdminStatus
--           SYNTAX       INTEGER { up(1), down(2) }
--           MIN-ACCESS   read-only
--           DESCRIPTION
--               "Write access is not required, nor is support for the
--               value testing(3)."
--
--           OBJECT       ifAlias
--           MIN-ACCESS   read-only
--           DESCRIPTION
--               "Write access is not required."
--
--       ::= { ifCompliances 2 }

   -- units of conformance

--   ifGeneralInformationGroup    OBJECT-GROUP
--       OBJECTS { ifIndex, ifDescr, ifType, ifSpeed, ifPhysAddress,
--                 ifAdminStatus, ifOperStatus, ifLastChange,
--                 ifLinkUpDownTrapEnable, ifConnectorPresent,
--                 ifHighSpeed, ifName, ifNumber, ifAlias,
--                 ifTableLastChange }
--       STATUS  current
--       DESCRIPTION
--               "A collection of objects providing information
--               applicable to all network interfaces."
--       ::= { ifGroups 10 }

   -- the following five groups are mutually exclusive; at most
   -- one of these groups is implemented for any interface

--   ifFixedLengthGroup    OBJECT-GROUP
--       OBJECTS { ifInOctets, ifOutOctets, ifInUnknownProtos,
--                 ifInErrors, ifOutErrors }
--       STATUS  current
--       DESCRIPTION
--               "A collection of objects providing information
--               specific to non-high speed (non-high speed interfaces
--               transmit and receive at speeds less than or equal to
--               20,000,000 bits/second) character-oriented or fixed-
--               length-transmission network interfaces."
--       ::= { ifGroups 2 }

--   ifHCFixedLengthGroup    OBJECT-GROUP
--       OBJECTS { ifHCInOctets, ifHCOutOctets,
--                 ifInOctets, ifOutOctets, ifInUnknownProtos,
--                 ifInErrors, ifOutErrors }
--       STATUS  current
--       DESCRIPTION
--               "A collection of objects providing information
--               specific to high speed (greater than 20,000,000
--               bits/second) character-oriented or fixed-length-
--               transmission network interfaces."
--       ::= { ifGroups 3 }

--   ifPacketGroup    OBJECT-GROUP
--       OBJECTS { ifInOctets, ifOutOctets, ifInUnknownProtos,
--                 ifInErrors, ifOutErrors,
--                 ifMtu, ifInUcastPkts, ifInMulticastPkts,
--                 ifInBroadcastPkts, ifInDiscards,
--                 ifOutUcastPkts, ifOutMulticastPkts,
--                 ifOutBroadcastPkts, ifOutDiscards,
--                 ifPromiscuousMode }
--       STATUS  current
--       DESCRIPTION
--               "A collection of objects providing information
--               specific to non-high speed (non-high speed interfaces
--               transmit and receive at speeds less than or equal to
--               20,000,000 bits/second) packet-oriented network
--               interfaces."
--       ::= { ifGroups 4 }

--   ifHCPacketGroup    OBJECT-GROUP
--       OBJECTS { ifHCInOctets, ifHCOutOctets,
--                 ifInOctets, ifOutOctets, ifInUnknownProtos,
--                 ifInErrors, ifOutErrors,
--                 ifMtu, ifInUcastPkts, ifInMulticastPkts,
--                 ifInBroadcastPkts, ifInDiscards,
--                 ifOutUcastPkts, ifOutMulticastPkts,
--                 ifOutBroadcastPkts, ifOutDiscards,
--                 ifPromiscuousMode }
--       STATUS  current
--       DESCRIPTION
--               "A collection of objects providing information
--               specific to high speed (greater than 20,000,000
--               bits/second but less than or equal to 650,000,000
--               bits/second) packet-oriented network interfaces."
--       ::= { ifGroups 5 }

--   ifVHCPacketGroup    OBJECT-GROUP
--       OBJECTS { ifHCInUcastPkts, ifHCInMulticastPkts,
--                 ifHCInBroadcastPkts, ifHCOutUcastPkts,
--                 ifHCOutMulticastPkts, ifHCOutBroadcastPkts,
--                 ifHCInOctets, ifHCOutOctets,
--                 ifInOctets, ifOutOctets, ifInUnknownProtos,
--                 ifInErrors, ifOutErrors,
--                 ifMtu, ifInUcastPkts, ifInMulticastPkts,
--                 ifInBroadcastPkts, ifInDiscards,
--                 ifOutUcastPkts, ifOutMulticastPkts,
--                 ifOutBroadcastPkts, ifOutDiscards,
--                 ifPromiscuousMode }
--       STATUS  current
--       DESCRIPTION
--               "A collection of objects providing information
--               specific to higher speed (greater than 650,000,000
--               bits/second) packet-oriented network interfaces."
--       ::= { ifGroups 6 }

--   ifRcvAddressGroup    OBJECT-GROUP
--       OBJECTS { ifRcvAddressStatus, ifRcvAddressType }
--       STATUS  current
--       DESCRIPTION
--               "A collection of objects providing information on the
--               multiple addresses which an interface receives."
--       ::= { ifGroups 7 }

--   ifStackGroup2    OBJECT-GROUP
--       OBJECTS { ifStackStatus, ifStackLastChange }
--       STATUS  current
--       DESCRIPTION
--               "A collection of objects providing information on the
--               layering of MIB-II interfaces."
--       ::= { ifGroups 11 }

--   ifCounterDiscontinuityGroup  OBJECT-GROUP
--       OBJECTS { ifCounterDiscontinuityTime }
--       STATUS  current
--       DESCRIPTION
--               "A collection of objects providing information
--               specific to interface counter discontinuities."
--       ::= { ifGroups 13 }

   -- Deprecated Definitions - Objects


   --
   --    The Interface Test Table
   --
   -- This group of objects is optional.  However, a media-specific
   -- MIB may make implementation of this group mandatory.
   --
   -- This table replaces the ifExtnsTestTable
   --

--   ifTestTable   OBJECT-TYPE
--       SYNTAX      SEQUENCE OF IfTestEntry
--       MAX-ACCESS  not-accessible
--       STATUS      deprecated
--       DESCRIPTION
--               "This table contains one entry per interface.  It
--               defines objects which allow a network manager to
--               instruct an agent to test an interface for various
--               faults.  Tests for an interface are defined in the
--               media-specific MIB for that interface.  After invoking
--               a test, the object ifTestResult can be read to
--               determine the outcome.  If an agent can not perform
--               the test, ifTestResult is set to so indicate.  The
--               object ifTestCode can be used to provide further
--               test-specific or interface-specific (or even
--               enterprise-specific) information concerning the
--               outcome of the test.  Only one test can be in progress
--               on each interface at any one time.  If one test is in
--               progress when another test is invoked, the second test
--               is rejected.  Some agents may reject a test when a
--               prior test is active on another interface.
--
--               Before starting a test, a manager-station must first
--               obtain 'ownership' of the entry in the ifTestTable for
--               the interface to be tested.  This is accomplished with
--               the ifTestId and ifTestStatus objects as follows:
--
--            try_again:
--                get (ifTestId, ifTestStatus)
--                while (ifTestStatus != notInUse)
--                    /*
--                     * Loop while a test is running or some other
--                     * manager is configuring a test.
--                     */
--                    short delay
--                    get (ifTestId, ifTestStatus)
--                }
--
--                /*
--                 * Is not being used right now 
						-- let's compete
--                 * to see who gets it.
--                 */
--                lock_value = ifTestId
--
--                if ( set(ifTestId = lock_value, ifTestStatus = inUse,
--                         ifTestOwner = 'my-IP-address') == FAILURE)
--                    /*
--                     * Another manager got the ifTestEntry 
								-- go
--                     * try again
--                     */
--                    goto try_again;
--
--                /*
--                 * I have the lock
--                 */
--                set up any test parameters.
--
--                /*
--                 * This starts the test
--                 */
--                set(ifTestType = test_to_run);
--
--                wait for test completion by polling ifTestResult
--
--                when test completes, agent sets ifTestResult
--                     agent also sets ifTestStatus = 'notInUse'
--
--                retrieve any additional test results, and ifTestId
--
--                if (ifTestId == lock_value+1) results are valid
--
--              A manager station first retrieves the value of the
--              appropriate ifTestId and ifTestStatus objects,
--              periodically repeating the retrieval if necessary,
--              until the value of ifTestStatus is 'notInUse'.  The
--              manager station then tries to set the same ifTestId
--              object to the value it just retrieved, the same
--              ifTestStatus object to 'inUse', and the corresponding
--              ifTestOwner object to a value indicating itself.  If
--              the set operation succeeds then the manager has
--              obtained ownership of the ifTestEntry, and the value of
--              the ifTestId object is incremented by the agent (per
--              the semantics of TestAndIncr).  Failure of the set
--              operation indicates that some other manager has
--              obtained ownership of the ifTestEntry.
--
--              Once ownership is obtained, any test parameters can be
--              setup, and then the test is initiated by setting
--              ifTestType.  On completion of the test, the agent sets
--              ifTestStatus to 'notInUse'.  Once this occurs, the
--              manager can retrieve the results.  In the (rare) event
--              that the invocation of tests by two network managers
--              were to overlap, then there would be a possibility that
--              the first test's results might be overwritten by the
--              second test's results prior to the first results being
--              read.  This unlikely circumstance can be detected by a
--              network manager retrieving ifTestId at the same time as
--              retrieving the test results, and ensuring that the
--              results are for the desired request.
--
--              If ifTestType is not set within an abnormally long
--              period of time after ownership is obtained, the agent
--              should time-out the manager, and reset the value of the
--              ifTestStatus object back to 'notInUse'.  It is
--              suggested that this time-out period be 5 minutes.
--
--              In general, a management station must not retransmit a
--              request to invoke a test for which it does not receive
--              a response; instead, it properly inspects an agent's
--              MIB to determine if the invocation was successful.
--              Only if the invocation was unsuccessful, is the
--              invocation request retransmitted.
--
--              Some tests may require the interface to be taken off-
--              line in order to execute them, or may even require the
--              agent to reboot after completion of the test.  In these
--              circumstances, communication with the management
--              station invoking the test may be lost until after
--              completion of the test.  An agent is not required to
--              support such tests.  However, if such tests are
--              supported, then the agent should make every effort to
--              transmit a response to the request which invoked the
--              test prior to losing communication.  When the agent is
--              restored to normal service, the results of the test are
--              properly made available in the appropriate objects.
--              Note that this requires that the ifIndex value assigned
--              to an interface must be unchanged even if the test
--              causes a reboot.  An agent must reject any test for
--              which it cannot, perhaps due to resource constraints,
--              make available at least the minimum amount of
--              information after that test completes."
--       ::= { ifMIBObjects 3 }

--   ifTestEntry OBJECT-TYPE
--       SYNTAX       IfTestEntry
--       MAX-ACCESS   not-accessible
--       STATUS       deprecated
--       DESCRIPTION
--               "An entry containing objects for invoking tests on an
--               interface."
--       AUGMENTS  { ifEntry }
--       ::= { ifTestTable 1 }
--
--   IfTestEntry ::=
--       SEQUENCE {
--           ifTestId           TestAndIncr,
--           ifTestStatus       INTEGER,
--           ifTestType         AutonomousType,
--           ifTestResult       INTEGER,
--           ifTestCode         OBJECT IDENTIFIER,
--           ifTestOwner        OwnerString
--       }

--   ifTestId         OBJECT-TYPE
--       SYNTAX       TestAndIncr
--       MAX-ACCESS   read-write
--       STATUS       deprecated
--       DESCRIPTION
--               "This object identifies the current invocation of the
--               interface's test."
--       ::= { ifTestEntry 1 }

--   ifTestStatus     OBJECT-TYPE
--       SYNTAX       INTEGER { notInUse(1), inUse(2) }
--       MAX-ACCESS   read-write
--       STATUS       deprecated
--       DESCRIPTION
--               "This object indicates whether or not some manager
--               currently has the necessary 'ownership' required to
--               invoke a test on this interface.  A write to this
--               object is only successful when it changes its value
--               from 'notInUse(1)' to 'inUse(2)'.  After completion of
--               a test, the agent resets the value back to
--               'notInUse(1)'."
--       ::= { ifTestEntry 2 }

--   ifTestType       OBJECT-TYPE
--       SYNTAX       AutonomousType
--       MAX-ACCESS   read-write
--       STATUS       deprecated
--       DESCRIPTION
--               "A control variable used to start and stop operator-
--               initiated interface tests.  Most OBJECT IDENTIFIER
--               values assigned to tests are defined elsewhere, in
--               association with specific types of interface.
--               However, this document assigns a value for a full-
--               duplex loopback test, and defines the special meanings
--               of the subject identifier:
--
--                   noTest  OBJECT IDENTIFIER ::= { 0 0 }
--
--               When the value noTest is written to this object, no
--               action is taken unless a test is in progress, in which
--               case the test is aborted.  Writing any other value to
--               this object is only valid when no test is currently in
--               progress, in which case the indicated test is
--               initiated.
--
--               When read, this object always returns the most recent
--               value that ifTestType was set to.  If it has not been
--               set since the last initialization of the network
--               management subsystem on the agent, a value of noTest
--               is returned."
--       ::= { ifTestEntry 3 }

--   ifTestResult  OBJECT-TYPE
--       SYNTAX       INTEGER {
--                        none(1),          
					-- no test yet requested
--                        success(2),
--                        inProgress(3),
--                        notSupported(4),
--                        unAbleToRun(5),   
					-- due to state of system
--                        aborted(6),
--                        failed(7)
--                    }
--       MAX-ACCESS   read-only
--       STATUS       deprecated
--       DESCRIPTION
--               "This object contains the result of the most recently
--               requested test, or the value none(1) if no tests have
--               been requested since the last reset.  Note that this
--               facility provides no provision for saving the results
--               of one test when starting another, as could be
--               required if used by multiple managers concurrently."
--       ::= { ifTestEntry 4 }

--   ifTestCode  OBJECT-TYPE
--       SYNTAX       OBJECT IDENTIFIER
--       MAX-ACCESS   read-only
--       STATUS       deprecated
--       DESCRIPTION
--               "This object contains a code which contains more
--               specific information on the test result, for example
--               an error-code after a failed test.  Error codes and
--               other values this object may take are specific to the
--               type of interface and/or test.  The value may have the
--               semantics of either the AutonomousType or
--               InstancePointer textual conventions as defined in RFC
--               1903.  The identifier:
--
--                   testCodeUnknown  OBJECT IDENTIFIER ::= { 0 0 }
--
--               is defined for use if no additional result code is
--               available."
--       ::= { ifTestEntry 5 }

--   ifTestOwner      OBJECT-TYPE
--       SYNTAX       OwnerString
--       MAX-ACCESS   read-write
--       STATUS       deprecated
--       DESCRIPTION
--               "The entity which currently has the 'ownership'
--               required to invoke a test on this interface."
--       ::= { ifTestEntry 6 }

   -- Deprecated Definitions - Groups


--   ifGeneralGroup    OBJECT-GROUP
--       OBJECTS { ifDescr, ifType, ifSpeed, ifPhysAddress,
--                 ifAdminStatus, ifOperStatus, ifLastChange,
--                 ifLinkUpDownTrapEnable, ifConnectorPresent,
--                 ifHighSpeed, ifName }
--       STATUS  deprecated
--       DESCRIPTION
--               "A collection of objects deprecated in favour of
--               ifGeneralInformationGroup."
--       ::= { ifGroups 1 }


--   ifTestGroup    OBJECT-GROUP
--       OBJECTS { ifTestId, ifTestStatus, ifTestType,
--                 ifTestResult, ifTestCode, ifTestOwner }
--       STATUS  deprecated
--       DESCRIPTION
--               "A collection of objects providing the ability to
--               invoke tests on an interface."
--       ::= { ifGroups 8 }


--   ifStackGroup    OBJECT-GROUP
--       OBJECTS { ifStackStatus }
--       STATUS  deprecated
--       DESCRIPTION
--               "The previous collection of objects providing
--               information on the layering of MIB-II interfaces."
--       ::= { ifGroups 9 }


--   ifOldObjectsGroup    OBJECT-GROUP
--       OBJECTS { ifInNUcastPkts, ifOutNUcastPkts,
--                 ifOutQLen, ifSpecific }
--       STATUS  deprecated
--       DESCRIPTION
--               "The collection of objects deprecated from the
--               original MIB-II interfaces group."
--       ::= { ifGroups 12 }


   -- Deprecated Definitions - Compliance

--   ifCompliance MODULE-COMPLIANCE
--       STATUS  deprecated
--       DESCRIPTION
--               "The previous compliance statement for SNMPv2 entities
--               which have network interfaces."
--
--       MODULE  
		-- this module
--           MANDATORY-GROUPS { ifGeneralGroup, ifStackGroup }
--
--           GROUP       ifFixedLengthGroup
--           DESCRIPTION
--               "This group is mandatory for all network interfaces
--               which are character-oriented or transmit data in
--               fixed-length transmission units."
--
--           GROUP       ifHCFixedLengthGroup
--           DESCRIPTION
--               "This group is mandatory only for those network
--               interfaces which are character-oriented or transmit
--               data in fixed-length transmission units, and for which
--               the value of the corresponding instance of ifSpeed is
--               greater than 20,000,000 bits/second."
--
--           GROUP       ifPacketGroup
--           DESCRIPTION
--               "This group is mandatory for all network interfaces
--               which are packet-oriented."
--
--           GROUP       ifHCPacketGroup
--           DESCRIPTION
--               "This group is mandatory only for those network
--               interfaces which are packet-oriented and for which the
--               value of the corresponding instance of ifSpeed is
--               greater than 650,000,000 bits/second."
--
--           GROUP       ifTestGroup
--           DESCRIPTION
--               "This group is optional.  Media-specific MIBs which
--               require interface tests are strongly encouraged to use
--               this group for invoking tests and reporting results.
--               A medium specific MIB which has mandatory tests may
--               make implementation of this group mandatory."
--
--           GROUP       ifRcvAddressGroup
--           DESCRIPTION
--               "The applicability of this group MUST be defined by
--               the media-specific MIBs.  Media-specific MIBs must
--               define the exact meaning, use, and semantics of the
--               addresses in this group."
--
--           OBJECT      ifLinkUpDownTrapEnable
--           MIN-ACCESS  read-only
--           DESCRIPTION
--               "Write access is not required."

--           OBJECT      ifPromiscuousMode
--           MIN-ACCESS  read-only
--           DESCRIPTION
--               "Write access is not required."

--           OBJECT      ifStackStatus
--           SYNTAX      INTEGER { active(1) } 
						-- subset of RowStatus
--           MIN-ACCESS  read-only
--           DESCRIPTION
--               "Write access is not required, and only one of the six
--               enumerated values for the RowStatus textual convention
--               need be supported, specifically: active(1)."
--           OBJECT       ifAdminStatus
--           SYNTAX       INTEGER { up(1), down(2) }
--           MIN-ACCESS   read-only
--           DESCRIPTION
--               "Write access is not required, nor is support for the
--               value testing(3)."
--       ::= { ifCompliances 1 }


   END
   SNMP-FRAMEWORK-MIB DEFINITIONS ::= BEGIN

   IMPORTS
       MODULE-IDENTITY, 
--       OBJECT-TYPE,
--       OBJECT-IDENTITY,
       snmpModules                           FROM SNMPv2-SMI
       TEXTUAL-CONVENTION                    FROM SNMPv2-TC;
--       MODULE-COMPLIANCE, OBJECT-GROUP       FROM SNMPv2-CONF;

   snmpFrameworkMIB MODULE-IDENTITY
       LAST-UPDATED "9711200000Z"            -- 20 November 1997
       ORGANIZATION "SNMPv3 Working Group"
       CONTACT-INFO "WG-email:   snmpv3@tis.com
                     Subscribe:  majordomo@tis.com
                                 In message body:  subscribe snmpv3

                     Chair:      Russ Mundy
                                 Trusted Information Systems
                     postal:     3060 Washington Rd
                                 Glenwood MD 21738
                                 USA
                     email:      mundy@tis.com
                     phone:      +1 301-854-6889

                     Co-editor   Dave Harrington
                                 Cabletron Systems, Inc.
                     postal:     Post Office Box 5005
                                 Mail Stop: Durham
                                 35 Industrial Way
                                 Rochester, NH 03867-5005
                                 USA
                     email:      dbh@ctron.com
                     phone:      +1 603-337-7357

                     Co-editor   Randy Presuhn
                                 BMC Software, Inc.
                     postal:     1190 Saratoga Avenue
                                 Suite 130
                                 San Jose, CA 95129
                                 USA
                     email:      rpresuhn@bmc.com
                     phone:      +1 408-556-0720

                     Co-editor:  Bert Wijnen
                                 IBM T.J. Watson Research
                     postal:     Schagen 33
                                 3461 GL Linschoten
                                 Netherlands
                     email:      wijnen@vnet.ibm.com
                     phone:      +31 348-432-794
                    "
       DESCRIPTION  "The SNMP Management Architecture MIB"
       ::= { snmpModules 2 }

   -- Textual Conventions used in the SNMP Management Architecture ***

   SnmpEngineID ::= TEXTUAL-CONVENTION
       STATUS       current
       DESCRIPTION "An SNMP engine's administratively-unique identifier.

                    The value for this object may not be all zeros or
                    all 'ff'H or the empty (zero length) string.

                    The initial value for this object may be configured
                    via an operator console entry or via an algorithmic
                    function.  In the latter case, the following
                    example algorithm is recommended.

                    In cases where there are multiple engines on the
                    same system, the use of this algorithm is NOT
                    appropriate, as it would result in all of those
                    engines ending up with the same ID value.

                    1) The very first bit is used to indicate how the
                       rest of the data is composed.

                       0 - as defined by enterprise using former methods
                           that existed before SNMPv3. See item 2 below.

                       1 - as defined by this architecture, see item 3
                           below.

                       Note that this allows existing uses of the
                       engineID (also known as AgentID [RFC1910]) to
                       co-exist with any new uses.

                    2) The snmpEngineID has a length of 12 octets.

                       The first four octets are set to the binary
                       equivalent of the agent's SNMP management
                       private enterprise number as assigned by the
                       Internet Assigned Numbers Authority (IANA).
                       For example, if Acme Networks has been assigned
                       { enterprises 696 }, the first four octets would
                       be assigned '000002b8'H.

                       The remaining eight octets are determined via
                       one or more enterprise-specific methods. Such
                       methods must be designed so as to maximize the
                       possibility that the value of this object will
                       be unique in the agent's administrative domain.
                       For example, it may be the IP address of the SNMP
                       entity, or the MAC address of one of the
                       interfaces, with each address suitably padded
                       with random octets.  If multiple methods are
                       defined, then it is recommended that the first
                       octet indicate the method being used and the
                       remaining octets be a function of the method.

                    3) The length of the octet strings varies.

                       The first four octets are set to the binary
                       equivalent of the agent's SNMP management
                       private enterprise number as assigned by the
                       Internet Assigned Numbers Authority (IANA).
                       For example, if Acme Networks has been assigned
                       { enterprises 696 }, the first four octets would
                       be assigned '000002b8'H.

                       The very first bit is set to 1. For example, the
                       above value for Acme Networks now changes to be
                       '800002b8'H.

                       The fifth octet indicates how the rest (6th and
                       following octets) are formatted. The values for
                       the fifth octet are:

                         0     - reserved, unused.

                         1     - IPv4 address (4 octets)
                                 lowest non-special IP address

                         2     - IPv6 address (16 octets)
                                 lowest non-special IP address

                         3     - MAC address (6 octets)
                                 lowest IEEE MAC address, canonical
                                 order

                         4     - Text, administratively assigned
                                 Maximum remaining length 27

                         5     - Octets, administratively assigned
                                 Maximum remaining length 27

                         6-127 - reserved, unused

                       127-255 - as defined by the enterprise
                                 Maximum remaining length 27
                   "
       SYNTAX       OCTET STRING (SIZE(1..32))

   SnmpSecurityModel ::= TEXTUAL-CONVENTION
       STATUS       current
       DESCRIPTION "An identifier that uniquely identifies a
                    securityModel of the Security Subsystem within the
                    SNMP Management Architecture.

                    The values for securityModel are allocated as
                    follows:

                    - The zero value is reserved.
                    - Values between 1 and 255, inclusive, are reserved
                      for standards-track Security Models and are
                      managed by the Internet Assigned Numbers Authority
                      (IANA).
                    - Values greater than 255 are allocated to
                      enterprise-specific Security Models.  An
                      enterprise-specific securityModel value is defined
                      to be:

                      enterpriseID * 256 + security model within
                      enterprise

                      For example, the fourth Security Model defined by
                      the enterprise whose enterpriseID is 1 would be
                      260.

                    This scheme for allocation of securityModel
                    values allows for a maximum of 255 standards-
                    based Security Models, and for a maximum of
                    255 Security Models per enterprise.

                    It is believed that the assignment of new
                    securityModel values will be rare in practice
                    because the larger the number of simultaneously
                    utilized Security Models, the larger the
                    chance that interoperability will suffer.
                    Consequently, it is believed that such a range
                    will be sufficient.  In the unlikely event that
                    the standards committee finds this number to be
                    insufficient over time, an enterprise number
                    can be allocated to obtain an additional 255
                    possible values.

                    Note that the most significant bit must be zero;
                    hence, there are 23 bits allocated for various
                    organizations to design and define non-standard
                    securityModels.  This limits the ability to
                    define new proprietary implementations of Security
                    Models to the first 8,388,608 enterprises.

                    It is worthwhile to note that, in its encoded
                    form, the securityModel value will normally
                    require only a single byte since, in practice,
                    the leftmost bits will be zero for most messages
                    and sign extension is suppressed by the encoding
                    rules.

                    As of this writing, there are several values
                    of securityModel defined for use with SNMP or
                    reserved for use with supporting MIB objects.
                    They are as follows:

                        0  reserved for 'any'
                        1  reserved for SNMPv1
                        2  reserved for SNMPv2c
                        3  User-Based Security Model (USM)
                   "
       SYNTAX       INTEGER(0..2147483647)

   SnmpMessageProcessingModel ::= TEXTUAL-CONVENTION
       STATUS       current
       DESCRIPTION "An identifier that uniquely identifies a Message
                    Processing Model of the Message Processing
                    Subsystem within a SNMP Management Architecture.

                    The values for messageProcessingModel are
                    allocated as follows:

                    - Values between 0 and 255, inclusive, are
                      reserved for standards-track Message Processing
                      Models and are managed by the Internet Assigned
                      Numbers Authority (IANA).
                    - Values greater than 255 are allocated to
                      enterprise-specific Message Processing Models.
                      An enterprise messageProcessingModel value is
                      defined to be:
                      enterpriseID * 256 +
                           messageProcessingModel within enterprise

                      For example, the fourth Message Processing Model
                      defined by the enterprise whose enterpriseID
                      is 1 would be 260.

                    This scheme for allocation of securityModel
                    values allows for a maximum of 255 standards-
                    based Message Processing Models, and for a
                    maximum of 255 Message Processing Models per
                    enterprise.

                    It is believed that the assignment of new
                    messageProcessingModel values will be rare
                    in practice because the larger the number of
                    simultaneously utilized Message Processing Models,
                    the larger the chance that interoperability
                    will suffer. It is believed that such a range
                    will be sufficient.  In the unlikely event that
                    the standards committee finds this number to be
                    insufficient over time, an enterprise number
                    can be allocated to obtain an additional 256
                    possible values.

                    Note that the most significant bit must be zero;
                    hence, there are 23 bits allocated for various
                    organizations to design and define non-standard
                    messageProcessingModels.  This limits the ability
                    to define new proprietary implementations of
                    Message Processing Models to the first 8,388,608
                    enterprises.

                    It is worthwhile to note that, in its encoded
                    form, the securityModel value will normally
                    require only a single byte since, in practice,
                    the leftmost bits will be zero for most messages
                    and sign extension is suppressed by the encoding
                    rules.

                    As of this writing, there are several values of
                    messageProcessingModel defined for use with SNMP.
                    They are as follows:

                        0  reserved for SNMPv1
                        1  reserved for SNMPv2c
                        2  reserved for SNMPv2u and SNMPv2*
                        3  reserved for SNMPv3
                   "
       SYNTAX       INTEGER(0..2147483647)

   SnmpSecurityLevel ::= TEXTUAL-CONVENTION
       STATUS       current
       DESCRIPTION "A Level of Security at which SNMP messages can be
                    sent or with which operations are being processed;
                    in particular, one of:

                      noAuthNoPriv - without authentication and
                                     without privacy,
                      authNoPriv   - with authentication but
                                     without privacy,
                      authPriv     - with authentication and
                                     with privacy.

                    These three values are ordered such that
                    noAuthNoPriv is less than authNoPriv and
                    authNoPriv is less than authPriv.
                   "
       SYNTAX       INTEGER { noAuthNoPriv(1),
                              authNoPriv(2),
                              authPriv(3)
                            }

   SnmpAdminString ::= TEXTUAL-CONVENTION
       DISPLAY-HINT "255a"
       STATUS       current
       DESCRIPTION "An octet string containing administrative
                    information, preferably in human-readable form.

                    To facilitate internationalization, this
                    information is represented using the ISO/IEC
                    IS 10646-1 character set, encoded as an octet
                    string using the UTF-8 transformation format
                    described in [RFC2044].

                    Since additional code points are added by
                    amendments to the 10646 standard from time
                    to time, implementations must be prepared to
                    encounter any code point from 0x00000000 to
                    0x7fffffff.

                    The use of control codes should be avoided.

                    When it is necessary to represent a newline,
                    the control code sequence CR LF should be used.
                    The use of leading or trailing white space should
                    be avoided.

                    For code points not directly supported by user
                    interface hardware or software, an alternative
                    means of entry and display, such as hexadecimal,
                    may be provided.

                    For information encoded in 7-bit US-ASCII,
                    the UTF-8 encoding is identical to the
                    US-ASCII encoding.

                    Note that when this TC is used for an object that
                    is used or envisioned to be used as an index, then
                    a SIZE restriction must be specified so that the
                    number of sub-identifiers for any object instance
                    does not exceed the limit of 128, as defined by
                    [RFC1905].
                   "
       SYNTAX       OCTET STRING (SIZE (0..255))


   -- Administrative assignments ***************************************

--   snmpFrameworkAdmin
--       OBJECT IDENTIFIER ::= { snmpFrameworkMIB 1 }
--   snmpFrameworkMIBObjects
--       OBJECT IDENTIFIER ::= { snmpFrameworkMIB 2 }
--   snmpFrameworkMIBConformance
--       OBJECT IDENTIFIER ::= { snmpFrameworkMIB 3 }

--   the snmpEngine Group ********************************************

--   snmpEngine OBJECT IDENTIFIER ::= { snmpFrameworkMIBObjects 1 }

--   snmpEngineID     OBJECT-TYPE
--       SYNTAX       SnmpEngineID
--       MAX-ACCESS   read-only
--       STATUS       current
--       DESCRIPTION "An SNMP engine's administratively-unique identifier.
--                   "
--       ::= { snmpEngine 1 }

--   snmpEngineBoots  OBJECT-TYPE
--       SYNTAX       INTEGER (1..2147483647)
--       MAX-ACCESS   read-only
--       STATUS       current
--       DESCRIPTION "The number of times that the SNMP engine has
--                    (re-)initialized itself since its initial
--                    configuration.
--                   "
--       ::= { snmpEngine 2 }

--   snmpEngineTime   OBJECT-TYPE
--       SYNTAX       INTEGER (0..2147483647)
--       MAX-ACCESS   read-only
--       STATUS       current
--       DESCRIPTION "The number of seconds since the SNMP engine last
--                    incremented the snmpEngineBoots object.
--                   "
--       ::= { snmpEngine 3 }

--   snmpEngineMaxMessageSize OBJECT-TYPE
--       SYNTAX       INTEGER (484..2147483647)
--       MAX-ACCESS   read-only
--       STATUS       current
--       DESCRIPTION "The maximum length in octets of an SNMP message
--                    which this SNMP engine can send or receive and
--                    process, determined as the minimum of the maximum
--                    message size values supported among all of the
--                    transports available to and supported by the engine.
--                   "
--      ::= { snmpEngine 4 }


   -- Registration Points for Authentication and Privacy Protocols **

--   snmpAuthProtocols OBJECT-IDENTITY
--       STATUS        current
--       DESCRIPTION  "Registration point for standards-track
--                     authentication protocols used in SNMP Management
--                     Frameworks.
--                    "
--       ::= { snmpFrameworkAdmin 1 }

--   snmpPrivProtocols OBJECT-IDENTITY
--       STATUS        current
--       DESCRIPTION  "Registration point for standards-track privacy
--                     protocols used in SNMP Management Frameworks.
--                    "
--       ::= { snmpFrameworkAdmin 2 }

   -- Conformance information ******************************************

--   snmpFrameworkMIBCompliances
--                  OBJECT IDENTIFIER ::= {snmpFrameworkMIBConformance 1}

--   snmpFrameworkMIBGroups
--                  OBJECT IDENTIFIER ::= {snmpFrameworkMIBConformance 2}

   -- compliance statements

--   snmpFrameworkMIBCompliance MODULE-COMPLIANCE
--       STATUS       current
--       DESCRIPTION "The compliance statement for SNMP engines which
--                    implement the SNMP Management Framework MIB.
--                   "
--       MODULE   
		 -- this module
--           MANDATORY-GROUPS { snmpEngineGroup }

--       ::= { snmpFrameworkMIBCompliances 1 }

   -- units of conformance

--   snmpEngineGroup OBJECT-GROUP
--       OBJECTS {
--                 snmpEngineID,
--                 snmpEngineBoots,
--                 snmpEngineTime,
--                 snmpEngineMaxMessageSize
--               }
--       STATUS       current
--       DESCRIPTION "A collection of objects for identifying and
--                    determining the configuration and current timeliness
--                    values of an SNMP engine.
--                   "
--       ::= { snmpFrameworkMIBGroups 1 }

   END
     PerfHist-TC-MIB DEFINITIONS ::= BEGIN

     IMPORTS
        MODULE-IDENTITY,
        Gauge32, mib-2
            FROM SNMPv2-SMI
        TEXTUAL-CONVENTION
            FROM SNMPv2-TC;

     perfHistTCMIB MODULE-IDENTITY
          LAST-UPDATED "9811071100Z"
          ORGANIZATION "IETF AToMMIB and TrunkMIB WGs"
          CONTACT-INFO
                       "Kaj Tesink
              Postal:  Bellcore
                       331 Newman Springs Road
                       Red Bank, NJ 07701
                       USA
              Tel:     +1 732 758 5254
              Fax:     +1 732 758 2269
              E-mail:  kaj@bellcore.com"
          DESCRIPTION
           "This MIB Module provides Textual Conventions
             to be used by systems supporting 15 minute
             based performance history counts."
          ::= { mib-2 58 }

     -- The Textual Conventions defined below are organized
     -- alphabetically

     -- Use of these TCs assumes the following:
     -- 0  The agent supports 15 minute based history
     --    counters.
     -- 0  The agent is capable of keeping a history of n
     --    intervals of 15 minute performance data. The
     --    value of n is defined by the specific MIB
     --    module but shall be 0 < n =< 96.
     -- 0  The agent may optionally support performance
     --    data aggregating the history intervals.
     -- 0  The agent will keep separate tables for the
     --    current interval, the history intervals, and
     --    the total aggregates.
     -- 0  The agent will keep the following objects.
     --    If performance data is kept for multiple instances
     --    of a measured entity, then
     --    these objects are applied to each instance of
     --    the measured entity (e.g., interfaces).
     --


     -- xyzTimeElapsed OBJECT-TYPE
     --       SYNTAX  INTEGER (0..899)
     --       MAX-ACCESS  read-only
     --       STATUS  current
     --       DESCRIPTION
     --       "The number of seconds that have elapsed since
     --       the beginning of the current measurement period.
     --       If, for some reason, such as an adjustment in the
     --       system's time-of-day clock, the current interval
     --       exceeds the maximum value, the agent will return
     --       the maximum value."
     --       ::= { xxx }

     -- xyzValidIntervals OBJECT-TYPE
     --       SYNTAX  INTEGER (0..<n>)
     --       MAX-ACCESS  read-only
     --       STATUS  current
     --       DESCRIPTION
     --       "The number of previous near end intervals
     --       for which data was collected.
     --          [ The overall constraint on <n> is 1 =< n =< 96; ]
     --          [ Define any additional constraints on <n> here. ]
     --       The value will be <n> unless the measurement was
     --       (re-)started within the last (<n>*15) minutes, in which
     --       case the value will be the number of complete 15
     --       minute intervals for which the agent has at least
     --       some data. In certain cases (e.g., in the case
     --       where the agent is a proxy) it is possible that some
     --       intervals are unavailable.  In this case, this
     --       interval is the maximum interval number for
     --       which data is available."
     --       ::= { xxx }

     -- xyzInvalidIntervals OBJECT-TYPE
     --     SYNTAX  INTEGER (0..<n>)
     --     MAX-ACCESS  read-only
     --     STATUS  current
     --     DESCRIPTION
     --       "The number of intervals in the range from
     --        0 to xyzValidIntervals for which no
     --        data is available. This object will typically
     --        be zero except in cases where the data for some
     --        intervals are not available (e.g., in proxy
     --        situations)."
     --       ::= { xxx }

     PerfCurrentCount ::= TEXTUAL-CONVENTION
           STATUS  current
           DESCRIPTION
              "A counter associated with a
               performance measurement in a current 15
               minute measurement interval. The value
               of this counter starts from zero and is
               increased when associated events occur,
               until the end of the 15 minute interval.
               At that time the value of the counter is
               stored in the first 15 minute history
               interval, and the CurrentCount is
               restarted at zero. In the
               case where the agent has no valid data
               available for the current interval the
               corresponding object instance is not
               available and upon a retrieval request
               a corresponding error message shall be
               returned to indicate that this instance
               does not exist (for example, a noSuchName
               error for SNMPv1 and a noSuchInstance for
               SNMPv2 GET operation)."
            SYNTAX  Gauge32

     PerfIntervalCount ::= TEXTUAL-CONVENTION
           STATUS  current
           DESCRIPTION
              "A counter associated with a
               performance measurement in a previous
               15 minute measurement interval. In the
               case where the agent has no valid data
               available for a particular interval the
               corresponding object instance is not
               available and upon a retrieval request
               a corresponding error message shall be
               returned to indicate that this instance
               does not exist (for example, a noSuchName
               error for SNMPv1 and a noSuchInstance for
               SNMPv2 GET operation).
               In a system supporting
               a history of n intervals with
               IntervalCount(1) and IntervalCount(n) the
               most and least recent intervals
               respectively, the following applies at
               the end of a 15 minute interval:
               - discard the value of IntervalCount(n)
               - the value of IntervalCount(i) becomes that
                 of IntervalCount(i-1) for n >= i > 1
               - the value of IntervalCount(1) becomes that
                 of CurrentCount
               - the TotalCount, if supported, is adjusted."
            SYNTAX  Gauge32

    PerfTotalCount ::= TEXTUAL-CONVENTION
          STATUS  current
          DESCRIPTION
              "A counter associated with a
               performance measurements aggregating the
               previous valid 15 minute measurement
               intervals. (Intervals for which no valid
               data was available are not counted)"
            SYNTAX  Gauge32

     END
ZX-IMA-MIB DEFINITIONS ::= BEGIN

IMPORTS
           MODULE-IDENTITY, OBJECT-TYPE, Integer32, Counter32, Gauge32,
           NOTIFICATION-TYPE, enterprises
              FROM SNMPv2-SMI
           MODULE-COMPLIANCE, OBJECT-GROUP, NOTIFICATION-GROUP
              FROM SNMPv2-CONF
           TEXTUAL-CONVENTION, DateAndTime, RowStatus
              FROM SNMPv2-TC
           InterfaceIndex, InterfaceIndexOrZero, ifIndex
              FROM IF-MIB;
              
zxImaMib MODULE-IDENTITY
           LAST-UPDATED "9902111830Z"
           ORGANIZATION "The ATM Forum"
           CONTACT-INFO
              "ATM Forum
              World Headquarters
              2570 West El Camino Real
              Suite 304
              Mountain View, CA 94040-1313
              USA
              Phone: +1 415 949 6700
              Fax: +1 415 949 6705
              email: info@ atmforum. com"
           DESCRIPTION
              "The MIB module for managing ATM Forum Inverse Multiplexing
              for ATM (IMA) interfaces."
           REVISION          "9902111830Z"
           DESCRIPTION
              "Updated and repaired version of the IMA-MIB released with the
              IMA v1.1 specification (af-phy-0086.001)."
           REVISION          "9701092245Z"
           DESCRIPTION
              "Initial incomplete version of the IMA-MIB as published in the
              IMA v1.0 specification (af-phy-0086.000)."
           ::= { zxAdsl 2 }

zte OBJECT IDENTIFIER ::= { enterprises 3902 }
zxAdsl OBJECT IDENTIFIER ::= { zte 1004 }

zxImaSysMib OBJECT IDENTIFIER ::= { zxImaMib 1 }
zxImaGroupMib OBJECT IDENTIFIER ::= { zxImaMib 2 }
zxImaLinkMib OBJECT IDENTIFIER ::= { zxImaMib 3 }

--Sys subTree
zxImaSysMibTraps OBJECT IDENTIFIER ::= { zxImaSysMib 1 }
zxImaSysMibTrapPrefix OBJECT IDENTIFIER ::= { zxImaSysMibTraps 0 }

zxImaSysMibObjects OBJECT IDENTIFIER ::= { zxImaSysMib 2 }
zxImaSysMibConformance OBJECT IDENTIFIER ::= { zxImaSysMib 3 }
zxImaSysMibGroups OBJECT IDENTIFIER ::= { zxImaSysMibConformance 1 }
zxImaSysMibCompliances OBJECT IDENTIFIER ::= { zxImaSysMibConformance 2 }

--Group subTree
zxImaGroupMibObjects OBJECT IDENTIFIER ::= { zxImaGroupMib 1 }

zxImaGroupMibConformance OBJECT IDENTIFIER ::= { zxImaGroupMib 2 }
zxImaGroupMibGroups OBJECT IDENTIFIER ::= { zxImaGroupMibConformance 1 }
zxImaGroupMibCompliances OBJECT IDENTIFIER ::= { zxImaGroupMibConformance 2 }

--Link  subTree
zxImaLinkMibObjects OBJECT IDENTIFIER ::= { zxImaLinkMib 1 }

zxImaLinkMibConformance OBJECT IDENTIFIER ::= { zxImaLinkMib 2 }
zxImaLinkMibGroups OBJECT IDENTIFIER ::= { zxImaLinkMibConformance 1 }
zxImaLinkMibCompliances OBJECT IDENTIFIER ::= { zxImaLinkMibConformance 2 }



--Textual conventions
MilliSeconds ::= TEXTUAL-CONVENTION
           STATUS           current
           DESCRIPTION
              "Time in milliseconds"
           SYNTAX           Integer32

ImaGroupState ::= TEXTUAL-CONVENTION
           STATUS           current
           DESCRIPTION
              "State of the IMA group."
           REFERENCE
              "ATM Forum IMA v1.1, Section 10.2.1 on page 55"
           SYNTAX            INTEGER {
              notConfigured( 1),
              startUp( 2),
              startUpAck( 3),
              configAbortUnsupportedM( 4),
              configAbortIncompatibleSymmetry( 5),
              configAbortOther( 6),
              insufficientLinks( 7),
              blocked( 8),
              operational( 9),
              configAbortUnsupportedImaVersion( 10) }

ImaGroupFailureStatus ::= TEXTUAL-CONVENTION
           STATUS           current
           DESCRIPTION
              "Failure reason of an IMA group."
           REFERENCE
              "ATM Forum IMA v1.1, Section 10.2.1, page 55"
           SYNTAX            INTEGER {
              noFailure( 1), --unit is up
              startUpNe( 2),
              startUpFe( 3),
              invalidMValueNe( 4),
              invalidMValueFe( 5),
              failedAssymetricNe( 6),
              failedAssymetricFe( 7),
              insufficientLinksNe( 8),
              insufficientLinksFe( 9),
              blockedNe( 10),
              blockedFe( 11),
              otherFailure( 12),
              invalidImaVersionNe( 13),
              invalidImaVersionFe( 14) }

ImaAlarmStatus ::= TEXTUAL-CONVENTION
           STATUS           current
           DESCRIPTION
              "A qualification of the IMA trap which indicates if the
              condition causing the trap has been detected (declared)
              or is no longer present (cleared)."
           SYNTAX            INTEGER {
              cleared( 1),
              declared( 2) }

ImaAlarmType ::= TEXTUAL-CONVENTION
           STATUS           current
           DESCRIPTION
              "An identification of the event that caused the generation
              of the IMA trap."
           REFERENCE
              "ATM Forum IMA v1.1, Section 12.2.3 on page 79"
           SYNTAX            INTEGER {
              imaAlarmLinkLif( 1),
              imaAlarmLinkLods( 2),
              imaAlarmLinkRfi( 3),
              imaAlarmLinkTxMisConnect( 4),
              imaAlarmLinkRxMisConnect( 5),
              imaAlarmLinkTxFault( 6),
              imaAlarmLinkRxFault( 7),
              imaAlarmLinkTxUnusableFe( 8),
              imaAlarmLinkRxUnusableFe( 9),
              imaAlarmGroupStartupFe( 10),
              imaAlarmGroupCfgAbort( 11),
              imaAlarmGroupCfgAbortFe( 12),
              imaAlarmGroupInsuffLinks( 13),
              imaAlarmGroupInsuffLinksFe( 14),
              imaAlarmGroupBlockedFe( 15),
              imaAlarmGroupTimingSynch( 16) }

ImaGroupTxClkMode ::= TEXTUAL-CONVENTION
           STATUS           current
           DESCRIPTION
              "Indicate the transmit clock mode of the IMA group.
              There are two possible modes: the Common Transmit
              Clock (CTC) and the Independent Transmit Clock (ITC).
              The CTC mode corresponds to the case when the transmit clock
              of all IMA links are derived from the same source.    The ITC
              configuration corresponds to the case where there is at least
              one IMA link whose transmit clock is derived from a source
              different than at least another link transmit clock."
           REFERENCE
              "ATM Forum IMA v1.1, Section 7 on page 38"
           SYNTAX            INTEGER {
              ctc( 1),
              itc( 2) }

ImaGroupSymmetry ::= TEXTUAL-CONVENTION
           STATUS           current
           DESCRIPTION
              "The group symmetry mode adjusted during the group start-up."
           REFERENCE
              "ATM Forum IMA v1.1, Section 5.2.2.7 on page 35"
           SYNTAX            INTEGER {
              symmetricOperation( 1),
              asymmetricOperation( 2),
              asymmetricConfiguration( 3) }

ImaFrameLength ::= TEXTUAL-CONVENTION
           STATUS           current
           DESCRIPTION
              "Length of the IMA frames."
           REFERENCE
              "ATM Forum IMA v1.1, Section 5.2.2.4.2 on page 34"
           SYNTAX            INTEGER {
              m32( 32),
              m64( 64),
              m128( 128),
              m256( 256) }

ImaLinkState ::= TEXTUAL-CONVENTION
           STATUS           current
           DESCRIPTION
              "State of a link belonging to an IMA group."
           REFERENCE
              "ATM Forum IMA v1.1, Section 10.1.2 on page 48"
           SYNTAX            INTEGER {
              notInGroup( 1),
              unusableNoGivenReason( 2),
              unusableFault( 3),
              unusableMisconnected( 4),
              unusableInhibited( 5),
              unusableFailed( 6),
              usable( 7),
              active( 8) }

ImaLinkFailureStatus ::= TEXTUAL-CONVENTION
           STATUS           current
           DESCRIPTION
              "Local failure status of a link belonging to an IMA group."
           REFERENCE
              "ATM Forum IMA v1.1, Section 10.1.2 on page 48"
           SYNTAX            INTEGER {
              noFailure( 1),
              imaLinkFailure( 2),
              lifFailure( 3),
              lodsFailure( 4),
              misConnected( 5),
              blocked( 6),
              fault( 7),
              farEndTxLinkUnusable( 8),
              farEndRxLinkUnusable( 9) }

ImaTestProcStatus ::= TEXTUAL-CONVENTION
           STATUS           current
           DESCRIPTION
              "States of the Test Pattern Procedure."
           REFERENCE
              "ATM Forum IMA v1.1, Section 13 on page 81"
           SYNTAX            INTEGER {
              disabled( 1),
              operating( 2),
              linkFail( 3) }

-- liqx add start
imaAlarmStatus OBJECT-TYPE
           SYNTAX           ImaAlarmStatus
           MAX-ACCESS    accessible-for-notify
           STATUS           current
           DESCRIPTION
              "Status of the IMA alarm."
            ::= { zxImaSysMibObjects 1 }

imaAlarmType OBJECT-TYPE
           SYNTAX           ImaAlarmType
           MAX-ACCESS    accessible-for-notify
           STATUS           current
           DESCRIPTION
              "The Type of IMA alarm declared or cleared.    The value of
              ImaAlarmType identifies the type of alarm according to the
              definitions in the IMA specification."
           REFERENCE
              "ATM Forum IMA v1.1, Section 12.2.3 on page 79"
            ::= { zxImaSysMibObjects 2 }

imaFailureAlarm NOTIFICATION-TYPE
           OBJECTS {
              ifIndex,
              imaAlarmStatus,
              imaAlarmType }
           STATUS           current
           DESCRIPTION
              "The imaFailureAlarm provides a method for an agent implementing IMA
              to notify an NMS of an alarm condition."
           REFERENCE
              "ATM Forum IMA v1.1, Section 12.2.3 on page 79"
           ::= { zxImaSysMibTrapPrefix 1 }
-- liqx add end

--
--The IMA Group subtree
--
--The IMA Group subtree consists of the number of IMA groups and a
--table of IMA groups.    Each entry in the table of IMA groups contains
--information (configuration and status) specific to each group.
--
imaGroupNumber OBJECT-TYPE
           SYNTAX            INTEGER (0.. 2147483647)
           MAX-ACCESS    read-only
           STATUS           current
           DESCRIPTION
              "The number of IMA groups configured on this system."
           ::= { zxImaGroupMibObjects 1 }

imaGroupTable OBJECT-TYPE
           SYNTAX           SEQUENCE OF ImaGroupEntry
           MAX-ACCESS    not-accessible
           STATUS           current
           DESCRIPTION
              "The IMA Group Configuration table."
           ::= { zxImaGroupMibObjects 2 }

imaGroupEntry OBJECT-TYPE
           SYNTAX           ImaGroupEntry
           MAX-ACCESS    not-accessible
           STATUS           current
           DESCRIPTION
              "An entry in the IMA Group table."
           INDEX             { imaGroupIndex }
           ::= { imaGroupTable 1 }

ImaGroupEntry ::= SEQUENCE {
           imaGroupIndex                            INTEGER (1.. 2147483647),
           imaGroupRowStatus                     RowStatus,
           imaGroupIfIndex                        InterfaceIndex,
           imaGroupNeState                        ImaGroupState,
           imaGroupFeState                        ImaGroupState,
           imaGroupFailureStatus             ImaGroupFailureStatus,
           imaGroupSymmetry                      ImaGroupSymmetry,
           imaGroupMinNumTxLinks             INTEGER (1.. 32),
           imaGroupMinNumRxLinks             INTEGER (1.. 32),
           imaGroupNeTxClkMode                 ImaGroupTxClkMode,
           imaGroupFeTxClkMode                 ImaGroupTxClkMode,
           imaGroupTxTimingRefLink          InterfaceIndexOrZero,
           imaGroupRxTimingRefLink          InterfaceIndexOrZero,
           imaGroupLastChange                   DateAndTime,
           imaGroupTxImaId                        INTEGER (0.. 255),
           imaGroupRxImaId                        INTEGER (0.. 255),
           imaGroupTxFrameLength             ImaFrameLength,
           imaGroupRxFrameLength             ImaFrameLength,
           imaGroupDiffDelayMax               MilliSeconds,
           imaGroupLeastDelayLink            InterfaceIndexOrZero,
           imaGroupDiffDelayMaxObs          MilliSeconds,
           imaGroupAlphaValue                   INTEGER (1.. 2),
           imaGroupBetaValue                     INTEGER (1.. 5),
           imaGroupGammaValue                   INTEGER (1.. 5),
           imaGroupRunningSecs                 Gauge32,
           imaGroupUnavailSecs                 Counter32,
           imaGroupNeNumFailures             Counter32,
           imaGroupFeNumFailures             Counter32,
           imaGroupTxAvailCellRate          Gauge32,
           imaGroupRxAvailCellRate          Gauge32,
           imaGroupNumTxCfgLinks             Gauge32,
           imaGroupNumRxCfgLinks             Gauge32,
           imaGroupNumTxActLinks             Gauge32,
           imaGroupNumRxActLinks             Gauge32,
           imaGroupTestLinkIfIndex          InterfaceIndexOrZero,
           imaGroupTestPattern                 INTEGER (-1.. 255),
           imaGroupTestProcStatus            ImaTestProcStatus,
           imaGroupValidIntervals            INTEGER (0.. 96),
           imaGroupInvalidIntervals        INTEGER (0.. 96),
           imaGroupTimeElapsed                 INTEGER (0.. 899),
           imaGroupTxOamLabelValue          INTEGER ,
           imaGroupRxOamLabelValue          INTEGER (0.. 255),
           imaGroupCLKMode					 INTEGER}

imaGroupIndex OBJECT-TYPE
           SYNTAX            INTEGER (1.. 2147483647)
           MAX-ACCESS    not-accessible
           STATUS           current
           DESCRIPTION
              "A unique value for the IMA Group."
           ::= { imaGroupEntry 1 }

imaGroupRowStatus OBJECT-TYPE
           SYNTAX           RowStatus
           MAX-ACCESS    read-create
           STATUS           current
           DESCRIPTION
              "The imaGroupRowStatus object allows create, change, and delete
              operations on imaGroupTable entries.

              To create a new conceptual row (or instance) of the imaGroupTable,
              imaGroupRowStatus must be set to 'createAndWait' or 'createAndGo'.
              If settable, a successful set of the following objects must be
              performed before the imaGroupRowStatus of a new conceptual row can
              be set to 'active':

                  imaGroupMinNumTxLinks
                  imaGroupMinNumRxLinks
                  imaGroupTxImaId

              Some objects in the imaGroupTable control settings which can only
              be established or changed at group start-up time.    These objects
              include:

                  imaGroupTxImaId
                  imaGroupSymmetry
                  imaGroupTxFrameLength

              To change (modify) the imaGroupTxImaId object, the manager must
              first set imaGroupRowStatus to 'notInService'.    However, changes
              to the following two objects can be optionally allowed while the
              imaGroupRowStatus is 'active':

                  imaGroupSymmetry
                  imaGroupTxFrameLength

              These two objects can be changed when the imaGroupRowStatus is
              'active' in order to allow the far-end to recover from its
              Config-Aborted state without having to force the near-end Group
              State machine to go to the 'Not Configured' state.    Changing
              these object values after group start-up has completed causes a
              restart of the IMA group.

              Alternatively, as noted above, the agent implementation may
              simply require the imaGroupRowStatus object to first be set to
              'notInService' before allowing changes to either of these two
              objects.

              To remove (delete) an imaGroupTable entry from this table, set
              imaGroupRowStatus to 'destroy'.

              Setting the imaGroupRowStatus to 'active' has the effect of
              activating the Group Startup Procedure.    The Group Startup
              Procedure uses provisioned links that have imaLinkRowStatus set
              to 'active' and imaLinkGroupIndex set to the imaGroupIndex in
              this conceptual row.

              When the imaGroupRowStatus is not in 'active' state, the Group
              State machine is in its 'Not Configured' state."
           ::= { imaGroupEntry 2 }

imaGroupIfIndex OBJECT-TYPE
           SYNTAX           InterfaceIndex
           MAX-ACCESS    read-only
           STATUS           current
           DESCRIPTION
              "This object identifies the logical interface number ('ifIndex')
              assigned to this IMA group, and is used to identify corresponding
              rows in the Interfaces MIB.

              Note that re-initialization of the management agent may cause
              a client's 'imaGroupIfIndex' to change."
           ::= { imaGroupEntry 3 }

imaGroupNeState OBJECT-TYPE
           SYNTAX           ImaGroupState
           MAX-ACCESS    read-only
           STATUS           current
           DESCRIPTION
              "The current operational state of the near-end IMA Group State
              Machine."
           REFERENCE
              "ATM Forum IMA v1.1, Section 10.2.1 on page 55"
           ::= { imaGroupEntry 4 }

imaGroupFeState OBJECT-TYPE
           SYNTAX           ImaGroupState
           MAX-ACCESS    read-only
           STATUS           current
           DESCRIPTION
              "The current operational state of the far-end IMA Group State
              Machine."
           REFERENCE
              "ATM Forum IMA v1.1, Section 10.2.1 on page 55"
           ::= { imaGroupEntry 5 }

imaGroupFailureStatus OBJECT-TYPE
           SYNTAX           ImaGroupFailureStatus
           MAX-ACCESS    read-only
           STATUS           current
           DESCRIPTION
              "The current failure status of the IMA group (the reason why
              the GTSM is in the down state)."
           REFERENCE
              "ATM Forum IMA v1.1, Section 10.2.1 on page 55"
           ::= { imaGroupEntry 6 }

imaGroupSymmetry OBJECT-TYPE
           SYNTAX           ImaGroupSymmetry
           MAX-ACCESS    read-create
           STATUS           current
           DESCRIPTION
              "Symmetry of the IMA group."
           REFERENCE
              "ATM Forum IMA v1.1, Section 5.2.2.7 on page 35"
           DEFVAL { symmetricOperation }
           ::= { imaGroupEntry 7 }

imaGroupMinNumTxLinks OBJECT-TYPE
           SYNTAX            INTEGER (1.. 32)
           MAX-ACCESS    read-create
           STATUS           current
           DESCRIPTION
              "Minimum number of transmit links required to be Active for
              the IMA group to be in the Operational state."
           REFERENCE
              "ATM Forum IMA v1.1, Section 10.2.1.1 on page 55"
           ::= { imaGroupEntry 8 }

imaGroupMinNumRxLinks OBJECT-TYPE
           SYNTAX            INTEGER (1.. 32)
           MAX-ACCESS    read-create
           STATUS           current
           DESCRIPTION
              "Minimum number of receive links required to be Active for
              the IMA group to be in the Operational state."
           REFERENCE
              "ATM Forum IMA v1.1, Section 10.2.1.1 on page 55"
           ::= { imaGroupEntry 9 }

imaGroupNeTxClkMode OBJECT-TYPE
           SYNTAX           ImaGroupTxClkMode
           MAX-ACCESS    read-create
           STATUS           current
           DESCRIPTION
              "Transmit clocking mode used by the near-end IMA group."
           REFERENCE
              "ATM Forum IMA v1.1, Section 7 on page 38"
           DEFVAL { ctc }
           ::= { imaGroupEntry 10 }

imaGroupFeTxClkMode OBJECT-TYPE
           SYNTAX           ImaGroupTxClkMode
           MAX-ACCESS    read-only
           STATUS           current
           DESCRIPTION
              "Transmit clocking mode used by the far-end IMA group."
           REFERENCE
              "ATM Forum IMA v1.1, Section 7 on page 38"
           ::= { imaGroupEntry 11 }

imaGroupTxTimingRefLink OBJECT-TYPE
           SYNTAX           InterfaceIndexOrZero
           MAX-ACCESS    read-only
           STATUS           current
           DESCRIPTION
              "The ifIndex of the transmit timing reference link to be
              used by the near-end for IMA data cell clock recovery from
              the ATM layer.    The distinguished value of zero may be used
              if no link has been configured in the IMA group, or if the
              transmit timing reference link has not yet been selected."
           REFERENCE
              "ATM Forum IMA v1.1, Section 8.1.1 on page 41"
           ::= { imaGroupEntry 12 }

imaGroupRxTimingRefLink OBJECT-TYPE
           SYNTAX           InterfaceIndexOrZero
           MAX-ACCESS    read-only
           STATUS           current
           DESCRIPTION
              "The ifIndex of the receive timing reference link to be
              used by near-end for IMA data cell clock recovery toward
              the ATM layer.    The distinguished value of zero may be used
              if no link has been configured in the IMA group, or if the
              receive timing reference link has not yet been detected."
           REFERENCE
              "ATM Forum IMA v1.1, Section 8.1.1 on page 41"
           ::= { imaGroupEntry 13 }

imaGroupLastChange OBJECT-TYPE
           SYNTAX           DateAndTime
           MAX-ACCESS    read-only
           STATUS           current
           DESCRIPTION
              "The time-of-day the IMA group last changed operational
              state (i. e., value of imaGroupNeState changed)."
           ::= { imaGroupEntry 14 }

imaGroupTxImaId OBJECT-TYPE
           SYNTAX           INTEGER (0.. 255)
           MAX-ACCESS    read-only
           STATUS           current
           DESCRIPTION
              "The IMA ID currently in use by the near-end IMA function."
           REFERENCE
              "ATM Forum IMA v1.1, Section 5.2.2.6 on page 35"
           ::= { imaGroupEntry 15 }

imaGroupRxImaId OBJECT-TYPE
           SYNTAX           INTEGER (0.. 255)
           MAX-ACCESS    read-only
           STATUS           current
           DESCRIPTION
              "The IMA ID currently in use by the far-end IMA function."
           REFERENCE
              "ATM Forum IMA v1.1, Section 5.2.2.6 on page 35"
           ::= { imaGroupEntry 16 }

imaGroupTxFrameLength OBJECT-TYPE
           SYNTAX           ImaFrameLength
           MAX-ACCESS    read-create
           STATUS           current
           DESCRIPTION
              "The frame length to be used by the IMA group in the transmit
              direction.    Can only be set when the IMA group is startup."
           REFERENCE
              "ATM Forum IMA v1.1, Section 5.2.2.4.2 on page 34"
           DEFVAL { m128 }
           ::= { imaGroupEntry 17 }

imaGroupRxFrameLength OBJECT-TYPE
           SYNTAX           ImaFrameLength
           MAX-ACCESS    read-only
           STATUS           current
           DESCRIPTION
              "Value of IMA frame length as received from remote IMA function."
           REFERENCE
              "ATM Forum IMA v1.1, Section 5.2.2.4.2 on page 34"
           ::= { imaGroupEntry 18 }

imaGroupDiffDelayMax OBJECT-TYPE
           SYNTAX           MilliSeconds
           MAX-ACCESS    read-create
           STATUS           current
           DESCRIPTION
              "The maximum number of milliseconds of differential delay among
              the links that will be tolerated on this interface."
           REFERENCE
              "ATM Forum IMA v1.1, Section 9.2 on page 45"
           DEFVAL { 25 }
           ::= { imaGroupEntry 19 }

imaGroupLeastDelayLink OBJECT-TYPE
           SYNTAX           InterfaceIndexOrZero
           MAX-ACCESS    read-only
           STATUS           current
           DESCRIPTION
              "The ifIndex of the link configured in the IMA group which has
              the smallest link propagation delay.    The distinguished value of
              zero may be used if no link has been configured in the IMA group,
              or if the link with the smallest link propagation delay has not
              yet been determined."
           REFERENCE
              "ATM Forum IMA v1.1, Section 9.2 on page 45"
           ::= { imaGroupEntry 20 }

imaGroupDiffDelayMaxObs OBJECT-TYPE
           SYNTAX           MilliSeconds
           MAX-ACCESS    read-only
           STATUS           current
           DESCRIPTION
              "The latest maximum differential delay observed (in milliseconds)
              between the links having the least and most link propagation delay,
              among the receive links that are currently configured in the IMA
              group."
           REFERENCE
              "ATM Forum IMA v1.1, Section 9.2 on page 45"
           ::= { imaGroupEntry 21 }

imaGroupAlphaValue OBJECT-TYPE
           SYNTAX           INTEGER (1.. 2)
           MAX-ACCESS    read-create
           STATUS           current
           DESCRIPTION
              "This indicates the 'alpha' value used to specify the number
              of consecutive invalid ICP cells to be detected before moving
              to the IMA Hunt state from the IMA Sync state."
           REFERENCE
              "ATM Forum IMA v1.1, Section 11 on page 68"
           DEFVAL { 2 }
           ::= { imaGroupEntry 22 }

imaGroupBetaValue OBJECT-TYPE
           SYNTAX           INTEGER (1.. 5)
           MAX-ACCESS    read-create
           STATUS           current
           DESCRIPTION
              "This indicates the 'beta' value used to specify the number
              of consecutive errored ICP cells to be detected before moving
              to the IMA Hunt state from the IMA Sync state."
           REFERENCE
              "ATM Forum IMA v1.1, Section 11 on page 68"
           DEFVAL { 2 }
           ::= { imaGroupEntry 23 }

imaGroupGammaValue OBJECT-TYPE
           SYNTAX           INTEGER (1.. 5)
           MAX-ACCESS    read-create
           STATUS           current
           DESCRIPTION
              "This indicates the 'gamma' value used to specify the number
              of consecutive valid ICP cells to be detected before moving
              to the IMA Sync state from the IMA PreSync state."
           REFERENCE
              "ATM Forum IMA v1.1, Section 11 on page 68"
           DEFVAL { 1 }
           ::= { imaGroupEntry 24 }

imaGroupRunningSecs OBJECT-TYPE
           SYNTAX           Gauge32
           MAX-ACCESS    read-only
           STATUS           current
           DESCRIPTION
              "The amount of time (in seconds) since this IMA group has
              been in the Operational state."
           REFERENCE
              "ATM Forum IMA v1.1, Section 10.2.1 on page 55"
           ::= { imaGroupEntry 25 }

imaGroupUnavailSecs OBJECT-TYPE
           SYNTAX           Counter32
           MAX-ACCESS    read-only
           STATUS           current
           DESCRIPTION
              "Count of one second intervals where the IMA Group Traffic
              State Machine is Down."
           REFERENCE
              "ATM Forum IMA v1.1, Section 10.2.1 on page 55 and (R-136) in Section
              12.2.2.2 on page 77"
           ::= { imaGroupEntry 26 }

imaGroupNeNumFailures OBJECT-TYPE
           SYNTAX           Counter32
           MAX-ACCESS    read-only
           STATUS           current
           DESCRIPTION
              "The number of times a near-end group failure (Config-Aborted,
              Insufficient-Links) has been reported since power-up or reboot."
           REFERENCE
              "ATM Forum IMA v1.1, (R-137) in Section 12.2.2.2 on page 77"
           ::= { imaGroupEntry 27 }

imaGroupFeNumFailures OBJECT-TYPE
           SYNTAX           Counter32
           MAX-ACCESS    read-only
           STATUS           current
           DESCRIPTION
              "The number of times a far-end group failure (Config-Aborted-FE,
              Insufficient-Links-FE, Blocked-FE) has been reported since
              power-up or reboot.    This is an optional attribute."
           REFERENCE
              "ATM Forum IMA v1.1, (O-25) in Section 12.2.2.2 on page 77"
           ::= { imaGroupEntry 28 }

imaGroupTxAvailCellRate OBJECT-TYPE
           SYNTAX           Gauge32
           MAX-ACCESS    read-only
           STATUS           current
           DESCRIPTION
              "The current cell rate (truncated value in cells per second)
              provided by this IMA group in the transmit direction,
              considering all the transmit links in the Active state."
           ::= { imaGroupEntry 29 }

imaGroupRxAvailCellRate OBJECT-TYPE
           SYNTAX           Gauge32
           MAX-ACCESS    read-only
           STATUS           current
           DESCRIPTION
              "The current cell rate (truncated value in cells per second)
              provided by this IMA group in the receive direction,
              considering all the receive links in the Active state."
           ::= { imaGroupEntry 30 }

--imaGroupNumTxCfgLinks is used by a network operator to tell how many
--links are configured for transmit in the IMA group.

imaGroupNumTxCfgLinks OBJECT-TYPE
           SYNTAX           Gauge32
           MAX-ACCESS    read-only
           STATUS           current
           DESCRIPTION
              "The number of links that are configured to transmit in this IMA
              group. This attribute overwrites the value of the
              imaGroupNumRxActLinks attribute when the IMA group is configured
              in the Symmetrical Configuration group symmetry mode."
           ::= { imaGroupEntry 31 }

--imaGroupNumRxCfgLinks is used by a network operator to tell how many
--links are configured for receive in the IMA group.

imaGroupNumRxCfgLinks OBJECT-TYPE
           SYNTAX           Gauge32
           MAX-ACCESS    read-only
           STATUS           current
           DESCRIPTION
              "The number of links that are configured to receive in this IMA
              group. This attribute is overwritten by the value of the
              imaGroupNumTxActLinks attribute when the IMA group is configured
              in the Symmetrical Configuration group symmetry mode."
           ::= { imaGroupEntry 32 }

--imaGroupNumTxActLinks is used by a network operator to tell how many
--links which are configured for transmit are also Active.

imaGroupNumTxActLinks OBJECT-TYPE
           SYNTAX           Gauge32
           MAX-ACCESS    read-only
           STATUS           current
           DESCRIPTION
              "The number of links which are configured to transmit and are
              currently Active in this IMA group."
           ::= { imaGroupEntry 33 }

--imaGroupNumRxActLinks is used by a network operator to tell how many
--links which are configured for receive are also Active.

imaGroupNumRxActLinks OBJECT-TYPE
           SYNTAX           Gauge32
           MAX-ACCESS    read-only
           STATUS           current
           DESCRIPTION
              "The number of links which are configured to receive and are
              currently Active in this IMA group."
           ::= { imaGroupEntry 34 }

--
--Test Pattern Procedure control objects.    These objects are implemented
--if the IMA implements the Test Pattern Procedure.    In this case all
--test pattern procedure related objects must be implemented.    Specifically,
--these objects are:
--
--     imaGroupTestLinkIfIndex
--     imaGroupTestPattern
--     imaGroupTestProcStatus
--     imaLinkRxTestPattern
--     imaLinkTestProcStatus
--

imaGroupTestLinkIfIndex OBJECT-TYPE
           SYNTAX           InterfaceIndexOrZero
           MAX-ACCESS    read-create
           STATUS           current
           DESCRIPTION
              "This object is used to designate an interface as the test link
              for use in the Test Pattern Procedure.    The distinguished value of
              zero specifies that the implementation may choose the Test Link,
              in which case, the implementation may also choose the value of
              'imaGroupTestPattern'.    The value zero may also be used if no link
              has yet been added to the group.

              Note that this value is NOT the same as the Tx LID value, but
              instead either identifies the ifIndex value of the test link to be
              used by the Test Pattern Procedure (i. e., the link whose LID value
              is inserted in the Tx LID field of the transmitted ICP cells),
              or identifies that the implementation may choose the test link (if
              the value is zero)."
           REFERENCE
              "ATM Forum IMA v1.1, Section 13 on page 81"
           DEFVAL { 0 }
           ::= { imaGroupEntry 35 }

imaGroupTestPattern OBJECT-TYPE
           SYNTAX            INTEGER (-1.. 255)
           MAX-ACCESS    read-create
           STATUS           current
           DESCRIPTION
              "The value of this object is used to specify the Tx Test Pattern
              in an IMA group loopback operation.    A value in the range 0 to
              255 designates a specific pattern.    The distinguished value of
              -1 specifies that the implementation may choose the value.    In
              this case, the implementation may also choose the value of
              'imaGroupTestLinkIfIndex'.

              It is recommended that the specific value 255 not be used for
              testing, since by (R-137) the IMA interface is required to
              transmit 0xFF (i. e., 255) when the incoming test command is
              inactive or the test link is not detected, and thus it cannot
              be established for certain whether 255 was received due to an
              actual loopback operation or due to the normal operation of an
              IMA that is not performing (or else cannot perform) the test
              pattern procedure."
           REFERENCE
              "ATM Forum IMA v1.1, Section 13 on page 81"
           DEFVAL { -1 }
           ::= { imaGroupEntry 36 }

imaGroupTestProcStatus OBJECT-TYPE
           SYNTAX           ImaTestProcStatus
           MAX-ACCESS    read-create
           STATUS           current
           DESCRIPTION
              "This object is used to enable or disable the
              Test Pattern Procedure, and to note whether at least one
              link failed the test.

              The test is started by setting operating( 2) status.    If any
              link should fail the test, the IMA will set the status to
              linkFail( 3).    The linkFail( 3) state will persist until
              either the disabled( 1) state is set or until no instance
              of imaLinkTestProcStatus has the value linkFail( 3).

              Only the values disabled( 1) and operating( 2) may be written.
              Writing the operating( 2) value will not cause clearing of
              the linkFail( 3) state."
           REFERENCE
              "ATM Forum IMA v1.1, Section 13 on page 81"
           DEFVAL { disabled }
           ::= { imaGroupEntry 37 }

--
--Objects for use with the IMA Group Current Table, the IMA Group
--Interval Table, and the IMA Group Total Table.
--
--Implementation of these objects is optional, dependent on whether
--the tables mentioned above are implemented.
--

imaGroupValidIntervals OBJECT-TYPE
           SYNTAX            INTEGER (0.. 96)
           MAX-ACCESS    read-only
           STATUS           current
           DESCRIPTION
              "The number of previous 15 minute intervals for which valid data
              was collected.    The value will be 96 unless the IMA group table
              entry was created within the last 24 hours, in which case the value
              will be the number of complete 15 minute intervals since the IMA
              group table entry was created.    In the case where the agent is a
              proxy, it is possible that some intervals are unavailable.    In this
              case, this value is the maximum interval number for which valid
              data is available.    This attribute is only mandatory when the IMA
              Group Interval Statistics and/ or IMA Group Total Statistics objects
              are implemented."
           REFERENCE
              "ATM Forum IMA v1.1, (O-26) in Section 12.2.2.2 on page 77"
           ::= { imaGroupEntry 38 }

imaGroupInvalidIntervals OBJECT-TYPE
           SYNTAX            INTEGER (0.. 96)
           MAX-ACCESS    read-only
           STATUS           current
           DESCRIPTION
              "The number of intervals for which no valid data is available.
              This attribute is only mandatory when the IMA Group Interval
              Statistics and/ or IMA Group Total Statistics objects are
              implemented."
           REFERENCE
              "ATM Forum IMA v1.1, (O-26) in Section 12.2.2.2 on page 77"
           ::= { imaGroupEntry 39 }

imaGroupTimeElapsed OBJECT-TYPE
           SYNTAX           INTEGER (0.. 899)
           MAX-ACCESS    read-only
           STATUS           current
           DESCRIPTION
              "The number of seconds that have elapsed since the beginning of
              the current measurement period.    This attribute is only mandatory
              when the IMA Group Current Statistics are implemented."
           REFERENCE
              "ATM Forum IMA v1.1, (O-26) in Section 12.2.2.2 on page 77"
           ::= { imaGroupEntry 40 }

--
--Objects to report the IMA OAM Label values transmitted and
--received by the IMA group.
--

imaGroupTxOamLabelValue OBJECT-TYPE
           SYNTAX           INTEGER {
			imaGRPV10(1),
			imaGRPV11(3),
			other(255)
	}
           MAX-ACCESS    read-create
           STATUS           current
           DESCRIPTION
              "IMA OAM Label value transmitted by the NE IMA unit.
              value 3:IMA_GRP_V1_1   ;
              value 1:IMA_GRP_V1_0
              value else:Other :  ;"
           REFERENCE
              "ATM Forum IMA v1.1, Section 5.2.2.3 on page 32"
           ::= { imaGroupEntry 41 }

imaGroupRxOamLabelValue OBJECT-TYPE
           SYNTAX           INTEGER (0.. 255)
           MAX-ACCESS    read-only
           STATUS           current
           DESCRIPTION
              "IMA OAM Label value transmitted by the FE IMA unit.    The value 0
              likely means that the IMA unit has not received an OAM Label
              from the FE IMA unit at this time."
           REFERENCE
              "ATM Forum IMA v1.1, Section 5.2.2.3 on page 32"
           ::= { imaGroupEntry 42 }

imaGroupCLKMode   OBJECT-TYPE
	SYNTAX     INTEGER{
			master(0),
			 slave(1)
	}
	MAX-ACCESS read-create
	STATUS current
	DESCRIPTION
		"The clock mode of the Group "
::= { imaGroupEntry 43 }

--
--The IMA Group Current Statistics subtree
--
--the IMA Group Current Table.    This table contains various statistics
--collected by each IMA group for the current 15 minute interval.
--
--Implementation of IMA Group Current Table is optional.
--

imaGroupCurrentTable OBJECT-TYPE
           SYNTAX           SEQUENCE OF ImaGroupCurrentEntry
           MAX-ACCESS    not-accessible
           STATUS           current
           DESCRIPTION
              "The IMA Group Current table."
           ::= { zxImaGroupMibObjects 3 }

imaGroupCurrentEntry OBJECT-TYPE
           SYNTAX           ImaGroupCurrentEntry
           MAX-ACCESS    not-accessible
           STATUS           current
           DESCRIPTION
              "An entry in the IMA Group Current table."
           INDEX             { imaGroupIndex }
           ::= { imaGroupCurrentTable 1 }

ImaGroupCurrentEntry ::= SEQUENCE {
           imaGroupCurrentUnavailSecs          Gauge32,
           imaGroupCurrentNeNumFailures      Gauge32,
           imaGroupCurrentFeNumFailures      Gauge32 }

imaGroupCurrentUnavailSecs OBJECT-TYPE
           SYNTAX           Gauge32
           MAX-ACCESS    read-only
           STATUS           current
           DESCRIPTION
              "Count of one second intervals where the IMA Group Traffic
              State Machine is Down in the current 15 minutes interval."
           REFERENCE
              "ATM Forum IMA v1.1, Section 10.2.1 on page 55, (R-136) and
              (O-26) in Section 12.2.2.2 on page 77"
           ::= { imaGroupCurrentEntry 1 }

imaGroupCurrentNeNumFailures OBJECT-TYPE
           SYNTAX           Gauge32
           MAX-ACCESS    read-only
           STATUS           current
           DESCRIPTION
              "The number of times a near-end group failure (Config-Aborted,
              Insufficient-Links) has been reported in the current 15
              minutes interval."
           REFERENCE
              "ATM Forum IMA v1.1, (R-137) and (O-26) in Section 12.2.2.2
              on page 77"
           ::= { imaGroupCurrentEntry 2 }

imaGroupCurrentFeNumFailures OBJECT-TYPE
           SYNTAX           Gauge32
           MAX-ACCESS    read-only
           STATUS           current
           DESCRIPTION
              "The number of times a far-end group failure (Config-Aborted-FE,
              Insufficient-Links-FE, Blocked-FE) has been reported in the
              current 15 minutes interval.    This is an optional attribute."
           REFERENCE
              "ATM Forum IMA v1.1, (O-25) and (O-26) in Section 12.2.2.2
              on page 77"
           ::= { imaGroupCurrentEntry 3 }

--
--The IMA Group Interval Statistics subtree
--
--The IMA Group Interval Statistics subtree consists of a single table:
--the IMA Group Interval Table.    This table contains various statistics
--collected by each IMA group over the previous 24 hours of operation.
--The past 24 hours are broken into 96 completed 15 minute intervals.
--
--Implementation of IMA Group Interval Table is optional.
--

imaGroupIntervalTable OBJECT-TYPE
           SYNTAX           SEQUENCE OF ImaGroupIntervalEntry
           MAX-ACCESS    not-accessible
           STATUS           current
           DESCRIPTION
              "The IMA Group Interval table."
           ::= { zxImaGroupMibObjects 4 }

imaGroupIntervalEntry OBJECT-TYPE
           SYNTAX           ImaGroupIntervalEntry
           MAX-ACCESS    not-accessible
           STATUS           current
           DESCRIPTION
              "An entry in the IMA Group Interval table."
           INDEX             { imaGroupIndex, imaGroupIntervalNumber }
           ::= { imaGroupIntervalTable 1 }

ImaGroupIntervalEntry ::= SEQUENCE {
           imaGroupIntervalNumber                   INTEGER (1.. 96),
           imaGroupIntervalUnavailSecs          Gauge32,
           imaGroupIntervalNeNumFailures      Gauge32,
           imaGroupIntervalFeNumFailures      Gauge32 }

imaGroupIntervalNumber OBJECT-TYPE
           SYNTAX            INTEGER (1.. 96)
           MAX-ACCESS    not-accessible
           STATUS           current
           DESCRIPTION
              "A number between 1 and 96, where 1 is the most
                recently completed 15 minute interval and 96 is the least
                recently completed 15 minutes interval (assuming that all
                96 intervals are valid)."
           ::= { imaGroupIntervalEntry 1 }

imaGroupIntervalUnavailSecs OBJECT-TYPE
           SYNTAX           Gauge32
           MAX-ACCESS    read-only
           STATUS           current
           DESCRIPTION
              "Count of one second intervals where the IMA Group Traffic
              State Machine is Down in one of the previous 96, individual 15
              minute, intervals."
           REFERENCE
              "ATM Forum IMA v1.1, Section 10.2.1 on page 55, (R-136) and
              (O-26) in Section 12.2.2.2 on page 77"
           ::= { imaGroupIntervalEntry 2 }

imaGroupIntervalNeNumFailures OBJECT-TYPE
           SYNTAX           Gauge32
           MAX-ACCESS    read-only
           STATUS           current
           DESCRIPTION
              "The number of times a near-end group failure (Config-Aborted,
              Insufficient-Links) has been reported in one of the previous
              96, individual 15 minute, intervals."
           REFERENCE
              "ATM Forum IMA v1.1, (R-137) and (O-26) in Section 12.2.2.2
              on page 77"
           ::= { imaGroupIntervalEntry 3 }

imaGroupIntervalFeNumFailures OBJECT-TYPE
           SYNTAX           Gauge32
           MAX-ACCESS    read-only
           STATUS           current
           DESCRIPTION
              "The number of times a far-end group failure (Config-Aborted-FE,
              Insufficient-Links-FE, Blocked-FE) has been reported in one of
              the previous 96, individual 15 minute, intervals.    This is an
              optional attribute."
           REFERENCE
              "ATM Forum IMA v1.1, (O-25) and (O-26) in Section 12.2.2.2
              on page 77"
           ::= { imaGroupIntervalEntry 4 }

--
--The IMA Group Total Statistics subtree
--
--The IMA Group Total Statistics subtree consists of a single table:
--the IMA Group Total Table.    This table contains the cumulative sum
--of the various statistics collected by each IMA group for the 24 hour
--period preceding the current interval.
--
--Implementation of IMA Group Total Table is optional.
--

imaGroupTotalTable OBJECT-TYPE
           SYNTAX           SEQUENCE OF ImaGroupTotalEntry
           MAX-ACCESS    not-accessible
           STATUS           current
           DESCRIPTION
              "The IMA Group Total table."
           ::= { zxImaGroupMibObjects 5 }

imaGroupTotalEntry OBJECT-TYPE
           SYNTAX           ImaGroupTotalEntry
           MAX-ACCESS    not-accessible
           STATUS           current
           DESCRIPTION
              "An entry in the IMA Group Total table."
           INDEX             { imaGroupIndex }
           ::= { imaGroupTotalTable 1 }

ImaGroupTotalEntry ::= SEQUENCE {
           imaGroupTotalUnavailSecs          Gauge32,
           imaGroupTotalNeNumFailures      Gauge32,
           imaGroupTotalFeNumFailures      Gauge32 }

imaGroupTotalUnavailSecs OBJECT-TYPE
           SYNTAX           Gauge32
           MAX-ACCESS    read-only
           STATUS           current
           DESCRIPTION
              "Count of one second intervals where the IMA Group Traffic
              State Machine is Down in the previous 24 hour interval.
              Invalid 15 minute intervals count as 0."
           REFERENCE
              "ATM Forum IMA v1.1, Section 10.2.1 on page 55, (R-136) and
              (O-27) in Section 12.2.2.2 on page 77"
           ::= { imaGroupTotalEntry 1 }

imaGroupTotalNeNumFailures OBJECT-TYPE
           SYNTAX           Gauge32
           MAX-ACCESS    read-only
           STATUS           current
           DESCRIPTION
              "The number of times a near-end group failure (Config-Aborted,
              Insufficient-Links) has been reported in the previous 24 hour
              interval.    Invalid 15 minute intervals count as 0."
           REFERENCE
              "ATM Forum IMA v1.1, (R-137) and (O-27) in Section 12.2.2.2
              on page 77"
           ::= { imaGroupTotalEntry 2 }

imaGroupTotalFeNumFailures OBJECT-TYPE
           SYNTAX           Gauge32
           MAX-ACCESS    read-only
           STATUS           current
           DESCRIPTION
              "The number of times a far-end group failure (Config-Aborted-FE,
              Insufficient-Links-FE, Blocked-FE) has been reported in the
              previous 24 hour interval.    Invalid 15 minute intervals count
              as 0.    This is an optional attribute."
           REFERENCE
              "ATM Forum IMA v1.1, (O-25) and (O-27) in Section 12.2.2.2
              on page 77"
           ::= { imaGroupTotalEntry 3 }

--Conformance Information
--Compliance Statements

--Units of ImaSys Conformance
imaAlarmGroup OBJECT-GROUP
           OBJECTS {
              imaAlarmStatus,
              imaAlarmType }
           STATUS          current
           DESCRIPTION
              "Objects used in the imaFailureAlarm notification."
           ::= { zxImaSysMibGroups 1 }


imaNotificationsGroup NOTIFICATION-GROUP
           NOTIFICATIONS {
              imaFailureAlarm }
           STATUS          current
           DESCRIPTION
              "Notifications that must be implemented for IMA groups and links."
           ::= { zxImaSysMibGroups 2 }

 zxImaSysMibCompliance MODULE-COMPLIANCE
    STATUS  current
    DESCRIPTION
           "The compliance statement."
    MODULE  -- this module
    MANDATORY-GROUPS{
            imaAlarmGroup,
            imaNotificationsGroup
            }
        ::= { zxImaSysMibCompliances 1 }

        
--Units of ImaGroup Conformance
imaGroupNumberGroup OBJECT-GROUP
  OBJECTS{
     imaGroupNumber
  }
 STATUS  current
 DESCRIPTION 
       "imaGroupNumber group"
 ::={zxImaGroupMibGroups 1}

imaGroupGroup OBJECT-GROUP
           OBJECTS {
           imaGroupNumber ,
           imaGroupRowStatus ,
           imaGroupIfIndex ,
           imaGroupNeState ,
           imaGroupFeState ,
           imaGroupFailureStatus ,
           imaGroupSymmetry ,
           imaGroupMinNumTxLinks ,
           imaGroupMinNumRxLinks ,
           imaGroupNeTxClkMode ,
           imaGroupFeTxClkMode ,
           imaGroupTxTimingRefLink ,
           imaGroupRxTimingRefLink ,
           imaGroupLastChange ,
           imaGroupTxImaId ,
           imaGroupRxImaId ,
           imaGroupTxFrameLength ,
           imaGroupRxFrameLength ,
           imaGroupDiffDelayMax ,
           imaGroupLeastDelayLink ,
           imaGroupDiffDelayMaxObs ,
           imaGroupAlphaValue ,
           imaGroupBetaValue ,
           imaGroupGammaValue ,
           imaGroupRunningSecs ,
           imaGroupUnavailSecs ,
           imaGroupNeNumFailures ,
           imaGroupFeNumFailures ,
           imaGroupTxAvailCellRate ,
           imaGroupRxAvailCellRate ,
           imaGroupNumTxCfgLinks ,
           imaGroupNumRxCfgLinks ,
           imaGroupNumTxActLinks ,
           imaGroupNumRxActLinks ,
           imaGroupValidIntervals ,
           imaGroupInvalidIntervals ,
           imaGroupTimeElapsed ,
           imaGroupTxOamLabelValue ,
           imaGroupRxOamLabelValue }
           STATUS          current
           DESCRIPTION
              "A set of objects providing configuration and status information for
              an IMA group definition."
           ::= { zxImaGroupMibGroups 2 }

 imaGroupTestPatternGroup OBJECT-GROUP
           OBJECTS {
              imaGroupTestLinkIfIndex,
              imaGroupTestPattern,
              imaGroupTestProcStatus}
           STATUS          current
           DESCRIPTION
              "Objects in the imaGroupTable and imaLinkTable which control and
              report on the Test Pattern Procedure.    These objects must be
              implemented if the IMA Test Pattern Procedure is supported."
           ::= { zxImaGroupMibGroups 3 }


imaGroupIntervalGroup OBJECT-GROUP
           OBJECTS {
              imaGroupValidIntervals,
              imaGroupInvalidIntervals,
              imaGroupTimeElapsed,
              imaGroupCurrentUnavailSecs,
              imaGroupCurrentNeNumFailures,
              imaGroupCurrentFeNumFailures,
              imaGroupIntervalUnavailSecs,
              imaGroupIntervalNeNumFailures,
              imaGroupIntervalFeNumFailures,
              imaGroupTotalUnavailSecs,
              imaGroupTotalNeNumFailures,
              imaGroupTotalFeNumFailures }
           STATUS          current
           DESCRIPTION
              "Objects containing interval statistics for an IMA group."
           ::= { zxImaGroupMibGroups 4 }

zxImaGroupMibCompliance MODULE-COMPLIANCE
    STATUS  current
    DESCRIPTION
           "The compliance statement."
    MODULE  -- this module
    MANDATORY-GROUPS{
            imaGroupNumberGroup,
            imaGroupGroup,
            imaGroupTestPatternGroup,
            imaGroupIntervalGroup
            }
        ::= { zxImaGroupMibCompliances 1 }

--
--The IMA Link subtree
--
--The IMA Link subtree consists of a table of IMA links.    Each entry
--in the table contains status information about a link which is part
--of an IMA group, and also contains a configuration object to select
--to which IMA group the link belongs.
--

imaLinkTable OBJECT-TYPE
           SYNTAX           SEQUENCE OF ImaLinkEntry
           MAX-ACCESS    not-accessible
           STATUS           current
           DESCRIPTION
              "The IMA group Link Status and Configuration table."
           ::= { zxImaLinkMibObjects 1 }

imaLinkEntry OBJECT-TYPE
           SYNTAX           ImaLinkEntry
           MAX-ACCESS    not-accessible
           STATUS           current
           DESCRIPTION
              "An entry in the IMA Group Link table."
           INDEX             { imaLinkIfIndex }
           ::= { imaLinkTable 1 }

ImaLinkEntry ::= SEQUENCE {
           imaLinkIfIndex                          InterfaceIndex,
           imaLinkRowStatus                      RowStatus,
           imaLinkGroupIndex                     Integer32,
           imaLinkNeTxState                      ImaLinkState,
           imaLinkNeRxState                      ImaLinkState,
           imaLinkFeTxState                      ImaLinkState,
           imaLinkFeRxState                      ImaLinkState,
           imaLinkNeRxFailureStatus        ImaLinkFailureStatus,
           imaLinkFeRxFailureStatus        ImaLinkFailureStatus,
           imaLinkTxLid                              INTEGER (0.. 31),
           imaLinkRxLid                              INTEGER (0.. 31),
           imaLinkRelDelay                        MilliSeconds,
           imaLinkImaViolations               Counter32,
           imaLinkOifAnomalies                 Counter32,
           imaLinkNeSevErroredSecs          Counter32,
           imaLinkFeSevErroredSecs          Counter32,
           imaLinkNeUnavailSecs               Counter32,
           imaLinkFeUnavailSecs               Counter32,
           imaLinkNeTxUnusableSecs          Counter32,
           imaLinkNeRxUnusableSecs          Counter32,
           imaLinkFeTxUnusableSecs          Counter32,
           imaLinkFeRxUnusableSecs          Counter32,
           imaLinkNeTxNumFailures            Counter32,
           imaLinkNeRxNumFailures            Counter32,
           imaLinkFeTxNumFailures            Counter32,
           imaLinkFeRxNumFailures            Counter32,
           imaLinkTxStuffs                        Counter32,
           imaLinkRxStuffs                        Counter32,
           imaLinkRxTestPattern               INTEGER (0.. 255),
           imaLinkTestProcStatus             ImaTestProcStatus,
           imaLinkValidIntervals             INTEGER (0.. 96),
           imaLinkInvalidIntervals          INTEGER (0.. 96),
           imaLinkTimeElapsed                   INTEGER (0.. 899),
           imaLinkScramble						INTEGER }

imaLinkIfIndex OBJECT-TYPE
           SYNTAX           InterfaceIndex
           MAX-ACCESS    not-accessible
           STATUS           current
           DESCRIPTION
              "This corresponds to the 'ifIndex' of the MIB-II interface
              on which this link is established.    This object also
              corresponds to the logical number ('ifIndex') assigned to
              this IMA link."
           ::= { imaLinkEntry 1 }

imaLinkRowStatus OBJECT-TYPE
           SYNTAX           RowStatus
           MAX-ACCESS    read-create
           STATUS           current
           DESCRIPTION
              "The imaLinkRowStatus object allows create, change, and delete
              operations on imaLinkTable entries.

              To create a new conceptual row (or instance) of the imaLinkTable,
              imaLinkRowStatus must be set to 'createAndWait' or 'createAndGo'.
              A successful set of the imaLinkGroupIndex object must be performed
              before the imaLinkRowStatus of a new conceptual row can be set to
              'active'.

              To change (modify) the imaLinkGroupIndex in an imaLinkTable entry,
              the imaLinkRowStatus object must first be set to 'notInService'.
              Only then can this object in the conceptual row be modified.
              This is due to the fact that the imaLinkGroupIndex object provides
              the association between a physical IMA link and the IMA group to
              which it belongs, and setting the imaLinkGroupIndex object to a
              different value has the effect of changing the association between
              a physical IMA link and an IMA group.    To place the link 'in group',
              the imaLinkRowStatus object is set to 'active'.    While the row is
              not in 'active' state, both the Transmit and Receive IMA link state
              machines are in the 'Not In Group' state.

              To remove (delete) an imaLinkTable entry from this table, set
              this object to 'destroy'."
           ::= { imaLinkEntry 2 }

imaLinkGroupIndex OBJECT-TYPE
           SYNTAX           Integer32
           MAX-ACCESS    read-create
           STATUS           current
           DESCRIPTION
              "The value which identifies the IMA group (imaGroupIndex)
              of which this link is a member."
           ::= { imaLinkEntry 3 }

imaLinkNeTxState OBJECT-TYPE
           SYNTAX           ImaLinkState
           MAX-ACCESS    read-only
           STATUS           current
           DESCRIPTION
              "The current state of the near-end transmit link."
           REFERENCE
              "ATM Forum IMA v1.1, Section 10.1.2 on page 48"
           ::= { imaLinkEntry 4 }

imaLinkNeRxState OBJECT-TYPE
           SYNTAX           ImaLinkState
           MAX-ACCESS    read-only
           STATUS           current
           DESCRIPTION
              "The current state of the near-end receive link."
           REFERENCE
              "ATM Forum IMA v1.1, Section 10.1.2 on page 48"
           ::= { imaLinkEntry 5 }

imaLinkFeTxState OBJECT-TYPE
           SYNTAX           ImaLinkState
           MAX-ACCESS    read-only
           STATUS           current
           DESCRIPTION
              "The current state of the far-end transmit link as reported
              via ICP cells."
           REFERENCE
              "ATM Forum IMA v1.1, Section 10.1.2 on page 48"
           ::= { imaLinkEntry 6 }

imaLinkFeRxState OBJECT-TYPE
           SYNTAX           ImaLinkState
           MAX-ACCESS    read-only
           STATUS           current
           DESCRIPTION
              "The current state of the far-end receive link as reported
              via ICP cells."
           REFERENCE
              "ATM Forum IMA v1.1, Section 10.1.2 on page 48"
           ::= { imaLinkEntry 7 }

imaLinkNeRxFailureStatus OBJECT-TYPE
           SYNTAX           ImaLinkFailureStatus
           MAX-ACCESS    read-only
           STATUS           current
           DESCRIPTION
              "The current link failure status of the near-end receive link."
           REFERENCE
              "ATM Forum IMA v1.1, Section 10.1.2 on page 48"
           ::= { imaLinkEntry 8 }

imaLinkFeRxFailureStatus OBJECT-TYPE
           SYNTAX           ImaLinkFailureStatus
           MAX-ACCESS    read-only
           STATUS           current
           DESCRIPTION
              "The current link failure status of the far-end receive link
              as reported via ICP cells."
           REFERENCE
              "ATM Forum IMA v1.1, Section 10.1.2 on page 48"
           ::= { imaLinkEntry 9 }

imaLinkTxLid OBJECT-TYPE
           SYNTAX            INTEGER (0.. 31)
           MAX-ACCESS    read-only
           STATUS           current
           DESCRIPTION
              "The outgoing LID used currently on the link by the local end.
              This value has meaning only if the link belongs to an IMA group."
           REFERENCE
              "ATM Forum IMA v1.1, Section 5.2.2.1 on page 26"
           ::= { imaLinkEntry 10 }

imaLinkRxLid OBJECT-TYPE
           SYNTAX            INTEGER (0.. 31)
           MAX-ACCESS    read-only
           STATUS           current
           DESCRIPTION
              "The incoming LID used currently on the link by the remote
              end as reported via ICP cells.    This value has meaning only
              if the link belongs to an IMA group."
           REFERENCE
              "ATM Forum IMA v1.1, Section 5.2.2.1 on page 26"
           ::= { imaLinkEntry 11 }

imaLinkRelDelay OBJECT-TYPE
           SYNTAX           MilliSeconds
           MAX-ACCESS    read-only
           STATUS           current
           DESCRIPTION
              "The latest measured delay on this link relative to the link, in
              the same IMA group, with the least delay."
           REFERENCE
              "ATM Forum IMA v1.1, Section 9.2 on page 45"
           ::= { imaLinkEntry 12 }

imaLinkImaViolations OBJECT-TYPE
           SYNTAX           Counter32
           MAX-ACCESS    read-only
           STATUS           current
           DESCRIPTION
              "ICP violations: count of errored, invalid or missing ICP cells,
              except during SES-IMA or UAS-IMA conditions."
           REFERENCE
              "ATM Forum IMA v1.1, (R-125) in Section 12.2.2.2 on page 77"
           ::= { imaLinkEntry 13 }

imaLinkOifAnomalies OBJECT-TYPE
           SYNTAX           Counter32
           MAX-ACCESS    read-only
           STATUS           current
           DESCRIPTION
              "The number of OIF anomalies, except during SES-IMA or UAS-IMA
              conditions, at the near-end.    This is an optional attribute."
           REFERENCE
              "ATM Forum IMA v1.1, (O-20) in Section 12.2.2.2 on page 77"
           ::= { imaLinkEntry 14 }

imaLinkNeSevErroredSecs OBJECT-TYPE
           SYNTAX           Counter32
           MAX-ACCESS    read-only
           STATUS           current
           DESCRIPTION
              "Count of one second intervals containing >= 30% of the ICP cells
              counted as IV-IMAs, or one or more link defects (e. g., LOS, OOF/ LOF,
              AIS, or LCD), LIF defects, or LODS defects, except during UAS-IMA
              condition."
           REFERENCE
              "ATM Forum IMA v1.1, (R-126) in Section 12.2.2.2 on page 77"
           ::= { imaLinkEntry 15 }

imaLinkFeSevErroredSecs OBJECT-TYPE
           SYNTAX           Counter32
           MAX-ACCESS    read-only
           STATUS           current
           DESCRIPTION
              "Count of one second intervals containing one or more RDI-IMA
              defects, except during UAS-IMA-FE condition."
           REFERENCE
              "ATM Forum IMA v1.1, (R-127) in Section 12.2.2.2 on page 77"
           ::= { imaLinkEntry 16 }

imaLinkNeUnavailSecs OBJECT-TYPE
           SYNTAX           Counter32
           MAX-ACCESS    read-only
           STATUS           current
           DESCRIPTION
              "Count of unavailable seconds at near-end: unavailability begins
              at the onset of 10 contiguous SES-IMA and ends at the onset
              of 10 contiguous seconds with no SES-IMA."
           REFERENCE
              "ATM Forum IMA v1.1, (R-128) in Section 12.2.2.2 on page 77"
           ::= { imaLinkEntry 17 }

imaLinkFeUnavailSecs OBJECT-TYPE
           SYNTAX           Counter32
           MAX-ACCESS    read-only
           STATUS           current
           DESCRIPTION
              "Count of unavailable seconds at far-end: unavailability begins
              at the onset of 10 contiguous SES-IMA-FE and ends at the onset of
              10 contiguous seconds with no SES-IMA-FE."
           REFERENCE
              "ATM Forum IMA v1.1, (R-129) in Section 12.2.2.2 on page 77"
           ::= { imaLinkEntry 18 }

imaLinkNeTxUnusableSecs OBJECT-TYPE
           SYNTAX           Counter32
           MAX-ACCESS    read-only
           STATUS           current
           DESCRIPTION
              "Tx Unusable seconds: count of Tx Unusable seconds at the near-end
              Tx LSM."
           REFERENCE
              "ATM Forum IMA v1.1, (R-130) in Section 12.2.2.2 on page 77"
           ::= { imaLinkEntry 19 }

imaLinkNeRxUnusableSecs OBJECT-TYPE
           SYNTAX           Counter32
           MAX-ACCESS    read-only
           STATUS           current
           DESCRIPTION
              "Rx Unusable seconds: count of Rx Unusable seconds at the near-end
              Rx LSM."
           REFERENCE
              "ATM Forum IMA v1.1, (R-131) in Section 12.2.2.2 on page 77"
           ::= { imaLinkEntry 20 }

imaLinkFeTxUnusableSecs OBJECT-TYPE
           SYNTAX           Counter32
           MAX-ACCESS    read-only
           STATUS           current
           DESCRIPTION
              "Tx Unusable seconds at far-end: count of seconds with Tx Unusable
              indications from the far-end Tx LSM."
           REFERENCE
              "ATM Forum IMA v1.1, (R-132) in Section 12.2.2.2 on page 77"
           ::= { imaLinkEntry 21 }

imaLinkFeRxUnusableSecs OBJECT-TYPE
           SYNTAX           Counter32
           MAX-ACCESS    read-only
           STATUS           current
           DESCRIPTION
              "Rx Unusable seconds at far-end: count of seconds with Rx Unusable
              indications from the far-end Rx LSM."
           REFERENCE
              "ATM Forum IMA v1.1, (R-133) in Section 12.2.2.2 on page 77"
           ::= { imaLinkEntry 22 }

imaLinkNeTxNumFailures OBJECT-TYPE
           SYNTAX           Counter32
           MAX-ACCESS    read-only
           STATUS           current
           DESCRIPTION
              "The number of times a near-end transmit failure alarm condition
              has been entered on this link (i. e., some form of implementation
              specific transmit fault)."
           REFERENCE
              "ATM Forum IMA v1.1, (R-134) in Section 12.2.2.2 on page 77"
           ::= { imaLinkEntry 23 }

imaLinkNeRxNumFailures OBJECT-TYPE
           SYNTAX           Counter32
           MAX-ACCESS    read-only
           STATUS           current
           DESCRIPTION
              "The number of times a near-end receive failure alarm condition
              has been entered on this link (i. e., LIF, LODS,
              RFI-IMA, Mis-Connected or some form of implementation specific receive
              fault)."
           REFERENCE
              "ATM Forum IMA v1.1, (R-135) in Section 12.2.2.2 on page 77"
           ::= { imaLinkEntry 24 }

imaLinkFeTxNumFailures OBJECT-TYPE
           SYNTAX           Counter32
           MAX-ACCESS    read-only
           STATUS           current
           DESCRIPTION
              "The number of times a far-end transmit failure alarm condition
              has been entered on this link (i. e., Tx-Unusable-FE).    This is an
              optional attribute."
           REFERENCE
              "ATM Forum IMA v1.1, (O-21) in Section 12.2.2.2 on page 77"
           ::= { imaLinkEntry 25 }

imaLinkFeRxNumFailures OBJECT-TYPE
           SYNTAX           Counter32
           MAX-ACCESS    read-only
           STATUS           current
           DESCRIPTION
              "The number of times a far-end receive failure alarm condition
              has been entered on this link (i. e., Rx-Unusable-FE).    This is an
              optional attribute."
           REFERENCE
              "ATM Forum IMA v1.1, (O-22) in Section 12.2.2.2 on page 77"
           ::= { imaLinkEntry 26 }

imaLinkTxStuffs OBJECT-TYPE
           SYNTAX           Counter32
           MAX-ACCESS    read-only
           STATUS           current
           DESCRIPTION
              "Count of stuff events inserted in the transmit direction.
              This is an optional attribute."
           REFERENCE
              "ATM Forum IMA v1.1, (O-23) in Section 12.2.2.2 on page 77"
           ::= { imaLinkEntry 27 }

imaLinkRxStuffs OBJECT-TYPE
           SYNTAX           Counter32
           MAX-ACCESS    read-only
           STATUS           current
           DESCRIPTION
              "Count of stuff events detected in the receive direction.
              This is an optional attribute."
           REFERENCE
              "ATM Forum IMA v1.1, (O-24) in Section 12.2.2.2 on page 77"
           ::= { imaLinkEntry 28 }

--
--Test Pattern Procedure control objects.    These objects are implemented
--if the IMA implements the Test Pattern Procedure.    In this case all
--test pattern procedure related objects must be implemented.    Specifically,
--these objects are:
--
--     imaGroupTestLinkIfIndex
--     imaGroupTestPattern
--     imaGroupTestProcStatus
--     imaLinkRxTestPattern
--     imaLinkTestProcStatus
--

imaLinkRxTestPattern OBJECT-TYPE
           SYNTAX           INTEGER (0.. 255)
           MAX-ACCESS    read-only
           STATUS           current
           DESCRIPTION
              "This object identifies the test pattern received in the
              ICP Cell (octet 17) on the link during the IMA Test Pattern
              Procedure.    This value may then be compared to the transmitted
              test pattern."
           ::= { imaLinkEntry 29 }

imaLinkTestProcStatus OBJECT-TYPE
           SYNTAX           ImaTestProcStatus
           MAX-ACCESS    read-only
           STATUS           current
           DESCRIPTION
              "This value indicates the current state of the Test Pattern
              Procedure.    If the value is disabled( 1), the test is not
              running.    A value of operating( 2) means the test is running
              and no error has been found on this interface.    A value of
              linkFail( 3) means an error has been detected on this link
              during the test.

              Once an error is detected, the linkFail( 3) value is latched until
              either this object is read or until the imaGroupTestProcStatus
              is moved to disabled( 1).    Once read, if the error no longer
              persists, a subsequent read will report the value operating( 2)."
           ::= { imaLinkEntry 30 }

--
--Objects for use with the IMA Link Current Table, the IMA Link
--Interval Table, and the IMA Link Total Table.
--
--Implementation of these objects is optional, dependent on whether
--the tables mentioned above are implemented.
--

imaLinkValidIntervals OBJECT-TYPE
           SYNTAX            INTEGER (0.. 96)
           MAX-ACCESS    read-only
           STATUS           current
           DESCRIPTION
              "The number of previous 15 minute intervals for which valid data
              was collected.    The value will be 96 unless the IMA group table
              entry was created within the last 24 hours, in which case the value
              will be the number of complete 15 minute intervals since the IMA
              group table entry was created.    In the case where the agent is a
              proxy, it is possible that some intervals are unavailable.    In this
              case, this value is the maximum interval number for which valid
              data is available.    This attribute is only mandatory when the IMA
              Link Interval Statistics and/ or IMA Link Total Statistics objects
              are implemented."
           REFERENCE
              "ATM Forum IMA v1.1, (O-26) in Section 12.2.2.2 on page 77"
           ::= { imaLinkEntry 31 }

imaLinkInvalidIntervals OBJECT-TYPE
           SYNTAX            INTEGER (0.. 96)
           MAX-ACCESS    read-only
           STATUS           current
           DESCRIPTION
              "The number of intervals for which no valid data is available.
              This attribute is only mandatory when the IMA Link Interval
              Statistics and/ or IMA Link Total Statistics objects are
              implemented."
           REFERENCE
              "ATM Forum IMA v1.1, (O-26) in Section 12.2.2.2
                on page 77"
           ::= { imaLinkEntry 32 }

imaLinkTimeElapsed OBJECT-TYPE
           SYNTAX           INTEGER (0.. 899)
           MAX-ACCESS    read-only
           STATUS           current
           DESCRIPTION
              "The number of seconds that have elapsed since the beginning of
              the current measurement period.    This attribute is only mandatory
              when the IMA Link Current Statistics are implemented."
           REFERENCE
              "ATM Forum IMA v1.1, (O-26) in Section 12.2.2.2
                on page 77"
           ::= { imaLinkEntry 33 }

imaLinkScramble OBJECT-TYPE
	SYNTAX        INTEGER{
			disable(0),
			 enable(1)
	}
	MAX-ACCESS read-create
	STATUS current
	DESCRIPTION
		"enable/disable the scramble status of the link"
::= { imaLinkEntry 34 }

--The IMA Link Current Statistics subtree
--
--The IMA Link Current Statistics subtree consists of a single table:
--the IMA Link Current Table.    This table contains various statistics
--collected by each IMA link for the current 15 minute interval.
--
--Implementation of IMA Link Current Table is optional.
--

imaLinkCurrentTable OBJECT-TYPE
           SYNTAX           SEQUENCE OF ImaLinkCurrentEntry
           MAX-ACCESS    not-accessible
           STATUS           current
           DESCRIPTION
              "The IMA Link Current table."
           ::= { zxImaLinkMibObjects 2 }

imaLinkCurrentEntry OBJECT-TYPE
           SYNTAX           ImaLinkCurrentEntry
           MAX-ACCESS    not-accessible
           STATUS           current
           DESCRIPTION
              "An entry in the IMA Link Current table."
           INDEX             { ifIndex }
           ::= { imaLinkCurrentTable 1 }

ImaLinkCurrentEntry ::= SEQUENCE {
           imaLinkCurrentImaViolations          Gauge32,
           imaLinkCurrentOifAnomalies            Gauge32,
           imaLinkCurrentNeSevErroredSecs    Gauge32,
           imaLinkCurrentFeSevErroredSecs    Gauge32,
           imaLinkCurrentNeUnavailSecs          Gauge32,
           imaLinkCurrentFeUnavailSecs          Gauge32,
           imaLinkCurrentNeTxUnusableSecs    Gauge32,
           imaLinkCurrentNeRxUnusableSecs    Gauge32,
           imaLinkCurrentFeTxUnusableSecs    Gauge32,
           imaLinkCurrentFeRxUnusableSecs    Gauge32,
           imaLinkCurrentNeTxNumFailures      Gauge32,
           imaLinkCurrentNeRxNumFailures      Gauge32,
           imaLinkCurrentFeTxNumFailures      Gauge32,
           imaLinkCurrentFeRxNumFailures      Gauge32,
           imaLinkCurrentTxStuffs                   Gauge32,
           imaLinkCurrentRxStuffs                   Gauge32 }

imaLinkCurrentImaViolations OBJECT-TYPE
           SYNTAX           Gauge32
           MAX-ACCESS    read-only
           STATUS           current
           DESCRIPTION
              "ICP violations: count of errored, invalid or missing ICP cells,
              except during SES-IMA or UAS-IMA conditions, in the current
              15 minute interval."
           REFERENCE
              "ATM Forum IMA v1.1, (R-125) and (O-26) in Section 12.2.2.2
              on page 77"
           ::= { imaLinkCurrentEntry 1 }

imaLinkCurrentOifAnomalies OBJECT-TYPE
           SYNTAX           Gauge32
           MAX-ACCESS    read-only
           STATUS           current
           DESCRIPTION
              "The number of OIF anomalies, except during SES-IMA or UAS-IMA
              conditions, at the near-end in the current 15 minute interval.
              This is an optional attribute."
           REFERENCE
              "ATM Forum IMA v1.1, (O-20) and (O-26) in Section 12.2.2.2
              on page 77"
           ::= { imaLinkCurrentEntry 2 }

imaLinkCurrentNeSevErroredSecs OBJECT-TYPE
           SYNTAX           Gauge32
           MAX-ACCESS    read-only
           STATUS           current
           DESCRIPTION
              "Count of one second intervals containing >= 30% of the ICP cells
              counted as IV-IMAs, or one or more link defects (e. g., LOS, OOF/ LOF,
              AIS, or LCD), LIF defects, or LODS defects, except during UAS-IMA
              condition, in the current 15 minute interval."
           REFERENCE
              "ATM Forum IMA v1.1, (R-126) and (O-26) in Section 12.2.2.2
              on page 77"
           ::= { imaLinkCurrentEntry 3 }

imaLinkCurrentFeSevErroredSecs OBJECT-TYPE
           SYNTAX           Gauge32
           MAX-ACCESS    read-only
           STATUS           current
           DESCRIPTION
              "Count of one second intervals containing one or more RDI-IMA
              defects, except during UAS-IMA-FE condition, in the current 15
              minute interval."
           REFERENCE
              "ATM Forum IMA v1.1, (R-127) and (O-26) in Section 12.2.2.2
              on page 77"
           ::= { imaLinkCurrentEntry 4 }

imaLinkCurrentNeUnavailSecs OBJECT-TYPE
           SYNTAX           Gauge32
           MAX-ACCESS    read-only
           STATUS           current
           DESCRIPTION
              "Count of unavailable seconds at near-end in the current 15 minute
              interval: unavailability begins at the onset of 10 contiguous
              SES-IMA and ends at the onset of 10 contiguous seconds with no
              SES-IMA."
           REFERENCE
              "ATM Forum IMA v1.1, (R-128) and (O-26) in Section 12.2.2.2
              on page 77"
           ::= { imaLinkCurrentEntry 5 }

imaLinkCurrentFeUnavailSecs OBJECT-TYPE
           SYNTAX           Gauge32
           MAX-ACCESS    read-only
           STATUS           current
           DESCRIPTION
              "Count of unavailable seconds at far-end in the current 15 minute
              interval: unavailability begins at the onset of 10 contiguous
              SES-IMA-FE and ends at the onset of 10 contiguous seconds with no
              SES-IMA-FE."
           REFERENCE
              "ATM Forum IMA v1.1, (R-129) and (O-26) in Section 12.2.2.2
              on page 77"
           ::= { imaLinkCurrentEntry 6 }

imaLinkCurrentNeTxUnusableSecs OBJECT-TYPE
           SYNTAX           Gauge32
           MAX-ACCESS    read-only
           STATUS           current
           DESCRIPTION
              "Tx Unusable seconds: count of Unusable seconds at the near-end
              Tx LSM in the current 15 minute interval."
           REFERENCE
              "ATM Forum IMA v1.1, (R-130) and (O-26) in Section 12.2.2.2
              on page 77"
           ::= { imaLinkCurrentEntry 7 }

imaLinkCurrentNeRxUnusableSecs OBJECT-TYPE
           SYNTAX           Gauge32
           MAX-ACCESS    read-only
           STATUS           current
           DESCRIPTION
              "Rx Unusable seconds: count of Unusable seconds at the near-end
              Rx LSM in the current 15 minute interval."
           REFERENCE
              "ATM Forum IMA v1.1, (R-131) and (O-26) in Section 12.2.2.2
              on page 77"
           ::= { imaLinkCurrentEntry 8 }

imaLinkCurrentFeTxUnusableSecs OBJECT-TYPE
           SYNTAX           Gauge32
           MAX-ACCESS    read-only
           STATUS           current
           DESCRIPTION
              "Tx Unusable seconds at far-end: count of seconds with Tx Unusable
              indications from the far-end Tx LSM in the current 15 minute
              interval."
           REFERENCE
              "ATM Forum IMA v1.1, (R-132) and (O-26) in Section 12.2.2.2
              on page 77"
           ::= { imaLinkCurrentEntry 9 }

imaLinkCurrentFeRxUnusableSecs OBJECT-TYPE
           SYNTAX           Gauge32
           MAX-ACCESS    read-only
           STATUS           current
           DESCRIPTION
              "Rx Unusable seconds at far-end: count of seconds with Rx Unusable
              indications from the far-end Rx LSM in the current 15 minute
              interval."
           REFERENCE
              "ATM Forum IMA v1.1, (R-133) and (O-26) in Section 12.2.2.2
              on page 77"
           ::= { imaLinkCurrentEntry 10 }

imaLinkCurrentNeTxNumFailures OBJECT-TYPE
           SYNTAX           Gauge32
           MAX-ACCESS    read-only
           STATUS           current
           DESCRIPTION
              "The number of times a near-end transmit failure alarm condition
              has been entered on this link (i. e., some form of implementation
              specific transmit fault) in the current 15 minute interval."
           REFERENCE
              "ATM Forum IMA v1.1, (R-134) and (O-26) in Section 12.2.2.2
              on page 77"
           ::= { imaLinkCurrentEntry 11 }

imaLinkCurrentNeRxNumFailures OBJECT-TYPE
           SYNTAX           Gauge32
           MAX-ACCESS    read-only
           STATUS           current
           DESCRIPTION
              "The number of times a near-end receive failure alarm condition
              has been entered on this link (i. e., LIF, LODS, RFI-IMA, Mis-Connected,
              or some form of implementation specific receive fault)
              in the current 15 minute interval."
           REFERENCE
              "ATM Forum IMA v1.1, (R-135) and (O-26) in Section 12.2.2.2
              on page 77"
           ::= { imaLinkCurrentEntry 12 }

imaLinkCurrentFeTxNumFailures OBJECT-TYPE
           SYNTAX           Gauge32
           MAX-ACCESS    read-only
           STATUS           current
           DESCRIPTION
              "The number of times a far-end transmit failure alarm condition
              has been entered on this link (i. e., Tx-Unusable-FE) in the
              current 15 minute interval.    This is an optional attribute."
           REFERENCE
              "ATM Forum IMA v1.1, (O-21) and (O-26) in Section 12.2.2.2
              on page 77"
           ::= { imaLinkCurrentEntry 13 }

imaLinkCurrentFeRxNumFailures OBJECT-TYPE
           SYNTAX           Gauge32
           MAX-ACCESS    read-only
           STATUS           current
           DESCRIPTION
              "The number of times a far-end receive failure alarm condition
              has been entered on this link (i. e., Rx-Unusable-FE) in the
              current 15 minute interval.    This is an optional attribute."
           REFERENCE
              "ATM Forum IMA v1.1, (O-22) and (O-26) in Section 12.2.2.2
              on page 77"
           ::= { imaLinkCurrentEntry 14 }

imaLinkCurrentTxStuffs OBJECT-TYPE
           SYNTAX           Gauge32
           MAX-ACCESS    read-only
           STATUS           current
           DESCRIPTION
              "Count of stuff events inserted in the transmit direction in
              the current 15 minute interval.    This is an optional attribute."
           REFERENCE
              "ATM Forum IMA v1.1, (O-23) and (O-26) in Section 12.2.2.2
              on page 77"
           ::= { imaLinkCurrentEntry 15 }

imaLinkCurrentRxStuffs OBJECT-TYPE
           SYNTAX           Gauge32
           MAX-ACCESS    read-only
           STATUS           current
           DESCRIPTION
              "Count of stuff events detected in the receive direction in
              the current 15 minute interval.    This is an optional attribute."
           REFERENCE
              "ATM Forum IMA v1.1, (O-24) and (O-26) in Section 12.2.2.2
              on page 77"
           ::= { imaLinkCurrentEntry 16 }

--
--The IMA Link Interval Statistics subtree
--
--The IMA Link Interval Statistics subtree consists of a single table:
--the IMA Link Interval Table.    This table contains various statistics
--collected by each IMA link over the previous 24 hours of operation.
--The past 24 hours are broken into 96 completed 15 minute intervals.
--
--Implementation of IMA Link Interval Table is optional.
--

imaLinkIntervalTable OBJECT-TYPE
           SYNTAX           SEQUENCE OF ImaLinkIntervalEntry
           MAX-ACCESS    not-accessible
           STATUS           current
           DESCRIPTION
              "The IMA Link Interval table."
           ::= { zxImaLinkMibObjects 3 }

imaLinkIntervalEntry OBJECT-TYPE
           SYNTAX           ImaLinkIntervalEntry
           MAX-ACCESS    not-accessible
           STATUS           current
           DESCRIPTION
              "An entry in the IMA Link Interval table."
           INDEX             { ifIndex, imaLinkIntervalNumber }
           ::= { imaLinkIntervalTable 1 }

ImaLinkIntervalEntry ::= SEQUENCE {
           imaLinkIntervalNumber                      INTEGER (1.. 96),
           imaLinkIntervalImaViolations          Gauge32,
           imaLinkIntervalOifAnomalies            Gauge32,
           imaLinkIntervalNeSevErroredSecs    Gauge32,
           imaLinkIntervalFeSevErroredSecs    Gauge32,
           imaLinkIntervalNeUnavailSecs          Gauge32,
           imaLinkIntervalFeUnavailSecs          Gauge32,
           imaLinkIntervalNeTxUnusableSecs    Gauge32,
           imaLinkIntervalNeRxUnusableSecs    Gauge32,
           imaLinkIntervalFeTxUnusableSecs    Gauge32,
           imaLinkIntervalFeRxUnusableSecs    Gauge32,
           imaLinkIntervalNeTxNumFailures      Gauge32,
           imaLinkIntervalNeRxNumFailures      Gauge32,
           imaLinkIntervalFeTxNumFailures      Gauge32,
           imaLinkIntervalFeRxNumFailures      Gauge32,
           imaLinkIntervalTxStuffs                   Gauge32,
           imaLinkIntervalRxStuffs                   Gauge32 }

imaLinkIntervalNumber OBJECT-TYPE
           SYNTAX            INTEGER (1.. 96)
           MAX-ACCESS    not-accessible
           STATUS           current
           DESCRIPTION
              "A number between 1 and 96, where 1 is the most
                recently completed 15 minute interval and 96 is the least
                recently completed 15 minutes interval (assuming that all
                96 intervals are valid)."
           ::= { imaLinkIntervalEntry 1 }

imaLinkIntervalImaViolations OBJECT-TYPE
           SYNTAX           Gauge32
           MAX-ACCESS    read-only
           STATUS           current
           DESCRIPTION
              "ICP violations: count of errored, invalid or missing ICP cells,
              except during SES-IMA or UAS-IMA conditions, in one of the
              previous 96, individual 15 minute, intervals."
           REFERENCE
              "ATM Forum IMA v1.1, (R-125) and (O-26) in Section 12.2.2.2
              on page 77"
           ::= { imaLinkIntervalEntry 2 }

imaLinkIntervalOifAnomalies OBJECT-TYPE
           SYNTAX           Gauge32
           MAX-ACCESS    read-only
           STATUS           current
           DESCRIPTION
              "The number of OIF anomalies, except during SES-IMA or UAS-IMA
              conditions, at the near-end in one of the previous 96, individual
              15 minute, intervals.    This is an optional attribute."
           REFERENCE
              "ATM Forum IMA v1.1, (O-20) and (O-26) in Section 12.2.2.2
              on page 77"
           ::= { imaLinkIntervalEntry 3 }

imaLinkIntervalNeSevErroredSecs OBJECT-TYPE
           SYNTAX           Gauge32
           MAX-ACCESS    read-only
           STATUS           current
           DESCRIPTION
              "Count of one second intervals containing >= 30% of the ICP cells
              counted as IV-IMAs, or one or more link defects (e. g., LOS, OOF/ LOF,
              AIS, or LCD), LIF defects, or LODS defects, except during UAS-IMA
              condition, in one of the previous 96, individual 15 minute,
              intervals."
           REFERENCE
              "ATM Forum IMA v1.1, (R-126) and (O-26) in Section 12.2.2.2
              on page 77"
           ::= { imaLinkIntervalEntry 4 }

imaLinkIntervalFeSevErroredSecs OBJECT-TYPE
           SYNTAX           Gauge32
           MAX-ACCESS    read-only
           STATUS           current
           DESCRIPTION
              "Count of one second intervals containing one or more RDI-IMA
              defects, except during UAS-IMA-FE condition, in one of the previous
              96, individual 15 minute, intervals."
           REFERENCE
              "ATM Forum IMA v1.1, (R-127) and (O-26) in Section 12.2.2.2
              on page 77"
           ::= { imaLinkIntervalEntry 5 }

imaLinkIntervalNeUnavailSecs OBJECT-TYPE
           SYNTAX           Gauge32
           MAX-ACCESS    read-only
           STATUS           current
           DESCRIPTION
              "Count of unavailable seconds at near-end in one of the previous
              96, individual 15 minute, intervals: unavailability begins at the
              onset of 10 contiguous SES-IMA and ends at the onset of 10
              contiguous seconds with no SES-IMA."
           REFERENCE
              "ATM Forum IMA v1.1, (R-128) and (O-26) in Section 12.2.2.2
              on page 77"
           ::= { imaLinkIntervalEntry 6 }

imaLinkIntervalFeUnavailSecs OBJECT-TYPE
           SYNTAX           Gauge32
           MAX-ACCESS    read-only
           STATUS           current
           DESCRIPTION
              "Count of unavailable seconds at far-end in one of the previous
              96, individual 15 minute, intervals: unavailability begins at the
              onset of 10 contiguous SES-IMA-FE and ends at the onset of 10
              contiguous seconds with no SES-IMA-FE."
           REFERENCE
              "ATM Forum IMA v1.1, (R-129) and (O-26) in Section 12.2.2.2
              on page 77"
           ::= { imaLinkIntervalEntry 7 }

imaLinkIntervalNeTxUnusableSecs OBJECT-TYPE
           SYNTAX           Gauge32
           MAX-ACCESS    read-only
           STATUS           current
           DESCRIPTION
              "Tx Unusable seconds: count of Unusable seconds at the near-end
              Tx LSM in one of the previous 96, individual 15 minute, intervals."
           REFERENCE
              "ATM Forum IMA v1.1, (R-130) and (O-26) in Section 12.2.2.2
              on page 77"
           ::= { imaLinkIntervalEntry 8 }

imaLinkIntervalNeRxUnusableSecs OBJECT-TYPE
           SYNTAX           Gauge32
           MAX-ACCESS    read-only
           STATUS           current
           DESCRIPTION
              "Rx Unusable seconds: count of Unusable seconds at the near-end
              Rx LSM in one of the previous 96, individual 15 minute, intervals."
           REFERENCE
              "ATM Forum IMA v1.1, (R-131) and (O-26) in Section 12.2.2.2
              on page 77"
           ::= { imaLinkIntervalEntry 9 }

imaLinkIntervalFeTxUnusableSecs OBJECT-TYPE
           SYNTAX           Gauge32
           MAX-ACCESS    read-only
           STATUS           current
           DESCRIPTION
              "Tx Unusable seconds at far-end: count of seconds with Tx Unusable
              indications from the far-end Tx LSM in one of the previous 96,
              individual 15 minute, intervals."
           REFERENCE
              "ATM Forum IMA v1.1, (R-132) and (O-26) in Section 12.2.2.2
              on page 77"
           ::= { imaLinkIntervalEntry 10 }

imaLinkIntervalFeRxUnusableSecs OBJECT-TYPE
           SYNTAX           Gauge32
           MAX-ACCESS    read-only
           STATUS           current
           DESCRIPTION
              "Rx Unusable seconds at far-end: count of seconds with Rx Unusable
              indications from the far-end Rx LSM in one of the previous 96,
              individual 15 minute, intervals."
           REFERENCE
              "ATM Forum IMA v1.1, (R-133) and (O-26) in Section 12.2.2.2
              on page 77"
           ::= { imaLinkIntervalEntry 11 }

imaLinkIntervalNeTxNumFailures OBJECT-TYPE
           SYNTAX           Gauge32
           MAX-ACCESS    read-only
           STATUS           current
           DESCRIPTION
              "The number of times a near-end transmit failure alarm condition
              has been entered on this link (i. e., some form of implementation
              specific transmit fault) in one of the previous 96, individual
              15 minute, intervals."
           REFERENCE
              "ATM Forum IMA v1.1, (R-134) and (O-26) in Section 12.2.2.2
              on page 77"
           ::= { imaLinkIntervalEntry 12 }

imaLinkIntervalNeRxNumFailures OBJECT-TYPE
           SYNTAX           Gauge32
           MAX-ACCESS    read-only
           STATUS           current
           DESCRIPTION
              "The number of times a near-end receive failure alarm condition
              has been entered on this link (i. e., LIF, LODS, RFI-IMA,
              Mis-Connected, or some form of implementation specific
              receive fault) in one of the previous 96, individual 15 minute,
              intervals."
           REFERENCE
              "ATM Forum IMA v1.1, (R-135) and (O-26) in Section 12.2.2.2
              on page 77"
           ::= { imaLinkIntervalEntry 13 }

imaLinkIntervalFeTxNumFailures OBJECT-TYPE
           SYNTAX           Gauge32
           MAX-ACCESS    read-only
           STATUS           current
           DESCRIPTION
              "The number of times a far-end transmit failure alarm condition
              has been entered on this link (i. e., Tx-Unusable-FE) in one of the
              previous 96, individual 15 minute, intervals.    This is an optional
              attribute."
           REFERENCE
              "ATM Forum IMA v1.1, (O-21) and (O-26) in Section 12.2.2.2
              on page 77"
           ::= { imaLinkIntervalEntry 14 }

imaLinkIntervalFeRxNumFailures OBJECT-TYPE
           SYNTAX           Gauge32
           MAX-ACCESS    read-only
           STATUS           current
           DESCRIPTION
              "The number of times a far-end receive failure alarm condition
              has been entered on this link (i. e., Rx-Unusable-FE) in one of
              the previous 96, individual 15 minute, intervals.    This is an
              optional attribute."
           REFERENCE
              "ATM Forum IMA v1.1, (O-22) and (O-26) in Section 12.2.2.2
              on page 77"
           ::= { imaLinkIntervalEntry 15 }

imaLinkIntervalTxStuffs OBJECT-TYPE
           SYNTAX           Gauge32
           MAX-ACCESS    read-only
           STATUS           current
           DESCRIPTION
              "Count of stuff events inserted in the transmit direction in
              one of the previous 96, individual 15 minute, intervals.    This
              is an optional attribute."
           REFERENCE
              "ATM Forum IMA v1.1, (O-23) and (O-26) in Section 12.2.2.2
              on page 77"
           ::= { imaLinkIntervalEntry 16 }

imaLinkIntervalRxStuffs OBJECT-TYPE
           SYNTAX           Gauge32
           MAX-ACCESS    read-only
           STATUS           current
           DESCRIPTION
              "Count of stuff events detected in the receive direction in
              one of the previous 96, individual 15 minute, intervals.    This
              is an optional attribute."
           REFERENCE
              "ATM Forum IMA v1.1, (O-24) and (O-26) in Section 12.2.2.2
              on page 77"
           ::= { imaLinkIntervalEntry 17 }

--
--The IMA Link Total Statistics subtree
--
--The IMA Link Total Statistics subtree consists of a single table:
--the IMA Link Total Table.    This table contains the cumulative sum
--of the various statistics collected by each IMA link for the 24 hour
--period preceding the current interval.
--
--Implementation of IMA Link Total Table is optional.
--

imaLinkTotalTable OBJECT-TYPE
           SYNTAX           SEQUENCE OF ImaLinkTotalEntry
           MAX-ACCESS    not-accessible
           STATUS           current
           DESCRIPTION
              "The IMA Link Total table."
           ::= { zxImaLinkMibObjects 4 }

imaLinkTotalEntry OBJECT-TYPE
           SYNTAX           ImaLinkTotalEntry
           MAX-ACCESS    not-accessible
           STATUS           current
           DESCRIPTION
              "An entry in the IMA Link Total table."
           INDEX             { ifIndex }
           ::= { imaLinkTotalTable 1 }

ImaLinkTotalEntry ::= SEQUENCE {
           imaLinkTotalImaViolations          Gauge32,
           imaLinkTotalOifAnomalies            Gauge32,
           imaLinkTotalNeSevErroredSecs    Gauge32,
           imaLinkTotalFeSevErroredSecs    Gauge32,
           imaLinkTotalNeUnavailSecs          Gauge32,
           imaLinkTotalFeUnavailSecs          Gauge32,
           imaLinkTotalNeTxUnusableSecs    Gauge32,
           imaLinkTotalNeRxUnusableSecs    Gauge32,
           imaLinkTotalFeTxUnusableSecs    Gauge32,
           imaLinkTotalFeRxUnusableSecs    Gauge32,
           imaLinkTotalNeTxNumFailures      Gauge32,
           imaLinkTotalNeRxNumFailures      Gauge32,
           imaLinkTotalFeTxNumFailures      Gauge32,
           imaLinkTotalFeRxNumFailures      Gauge32,
           imaLinkTotalTxStuffs                   Gauge32,
           imaLinkTotalRxStuffs                   Gauge32 }

imaLinkTotalImaViolations OBJECT-TYPE
           SYNTAX           Gauge32
           MAX-ACCESS    read-only
           STATUS           current
           DESCRIPTION
              "ICP violations: count of errored, invalid or missing ICP cells,
              except during SES-IMA or UAS-IMA conditions, in the previous 24
              hour interval.    Invalid 15 minute intervals count as 0."
           REFERENCE
              "ATM Forum IMA v1.1, (R-125) and (O-27) in Section 12.2.2.2
              on page 77"
           ::= { imaLinkTotalEntry 1 }

imaLinkTotalOifAnomalies OBJECT-TYPE
           SYNTAX           Gauge32
           MAX-ACCESS    read-only
           STATUS           current
           DESCRIPTION
              "The number of OIF anomalies, except during SES-IMA or UAS-IMA
              conditions, at the near-end in the previous 24 hour interval.
              Invalid 15 minute intervals count as 0.    This is an optional
              attribute."
           REFERENCE
              "ATM Forum IMA v1.1, (O-20) and (O-27) in Section 12.2.2.2
              on page 77"
           ::= { imaLinkTotalEntry 2 }

imaLinkTotalNeSevErroredSecs OBJECT-TYPE
           SYNTAX           Gauge32
           MAX-ACCESS    read-only
           STATUS           current
           DESCRIPTION
              "Count of one second intervals containing >= 30% of the ICP cells
              counted as IV-IMAs, or one or more link defects (e. g., LOS, OOF/ LOF,
              AIS, or LCD), LIF defects, or LODS defects, except during UAS-IMA
              condition, in the previous 24 hour interval.    Invalid 15 minute
              intervals count as 0."
           REFERENCE
              "ATM Forum IMA v1.1, (R-126) and (O-27) in Section 12.2.2.2
              on page 77"
           ::= { imaLinkTotalEntry 3 }

imaLinkTotalFeSevErroredSecs OBJECT-TYPE
           SYNTAX           Gauge32
           MAX-ACCESS    read-only
           STATUS           current
           DESCRIPTION
              "Count of one second intervals containing one or more RDI-IMA
              defects, except during UAS-IMA-FE condition, in the previous 24
              hour interval.    Invalid 15 minute intervals count as 0."
           REFERENCE
              "ATM Forum IMA v1.1, (R-127) and (O-27) in Section 12.2.2.2
              on page 77"
           ::= { imaLinkTotalEntry 4 }

imaLinkTotalNeUnavailSecs OBJECT-TYPE
           SYNTAX           Gauge32
           MAX-ACCESS    read-only
           STATUS           current
           DESCRIPTION
              "Count of unavailable seconds at near-end in the previous 24 hour
              interval: unavailability begins at the onset of 10 contiguous
              SES-IMA and ends at the onset of 10 contiguous seconds with no
              SES-IMA.    Invalid 15 minute intervals count as 0."
           REFERENCE
              "ATM Forum IMA v1.1, (R-128) and (O-27) in Section 12.2.2.2
              on page 77"
           ::= { imaLinkTotalEntry 5 }

imaLinkTotalFeUnavailSecs OBJECT-TYPE
           SYNTAX           Gauge32
           MAX-ACCESS    read-only
           STATUS           current
           DESCRIPTION
              "Count of unavailable seconds at far-end in the previous 24 hour
              interval: unavailability begins at the onset of 10 contiguous
              SES-IMA-FE and ends at the onset of 10 contiguous seconds with no
              SES-IMA-FE.    Invalid 15 minute intervals count as 0."
           REFERENCE
              "ATM Forum IMA v1.1, (R-129) and (O-27) in Section 12.2.2.2
              on page 77"
           ::= { imaLinkTotalEntry 6 }

imaLinkTotalNeTxUnusableSecs OBJECT-TYPE
           SYNTAX           Gauge32
           MAX-ACCESS    read-only
           STATUS           current
           DESCRIPTION
              "Tx Unusable seconds: count of Unusable seconds at the near-end
              Tx LSM in the previous 24 hour interval.    Invalid 15 minute
              intervals count as 0."
           REFERENCE
              "ATM Forum IMA v1.1, (R-130) and (O-27) in Section 12.2.2.2
              on page 77"
           ::= { imaLinkTotalEntry 7 }

imaLinkTotalNeRxUnusableSecs OBJECT-TYPE
           SYNTAX           Gauge32
           MAX-ACCESS    read-only
           STATUS           current
           DESCRIPTION
              "Rx Unusable seconds: count of Unusable seconds at the near-end
              Rx LSM in the previous 24 hour interval.    Invalid 15 minute
              intervals count as 0."
           REFERENCE
              "ATM Forum IMA v1.1, (R-131) and (O-27) in Section 12.2.2.2
              on page 77"
           ::= { imaLinkTotalEntry 8 }

imaLinkTotalFeTxUnusableSecs OBJECT-TYPE
           SYNTAX           Gauge32
           MAX-ACCESS    read-only
           STATUS           current
           DESCRIPTION
              "Tx Unusable seconds at far-end: count of seconds with Tx Unusable
              indications from the far-end Tx LSM in the previous 24 hour
              interval.    Invalid 15 minute intervals count as 0."
           REFERENCE
              "ATM Forum IMA v1.1, (R-132) and (O-27) in Section 12.2.2.2
              on page 77"
           ::= { imaLinkTotalEntry 9 }

imaLinkTotalFeRxUnusableSecs OBJECT-TYPE
           SYNTAX           Gauge32
           MAX-ACCESS    read-only
           STATUS           current
           DESCRIPTION
              "Rx Unusable seconds at far-end: count of seconds with Rx Unusable
              indications from the far-end Rx LSM in the previous 24 hour
              interval.    Invalid 15 minute intervals count as 0."
           REFERENCE
              "ATM Forum IMA v1.1, (R-133) and (O-27) in Section 12.2.2.2
              on page 77"
           ::= { imaLinkTotalEntry 10 }

imaLinkTotalNeTxNumFailures OBJECT-TYPE
           SYNTAX           Gauge32
           MAX-ACCESS    read-only
           STATUS           current
           DESCRIPTION
              "The number of times a near-end transmit failure alarm condition
              has been entered on this link (i. e., some form of implementation
              specific transmit fault) in the previous 24 hour interval.
              Invalid 15 minute intervals count as 0."
           REFERENCE
              "ATM Forum IMA v1.1, (R-134) and (O-27) in Section 12.2.2.2
              on page 77"
           ::= { imaLinkTotalEntry 11 }

imaLinkTotalNeRxNumFailures OBJECT-TYPE
           SYNTAX           Gauge32
           MAX-ACCESS    read-only
           STATUS           current
           DESCRIPTION
              "The number of times a near-end receive failure alarm condition
              has been entered on this link (i. e., LIF, LODS, RFI-IMA,
              Mis-Connected, or some form of implementation specific receive fault)
              in the previous 24 hour interval. Invalid 15 minute intervals
              count as 0."
           REFERENCE
              "ATM Forum IMA v1.1, (R-135) and (O-27) in Section 12.2.2.2
              on page 77"
           ::= { imaLinkTotalEntry 12 }

imaLinkTotalFeTxNumFailures OBJECT-TYPE
           SYNTAX           Gauge32
           MAX-ACCESS    read-only
           STATUS           current
           DESCRIPTION
              "The number of times a far-end transmit failure alarm condition
              has been entered on this link (i. e., Tx-Unusable-FE) in the
              previous 24 hour interval.    Invalid 15 minute intervals count
              as 0.    This is an optional attribute."
           REFERENCE
              "ATM Forum IMA v1.1, (O-21) and (O-27) in Section 12.2.2.2
              on page 77"
           ::= { imaLinkTotalEntry 13 }

imaLinkTotalFeRxNumFailures OBJECT-TYPE
           SYNTAX           Gauge32
           MAX-ACCESS    read-only
           STATUS           current
           DESCRIPTION
              "The number of times a far-end receive failure alarm condition
              has been entered on this link (i. e., Rx-Unusable-FE) in the
              previous 24 hour interval.    Invalid 15 minute intervals count
              as 0.    This is an optional attribute."
           REFERENCE
              "ATM Forum IMA v1.1, (O-22) and (O-27) in Section 12.2.2.2
              on page 77"
           ::= { imaLinkTotalEntry 14 }

imaLinkTotalTxStuffs OBJECT-TYPE
           SYNTAX           Gauge32
           MAX-ACCESS    read-only
           STATUS           current
           DESCRIPTION
              "Count of stuff events inserted in the transmit direction in
              the previous 24 hour interval.    Invalid 15 minute intervals
              count as 0.    This is an optional attribute."
           REFERENCE
              "ATM Forum IMA v1.1, (O-23) and (O-27) in Section 12.2.2.2
              on page 77"
           ::= { imaLinkTotalEntry 15 }

imaLinkTotalRxStuffs OBJECT-TYPE
           SYNTAX           Gauge32
           MAX-ACCESS    read-only
           STATUS           current
           DESCRIPTION
              "Count of stuff events detected in the receive direction in
              the previous 24 hour interval.    Invalid 15 minute intervals
              count as 0.    This is an optional attribute."
           REFERENCE
              "ATM Forum IMA v1.1, (O-24) and (O-27) in Section 12.2.2.2
              on page 77"
           ::= { imaLinkTotalEntry 16 }

--Units of ImaLink Conformance
imaLinkGroup OBJECT-GROUP
           OBJECTS {
              imaLinkRowStatus,
              imaLinkGroupIndex,
              imaLinkNeTxState,
              imaLinkNeRxState,
              imaLinkFeTxState,
              imaLinkFeRxState,
              imaLinkNeRxFailureStatus,
              imaLinkFeRxFailureStatus,
              imaLinkTxLid,
              imaLinkRxLid,
              imaLinkRelDelay,
              imaLinkImaViolations,
              imaLinkOifAnomalies,
              imaLinkNeSevErroredSecs,
              imaLinkFeSevErroredSecs,
              imaLinkNeUnavailSecs,
              imaLinkFeUnavailSecs,
              imaLinkNeTxUnusableSecs,
              imaLinkNeRxUnusableSecs,
              imaLinkFeTxUnusableSecs,
              imaLinkFeRxUnusableSecs,
              imaLinkNeTxNumFailures,
              imaLinkNeRxNumFailures,
              imaLinkFeTxNumFailures,
              imaLinkFeRxNumFailures,
              imaLinkTxStuffs,
              imaLinkRxStuffs }
           STATUS          current
           DESCRIPTION
              "A set of objects providing status information for an IMA link."
           ::= { zxImaLinkMibGroups 1 }

 imaLinkTestPatternGroup OBJECT-GROUP
           OBJECTS {
              imaLinkRxTestPattern,
              imaLinkTestProcStatus }
           STATUS          current
           DESCRIPTION
              "Objects in the imaGroupTable and imaLinkTable which control and
              report on the Test Pattern Procedure.    These objects must be
              implemented if the IMA Test Pattern Procedure is supported."
           ::= { zxImaLinkMibGroups 2 }

imaLinkIntervalGroup OBJECT-GROUP
           OBJECTS {
              imaLinkValidIntervals,
              imaLinkInvalidIntervals,
              imaLinkTimeElapsed,
              imaLinkCurrentImaViolations,
              imaLinkCurrentOifAnomalies,
              imaLinkCurrentNeSevErroredSecs,
              imaLinkCurrentFeSevErroredSecs,
              imaLinkCurrentNeUnavailSecs,
              imaLinkCurrentFeUnavailSecs,
              imaLinkCurrentNeTxUnusableSecs,
              imaLinkCurrentNeRxUnusableSecs,
              imaLinkCurrentFeTxUnusableSecs,
              imaLinkCurrentFeRxUnusableSecs,
              imaLinkCurrentNeTxNumFailures,
              imaLinkCurrentNeRxNumFailures,
              imaLinkCurrentFeTxNumFailures,
              imaLinkCurrentFeRxNumFailures,
              imaLinkCurrentTxStuffs,
              imaLinkCurrentRxStuffs,
              imaLinkIntervalImaViolations,
              imaLinkIntervalOifAnomalies,
              imaLinkIntervalNeSevErroredSecs,
              imaLinkIntervalFeSevErroredSecs,
              imaLinkIntervalNeUnavailSecs,
              imaLinkIntervalFeUnavailSecs,
              imaLinkIntervalNeTxUnusableSecs,
              imaLinkIntervalNeRxUnusableSecs,
              imaLinkIntervalFeTxUnusableSecs,
              imaLinkIntervalFeRxUnusableSecs,
              imaLinkIntervalNeTxNumFailures,
              imaLinkIntervalNeRxNumFailures,
              imaLinkIntervalFeTxNumFailures,
              imaLinkIntervalFeRxNumFailures,
              imaLinkIntervalTxStuffs,
              imaLinkIntervalRxStuffs,
              imaLinkTotalImaViolations,
              imaLinkTotalOifAnomalies,
              imaLinkTotalNeSevErroredSecs,
              imaLinkTotalFeSevErroredSecs,
              imaLinkTotalNeUnavailSecs,
              imaLinkTotalFeUnavailSecs,
              imaLinkTotalNeTxUnusableSecs,
              imaLinkTotalNeRxUnusableSecs,
              imaLinkTotalFeTxUnusableSecs,
              imaLinkTotalFeRxUnusableSecs,
              imaLinkTotalNeTxNumFailures,
              imaLinkTotalNeRxNumFailures,
              imaLinkTotalFeTxNumFailures,
              imaLinkTotalFeRxNumFailures,
              imaLinkTotalTxStuffs,
              imaLinkTotalRxStuffs }
           STATUS          current
           DESCRIPTION
              "Objects containing interval statistics for an IMA link."
           ::= { zxImaLinkMibGroups 3 }

zxImaLinkMibCompliance MODULE-COMPLIANCE
    STATUS  current
    DESCRIPTION
           "The compliance statement."
    MODULE  -- this module
    MANDATORY-GROUPS{
            imaLinkGroup,
            imaLinkTestPatternGroup,
            imaLinkIntervalGroup
            }
        ::= { zxImaLinkMibCompliances 1 }

END
     ATM-TC-MIB DEFINITIONS ::= BEGIN

     IMPORTS
        MODULE-IDENTITY, OBJECT-IDENTITY,
        TimeTicks, mib-2
            FROM SNMPv2-SMI
        TEXTUAL-CONVENTION
            FROM SNMPv2-TC;


     atmTCMIB MODULE-IDENTITY
          LAST-UPDATED "9810190200Z"
          ORGANIZATION "IETF AToMMIB Working Group"
          CONTACT-INFO
            "          Michael Noto
              Postal:  3Com Corporation
                       5400 Bayfront Plaza, M/S 3109
                       Santa Clara, CA 95052
                       USA
              Tel:     +1 408 326 2218
              E-mail:  mike_noto@3com.com

                       Ethan Mickey Spiegel
              Postal:  Cisco Systems
                       170 W. Tasman Dr.
                       San Jose, CA 95134
                       USA
              Tel:     +1 408 526 6408
              E-mail:  mspiegel@cisco.com

                       Kaj Tesink
              Postal:  Bellcore
                       331 Newman Springs Road
                       Red Bank, NJ 07701
                       USA
              Tel:     +1 732 758 5254
              Fax:     +1 732 758 4177
              E-mail:  kaj@bellcore.com"
          DESCRIPTION
           "This MIB Module provides Textual Conventions
           and OBJECT-IDENTITY Objects to be used by
           ATM systems."
          ::= { mib-2 37 3 } -- atmMIB 3 (see [3])

     -- The Textual Conventions defined below are organized
     -- alphabetically


     AtmAddr ::= TEXTUAL-CONVENTION
             DISPLAY-HINT "1x"
             STATUS  current
             DESCRIPTION
                 "An ATM address. The semantics are implied by
                 the length. The address types are: - no
                 address (0 octets) - E.164 (8 octets) - NSAP
                 (20 octets) In addition, when subaddresses
                 are used the AtmAddr may represent the
                 concatenation of address and subaddress. The
                 associated address types are: - E.164, E.164
                 (16 octets) - E.164, NSAP (28 octets) - NSAP,
                 NSAP (40 octets) Address lengths other than
                 defined in this definition imply address
                 types defined elsewhere.  Note: The E.164
                 address is encoded in BCD format."
            SYNTAX   OCTET STRING (SIZE(0..40))


     AtmConnCastType ::= TEXTUAL-CONVENTION
            STATUS  current
            DESCRIPTION
              "The type of topology of a connection (point-
              to-point, point-to-multipoint). In the case
              of point-to-multipoint, the orientation of
              this VPL or VCL in the connection.
              On a host:
              - p2mpRoot indicates that the host
                is the root of the p2mp connection.
              - p2mpLeaf indicates that the host
                is a leaf of the p2mp connection.
              On a switch interface:
              - p2mpRoot indicates that cells received
                by the switching fabric from the interface
                are from the root of the p2mp connection.
              - p2mpLeaf indicates that cells transmitted
                to the interface from the switching fabric
                are to the leaf of the p2mp connection."
            SYNTAX   INTEGER {
               p2p(1),
               p2mpRoot(2),
               p2mpLeaf(3)
               }

     AtmConnKind ::= TEXTUAL-CONVENTION
            STATUS  current
            DESCRIPTION
                "The type of call control used for an ATM
                connection at a particular interface. The use
                is as follows:
                   pvc(1)
                      Virtual link of a PVC. Should not be
                      used for an PVC/SVC (i.e., Soft PVC)
                      crossconnect.
                   svcIncoming(2)
                      Virtual link established after a
                      received signaling request to setup
                      an SVC.
                   svcOutgoing(3)
                      Virtual link established after a
                      transmitted or forwarded signaling
                      request to setup an SVC.
                   spvcInitiator(4)
                      Virtual link at the PVC side of an
                      SVC/PVC crossconnect, where the
                      switch is the initiator of the Soft PVC
                      setup.
                   spvcTarget(5)
                      Virtual link at the PVC side of an
                      SVC/PVC crossconnect, where the
                      switch is the target of the Soft PVC
                      setup.

                For PVCs, a pvc virtual link is always cross-
                connected to a pvc virtual link.

                For SVCs, an svcIncoming virtual link is always cross-
                connected to an svcOutgoing virtual link.

                For Soft PVCs, an spvcInitiator is either cross-connected to
                an svcOutgoing or an spvcTarget, and an spvcTarget is either
                cross-connected to an svcIncoming or an spvcInitiator."
        SYNTAX   INTEGER {
           pvc(1),
           svcIncoming(2),
           svcOutgoing(3),
           spvcInitiator(4),
           spvcTarget(5)
           }

     AtmIlmiNetworkPrefix ::= TEXTUAL-CONVENTION
        STATUS   current
        DESCRIPTION
            "A network prefix used for ILMI address
            registration.  In the case of ATM endsystem
            addresses (AESAs), the network prefix is the first
            13 octets of the address which includes the AFI,
            IDI, and HO-DSP fields.  In the case of native
            E.164 addresses, the network prefix is the entire
            E.164 address encoded in 8 octets, as if it were
            an E.164 IDP in an ATM endsystem address
            structure."
        REFERENCE
            "ATM Forum, Integrated Local Management Interface
               (ILMI) Specification, Version 4.0,
               af-ilmi-0065.000, September 1996, Section 9
             ATM Forum, ATM User-Network Interface Signalling
               Specification, Version 4.0 (UNI 4.0),
               af-sig-0061.000, June 1996, Section 3"
        SYNTAX   OCTET STRING (SIZE(8|13))

     AtmInterfaceType ::= TEXTUAL-CONVENTION
        STATUS       current
        DESCRIPTION
            "The connection setup procedures used for the
            identified interface.

            Other: Connection setup procedures other than
               those listed below.
               
            Auto-configuration:
               Indicates that the connection setup
               procedures are to be determined dynamically,
               or that determination has not yet been
               completed. One such mechanism is via ATM
               Forum ILMI auto-configuration procedures.

            ITU-T DSS2:
            -  ITU-T Recommendation Q.2931, Broadband
               Integrated Service Digital Network (B-ISDN)
               Digital Subscriber Signalling System No.2
               (DSS2) User-Network Interface (UNI) Layer 3
               Specification for Basic Call/Connection
               Control (September 1994)
            -  ITU-T Draft Recommendation Q.2961,
               B-ISDN DSS 2 Support of Additional Traffic
               Parameters (May 1995)

            -  ITU-T Draft Recommendation Q.2971,
               B-ISDN DSS 2 User Network Interface Layer 3
               Specification for Point-to-multipoint
               Call/connection Control (May 1995)

            ATM Forum UNI 3.0:
               ATM Forum, ATM User-Network Interface,
               Version 3.0 (UNI 3.0) Specification,
               (1994).

            ATM Forum UNI 3.1:
               ATM Forum, ATM User-Network Interface,
               Version 3.1 (UNI 3.1) Specification,
               (November 1994).

            ATM Forum UNI Signalling 4.0:
               ATM Forum, ATM User-Network Interface (UNI)
               Signalling Specification Version 4.0,
               af-sig-0061.000 (June 1996).

            ATM Forum IISP (based on UNI 3.0 or UNI 3.1) :
               Interim Inter-switch Signaling Protocol
               (IISP) Specification, Version 1.0,
               af-pnni-0026.000, (December 1994).

            ATM Forum PNNI 1.0 :
               ATM Forum, Private Network-Network Interface
               Specification, Version 1.0, af-pnni-0055.000,
               (March 1996).

            ATM Forum B-ICI:
               ATM Forum, B-ICI Specification, Version 2.0,
               af-bici-0013.002, (November 1995).

            ATM Forum UNI PVC Only:
               An ATM Forum compliant UNI with the
               signalling disabled.
            ATM Forum NNI PVC Only:
               An ATM Forum compliant NNI with the
               signalling disabled."
        SYNTAX  INTEGER  {
                  other(1),
                  autoConfig(2),
                  ituDss2(3),
                  atmfUni3Dot0(4),
                  atmfUni3Dot1(5),
                  atmfUni4Dot0(6),
                  atmfIispUni3Dot0(7),
                  atmfIispUni3Dot1(8),
                  atmfIispUni4Dot0(9),
        atmfPnni1Dot0(10),
        atmfBici2Dot0(11),
        atmfUniPvcOnly(12),
        atmfNniPvcOnly(13)  }

     AtmServiceCategory ::= TEXTUAL-CONVENTION
        STATUS  current
        DESCRIPTION
            "The service category for a connection."
        REFERENCE
            "ATM Forum Traffic Management Specification,
            Version 4.0, af-tm-0056.000, June 1996."
        SYNTAX   INTEGER {
           other(1),   -- none of the following
           cbr(2),     -- constant bit rate
           rtVbr(3),   -- real-time variable bit rate
           nrtVbr(4),  -- non real-time variable bit rate
           abr(5),     -- available bit rate
           ubr(6)      -- unspecified bit rate
           }

     AtmSigDescrParamIndex ::= TEXTUAL-CONVENTION
        STATUS  current
        DESCRIPTION
            "The value of this object identifies a row in the
            atmSigDescrParamTable. The value 0 signifies that
            none of the signalling parameters defined in the
            atmSigDescrParamTable are applicable."
        SYNTAX  INTEGER (0..2147483647)

     AtmTrafficDescrParamIndex ::= TEXTUAL-CONVENTION
        STATUS  current
        DESCRIPTION
            "The value of this object identifies a row in the
            atmTrafficDescrParamTable.  The value 0 signifies
            that no row has been identified."
        SYNTAX  INTEGER (0..2147483647)

     AtmVcIdentifier ::= TEXTUAL-CONVENTION
        STATUS  current
        DESCRIPTION
            "The VCI value for a VCL. The maximum VCI value
            cannot exceed the value allowable by
            atmInterfaceMaxVciBits defined in ATM-MIB."
        SYNTAX   INTEGER (0..65535)

     AtmVpIdentifier ::= TEXTUAL-CONVENTION
        STATUS  current
        DESCRIPTION
            "The VPI value for a VPL or VCL. The value VPI=0
            is only allowed for a VCL. For ATM UNIs supporting
            VPCs the VPI value ranges from 0 to 255.  The VPI
            value 0 is supported for ATM UNIs conforming to
            the ATM Forum UNI 4.0 Annex 8 (Virtual UNIs)
            specification. For ATM UNIs supporting VCCs the
            VPI value ranges from 0 to 255.  For ATM NNIs the
            VPI value ranges from 0 to 4095.  The maximum VPI
            value cannot exceed the value allowable by
            atmInterfaceMaxVpiBits defined in ATM-MIB."
        SYNTAX    INTEGER (0..4095)

     AtmVorXAdminStatus ::= TEXTUAL-CONVENTION
        STATUS  current
        DESCRIPTION
            "The value determines the desired administrative
            status of a virtual link or cross-connect. The up
            and down states indicate that the traffic flow is
            enabled or disabled respectively on the virtual
            link or cross-connect."
        SYNTAX   INTEGER {
           up(1),
           down(2)
            }

     AtmVorXLastChange ::= TEXTUAL-CONVENTION
        STATUS  current
        DESCRIPTION
            "The value of MIB II's sysUpTime at the time a
            virtual link or cross-connect entered its current
            operational state. If the current state was
            entered prior to the last re-initialization of the
            agent then this object contains a zero value."
        SYNTAX   TimeTicks

     AtmVorXOperStatus ::= TEXTUAL-CONVENTION
        STATUS  current
        DESCRIPTION
            "The value determines the operational status of a
            virtual link or cross-connect. The up and down
            states indicate that the traffic flow is enabled
            or disabled respectively on the virtual link or
            cross-connect. The unknown state indicates that
            the state of it cannot be determined. The state
            will be down or unknown if the supporting ATM
            interface(s) is down or unknown respectively."
        SYNTAX   INTEGER {
           up(1),
           down(2),
           unknown(3)
           }


-- OBJECT-IDENTITIES:

-- The following atmTrafficDescriptorTypes has been moved
-- from RFC1695 and no longer appear in the revision of
-- RFC1695[3].

atmTrafficDescriptorTypes OBJECT IDENTIFIER ::= {mib-2 37 1 1}
                                            -- atmMIBObjects
                                            -- See [3].

-- All other and new OBJECT IDENTITIES
-- are defined under the following subtree:

    atmObjectIdentities OBJECT IDENTIFIER ::= {atmTCMIB 1}

-- The following values are defined for use as
-- possible values of the ATM traffic descriptor type.

atmNoTrafficDescriptor  OBJECT-IDENTITY
    STATUS  deprecated
    DESCRIPTION
        "This identifies the no ATM traffic
        descriptor type.  Parameters 1, 2, 3, 4,
        and 5 are not used.  This traffic descriptor
        type can be used for best effort traffic."
    ::= {atmTrafficDescriptorTypes 1}

atmNoClpNoScr  OBJECT-IDENTITY
    STATUS  current
    DESCRIPTION
        "This traffic descriptor type is for no CLP
        and no Sustained Cell Rate.  The use of the
        parameter vector for this type:
        Parameter 1: peak cell rate in cells/second
                     for CLP=0+1 traffic
        Parameter 2: not used
        Parameter 3: not used
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 2}

atmClpNoTaggingNoScr  OBJECT-IDENTITY
    STATUS  deprecated
    DESCRIPTION
        "This traffic descriptor is for CLP without
        tagging and no Sustained Cell Rate.  The use
        of the parameter vector for this type:
        Parameter 1: peak cell rate in cells/second
                     for CLP=0+1 traffic
        Parameter 2: peak cell rate in cells/second
                     for CLP=0 traffic
        Parameter 3: not used
        Parameter 4: not used
        Parameter 5: not used."
    ::= {atmTrafficDescriptorTypes 3}

atmClpTaggingNoScr  OBJECT-IDENTITY
    STATUS  deprecated
    DESCRIPTION
        "This traffic descriptor is for CLP with
        tagging and no Sustained Cell Rate.  The use
        of the parameter vector for this type:
        Parameter 1: peak cell rate in cells/second
                     for CLP=0+1 traffic
        Parameter 2: peak cell rate in cells/second
                     for CLP=0 traffic, excess
                     tagged as CLP=1
        Parameter 3: not used
        Parameter 4: not used
        Parameter 5: not used."
    ::= {atmTrafficDescriptorTypes 4}

atmNoClpScr  OBJECT-IDENTITY
    STATUS  current
    DESCRIPTION
        "This traffic descriptor type is for no CLP
        with Sustained Cell Rate.  The use of the
        parameter vector for this type:
        Parameter 1: peak cell rate in cells/second
                     for CLP=0+1 traffic
        Parameter 2: sustainable cell rate in cells/second
                     for CLP=0+1 traffic
        Parameter 3: maximum burst size in cells
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 5}

atmClpNoTaggingScr  OBJECT-IDENTITY
    STATUS  current
    DESCRIPTION
        "This traffic descriptor type is for CLP with
        Sustained Cell Rate and no tagging.  The use
        of the parameter vector for this type:
        Parameter 1: peak cell rate in cells/second
                     for CLP=0+1 traffic
        Parameter 2: sustainable cell rate in cells/second
                     for CLP=0 traffic
        Parameter 3: maximum burst size in cells
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 6}

atmClpTaggingScr  OBJECT-IDENTITY
    STATUS  current
    DESCRIPTION
        "This traffic descriptor type is for CLP with
        tagging and Sustained Cell Rate.  The use of
        the parameter vector for this type:
        Parameter 1: peak cell rate in cells/second
                     for CLP=0+1 traffic
        Parameter 2: sustainable cell rate in cells/second
                     for CLP=0 traffic, excess tagged as
                     CLP=1
        Parameter 3: maximum burst size in cells
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 7}

atmClpNoTaggingMcr  OBJECT-IDENTITY
    STATUS  current
    DESCRIPTION
        "This traffic descriptor type is for CLP with
        Minimum Cell Rate and no tagging.  The use of
        the parameter vector for this type:
        Parameter 1: peak cell rate in cells/second
                     for CLP=0+1 traffic
        Parameter 2: CDVT in tenths of microseconds
        Parameter 3: minimum cell rate in cells/second
        Parameter 4: unused
        Parameter 5: unused."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 8}

atmClpTransparentNoScr  OBJECT-IDENTITY
    STATUS  current
    DESCRIPTION
        "This traffic descriptor type is for the CLP-
        transparent model and no Sustained Cell Rate.
        The use of the parameter vector for this type:
        Parameter 1: peak cell rate in cells/second
                     for CLP=0+1 traffic
        Parameter 2: CDVT in tenths of microseconds
        Parameter 3: not used
        Parameter 4: not used
        Parameter 5: not used.

        This traffic descriptor type is applicable to
        connections following the CBR.1 conformance
        definition.

        Connections specifying this traffic descriptor
        type will be rejected at UNI 3.0 or UNI 3.1
        interfaces.  For a similar traffic descriptor
        type that can be accepted at UNI 3.0 and
        UNI 3.1 interfaces, see atmNoClpNoScr."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 9}

atmClpTransparentScr  OBJECT-IDENTITY
    STATUS  current
    DESCRIPTION
        "This traffic descriptor type is for the CLP-
        transparent model with Sustained Cell Rate.
        The use of the parameter vector for this type:
        Parameter 1: peak cell rate in cells/second
                     for CLP=0+1 traffic
        Parameter 2: sustainable cell rate in cells/second
                     for CLP=0+1 traffic
        Parameter 3: maximum burst size in cells
        Parameter 4: CDVT in tenths of microseconds
        Parameter 5: not used.

        This traffic descriptor type is applicable to
        connections following the VBR.1 conformance
        definition.
        
        Connections specifying this traffic descriptor
        type will be rejected at UNI 3.0 or UNI 3.1
        interfaces.  For a similar traffic descriptor
        type that can be accepted at UNI 3.0 and
        UNI 3.1 interfaces, see atmNoClpScr."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 10}

atmNoClpTaggingNoScr  OBJECT-IDENTITY
    STATUS  current
    DESCRIPTION
        "This traffic descriptor type is for no CLP
        with tagging and no Sustained Cell Rate.  The
        use of the parameter vector for this type:
        Parameter 1: peak cell rate in cells/second
                     for CLP=0+1 traffic
        Parameter 2: CDVT in tenths of microseconds
        Parameter 3: not used
        Parameter 4: not used
        Parameter 5: not used.

        This traffic descriptor type is applicable to
        connections following the UBR.2 conformance
        definition ."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 11}

atmNoClpNoScrCdvt  OBJECT-IDENTITY
    STATUS  current
    DESCRIPTION
        "This traffic descriptor type is for no CLP
        and no Sustained Cell Rate.  The use of the
        parameter vector for this type:
        Parameter 1: peak cell rate in cells/second
                     for CLP=0+1 traffic
        Parameter 2: CDVT in tenths of microseconds
        Parameter 3: not used
        Parameter 4: not used
        Parameter 5: not used.

        This traffic descriptor type is applicable to
        CBR connections following the UNI 3.0/3.1
        conformance definition for PCR CLP=0+1.
        These CBR connections differ from CBR.1
        connections in that the CLR objective
        applies only to the CLP=0 cell flow.

        This traffic descriptor type is also
        applicable to connections following the UBR.1
        conformance definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 12}

atmNoClpScrCdvt  OBJECT-IDENTITY
    STATUS  current
    DESCRIPTION
        "This traffic descriptor type is for no CLP
        with Sustained Cell Rate.  The use of the
        parameter vector for this type:
        Parameter 1: peak cell rate in cells/second
                     for CLP=0+1 traffic
        Parameter 2: sustainable cell rate in cells/second
                     for CLP=0+1 traffic
        Parameter 3: maximum burst size in cells
        Parameter 4: CDVT in tenths of microseconds
        Parameter 5: not used.

        This traffic descriptor type is applicable
        to VBR connections following the UNI 3.0/3.1
        conformance definition for PCR CLP=0+1 and
        SCR CLP=0+1.  These VBR connections
        differ from VBR.1 connections in that
        the CLR objective applies only to the CLP=0
        cell flow."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 13}

atmClpNoTaggingScrCdvt  OBJECT-IDENTITY
    STATUS  current
    DESCRIPTION
        "This traffic descriptor type is for CLP with
        Sustained Cell Rate and no tagging.  The use
        of the parameter vector for this type:
        Parameter 1: peak cell rate in cells/second
                     for CLP=0+1 traffic
        Parameter 2: sustainable cell rate in cells/second
                     for CLP=0 traffic
        Parameter 3: maximum burst size in cells
        Parameter 4: CDVT in tenths of microseconds
        Parameter 5: not used.

        This traffic descriptor type is applicable to
        connections following the VBR.2 conformance
        definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 14}

atmClpTaggingScrCdvt  OBJECT-IDENTITY
    STATUS  current
    DESCRIPTION
        "This traffic descriptor type is for CLP with
        tagging and Sustained Cell Rate.  The use of
        the parameter vector for this type:
        Parameter 1: peak cell rate in cells/second
                     for CLP=0+1 traffic
        Parameter 2: sustainable cell rate in cells/second
                     for CLP=0 traffic, excess tagged as
                     CLP=1
        Parameter 3: maximum burst size in cells
        Parameter 4: CDVT in tenths of microseconds
        Parameter 5: not used.

        This traffic descriptor type is applicable to
        connections following the VBR.3 conformance
        definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 15}

END
   ADSL-TC-MIB DEFINITIONS ::= BEGIN

   IMPORTS
       transmission,
       MODULE-IDENTITY, Gauge32            FROM SNMPv2-SMI
       TEXTUAL-CONVENTION                  FROM SNMPv2-TC;

   adsltcmib MODULE-IDENTITY

   LAST-UPDATED "9908190000Z"

   ORGANIZATION "IETF ADSL MIB Working Group"

   CONTACT-INFO
       "
       Gregory Bathrick
       AG Communication Systems
       A Subsidiary of Lucent Technologies
       2500 W Utopia Rd.
       Phoenix, AZ 85027 USA
       Tel: +1 602-582-7679
       Fax: +1 602-582-7697
       E-mail: bathricg@agcs.com

       Faye Ly
       Copper Mountain Networks
       Norcal Office
       2470 Embarcadero Way
       Palo Alto, CA 94303
       Tel: +1 650-858-8500
       Fax: +1 650-858-8085
       E-Mail: faye@coppermountain.com
       IETF ADSL MIB Working Group (adsl@xlist.agcs.com)
       "
       DESCRIPTION
           "The MIB module which provides a ADSL
           Line Coding Textual Convention to be used
           by ADSL Lines."

       --  Revision history
       REVISION     "9908190000Z"  -- 19 August 1999, midnight
       DESCRIPTION  "Initial Version, published as RFC 2662"

       ::= { transmission 94 2 } -- adslMIB 2

       AdslLineCodingType ::= TEXTUAL-CONVENTION
           STATUS       current
           DESCRIPTION
               "This data type is used as the syntax for the ADSL
               Line Code."
           SYNTAX  INTEGER {
               other(1),-- none of the following
               dmt (2), -- Discrete MultiTone
               cap (3), -- Carrierless Amplitude & Phase modulation
               qam (4),  -- Quadrature Amplitude Modulation
               glite (5) -- Glite Mode
           }

       AdslPerfCurrDayCount ::= TEXTUAL-CONVENTION
           STATUS  current
           DESCRIPTION
               "A counter associated with interface performance
               measurements in a current 1-day (24 hour) measurement
               interval.

               The value of this counter starts at zero at the
               beginning of an interval and is increased when
               associated events occur, until the end of the
               1-day interval.  At that time the value of the
               counter is stored in the previous 1-day history
               interval, if available, and the current interval
               counter is restarted at zero.

               In the case where the agent has no valid data available
               for this interval the corresponding object
               instance is not available and upon a retrieval
               request a corresponding error message shall be
               returned to indicate that this instance does
               not exist (for example, a noSuchName error for
               SNMPv1 and a noSuchInstance for SNMPv2 GET
               operation)."
            SYNTAX  Gauge32

       AdslPerfPrevDayCount ::= TEXTUAL-CONVENTION
           STATUS  current
           DESCRIPTION
               "A counter associated with interface performance
               measurements during the most previous 1-day (24 hour)
               measurement interval.  The value of this counter is
               equal to the value of the current day counter at
               the end of its most recent interval.

               In the case where the agent has no valid data available
               for this interval the corresponding object
               instance is not available and upon a retrieval
               request a corresponding error message shall be
               returned to indicate that this instance does
               not exist (for example, a noSuchName error for
               SNMPv1 and a noSuchInstance for SNMPv2 GET
               operation)."
           SYNTAX  Gauge32

       AdslPerfTimeElapsed ::= TEXTUAL-CONVENTION
           STATUS current
           DESCRIPTION
               "The number of seconds that have elapsed since
               the beginning of the current measurement period.
               If, for some reason, such as an adjustment in the
               system's time-of-day clock, the current interval
               exceeds the maximum value, the agent will return
               the maximum value."
           SYNTAX  Gauge32

   END

   ADSL-LINE-MIB DEFINITIONS ::= BEGIN

   IMPORTS
       MODULE-IDENTITY, OBJECT-TYPE,
       Counter32, Gauge32,
       NOTIFICATION-TYPE,
       transmission, Unsigned32          FROM SNMPv2-SMI
       RowStatus,
       TruthValue, VariablePointer       FROM SNMPv2-TC
--       MODULE-COMPLIANCE, OBJECT-GROUP,
--       NOTIFICATION-GROUP                FROM SNMPv2-CONF
       ifIndex                           FROM IF-MIB
       PerfCurrentCount,
       PerfIntervalCount                 FROM PerfHist-TC-MIB
       SnmpAdminString                   FROM SNMP-FRAMEWORK-MIB
       AdslPerfCurrDayCount,
       AdslPerfPrevDayCount,
       AdslPerfTimeElapsed,
       AdslLineCodingType                FROM ADSL-TC-MIB
       ;

   adslMIB MODULE-IDENTITY

   LAST-UPDATED "9908190000Z"

   ORGANIZATION "IETF ADSL MIB Working Group"

   CONTACT-INFO
       "
       Gregory Bathrick
       AG Communication Systems
       A Subsidiary of Lucent Technologies
       2500 W Utopia Rd.
       Phoenix, AZ 85027 USA
       Tel: +1 602-582-7679
       Fax: +1 602-582-7697
       E-mail: bathricg@agcs.com

       Faye Ly
       Copper Mountain Networks
       Norcal Office
       2470 Embarcadero Way
       Palo Alto, CA 94303
       Tel: +1 650-858-8500
       Fax: +1 650-858-8085
       E-Mail: faye@coppermountain.com

       (ADSL Forum input only)
       John Burgess
       Predictive Systems, Inc.
       25A Vreeland Rd.
       Florham Park, NJ 07932 USA
       Tel: +1 973-301-5610
       Fax: +1 973-301-5699
       E-mail: jtburgess@predictive.com

       IETF ADSL MIB Working Group (adsl@xlist.agcs.com)
       "

   DESCRIPTION
       "The MIB module defining objects for the management of a pair of
       ADSL modems at each end of the ADSL line.  Each such line has
       an entry in an ifTable which may include multiple modem lines.
       An agent may reside at either end of the ADSL line however the
       MIB is designed to require no management communication between
       them beyond that inherent in the low-level ADSL line protocol.
       The agent may monitor and control this protocol for its needs.

       ADSL lines may support optional Fast or Interleaved channels.
       If these are supported, additional entries corresponding to the
       supported channels must be created in the ifTable. Thus an ADSL
       line that supports both channels will have three entries in the
       ifTable, one for each physical, fast, and interleaved, whose
       ifType values are equal to adsl(94), fast(125), and
       interleaved(124), respectively. The ifStackTable is used to
       represent the relationship between the entries.

       Naming Conventions:
                 Atuc -- (ATUC) modem at near (Central) end of line
                 Atur -- (ATUR) modem at Remote end of line
                 Curr -- Current
                 Prev -- Previous
                 Atn -- Attenuation
                 ES  -- Errored Second.
                 LCS -- Line Code Specific
                 Lof -- Loss of Frame
                 Lol -- Loss of Link
                 Los -- Loss of Signal
                 Lpr -- Loss of Power
                 xxxs-- interval of Seconds in which xxx occurs
                         (e.g., xxx=Lof, Los, Lpr)
                 Max -- Maximum
                 Mgn -- Margin
                 Min -- Minimum
                 Psd -- Power Spectral Density
                 Snr -- Signal to Noise Ratio
                 Tx  -- Transmit
                 Blks-- Blocks, a data unit, see
                        adslAtuXChanCrcBlockLength
         "
         --  Revision history
         REVISION     "9908190000Z"  -- 19 August 1999, midnight
         DESCRIPTION  "Initial Version, published as RFC 2662"

   ::= { transmission 94 }

   adslLineMib OBJECT IDENTIFIER ::= { adslMIB 1 }

   adslMibObjects OBJECT IDENTIFIER ::= { adslLineMib 1 }

   -- objects
         adslLineTable   OBJECT-TYPE
             SYNTAX          SEQUENCE OF AdslLineEntry
             MAX-ACCESS      not-accessible
             STATUS          current
             DESCRIPTION
                 "This table includes common attributes describing
                 both ends of the line.  It is required for all ADSL
                 physical interfaces.  ADSL physical interfaces are
                 those ifEntries where ifType is equal to adsl(94)."
         ::= { adslMibObjects 1 }

         adslLineEntry   OBJECT-TYPE
             SYNTAX          AdslLineEntry
             MAX-ACCESS      not-accessible
             STATUS          current
             DESCRIPTION     "An entry in adslLineTable."
             INDEX           { ifIndex }
         ::= { adslLineTable 1 }

         AdslLineEntry ::=
             SEQUENCE {
             adslLineCoding           AdslLineCodingType,
             adslLineType             INTEGER,
             adslLineSpecific         VariablePointer,
             adslLineConfProfile      SnmpAdminString,
             adslLineAlarmConfProfile SnmpAdminString
             }

         adslLineCoding OBJECT-TYPE
             SYNTAX      AdslLineCodingType
             MAX-ACCESS  read-write
             STATUS      current
             DESCRIPTION
                 "Specifies the ADSL coding type used on this
                 line."
         ::= { adslLineEntry 1 }

        adslLineType OBJECT-TYPE
             SYNTAX      INTEGER {
                 noChannel (1),        -- no channels exist
                 fastOnly (2),         -- fast channel exists only
                 interleavedOnly (3),  -- interleaved channel exists
                                       -- only
                 fastOrInterleaved (4),-- either fast or interleaved
                                       -- channels can exist, but
                                       -- only one at any time
                 fastAndInterleaved (5)-- both fast or interleaved
                                    -- channels exist
             }
             MAX-ACCESS  read-write
             STATUS      current
             DESCRIPTION
                 "Defines the type of ADSL physical line
                 entity that exists, by defining whether and how
                 the line is channelized.  If the line is channelized,
                 the value will be other than noChannel(1).  This
                 object defines which channel type(s) are supported.

                 In the case that the line is channelized, the manager
                 can use the ifStackTable to determine the ifIndex for
                 the associated channel(s)."
         ::= { adslLineEntry 2 }

         adslLineSpecific OBJECT-TYPE
             SYNTAX      VariablePointer
             MAX-ACCESS  read-only
             STATUS      current
             DESCRIPTION
                 "OID instance in vendor-specific MIB. The Instance may
                 be used to determine shelf/slot/port of the ATUC
                 interface in a DSLAM."
         ::= { adslLineEntry 3 }

        adslLineConfProfile OBJECT-TYPE
             SYNTAX      SnmpAdminString (SIZE (1..32))
             MAX-ACCESS  read-write
             STATUS      current
             DESCRIPTION
                 "The value of this object identifies the row
                 in the ADSL Line Configuration Profile Table,
                 (adslLineConfProfileTable), which applies for this
                 ADSL line, and channels if applicable.

                 For `dynamic' mode, in the case which the
                 configuration profile has not been set, the
                 value will be set to `DEFVAL'.

                 If the implementator of this MIB has chosen not
                 to implement `dynamic assignment' of profiles, this
                 object's MIN-ACCESS is read-only."
         ::= { adslLineEntry 4 }

        adslLineAlarmConfProfile OBJECT-TYPE
             SYNTAX      SnmpAdminString (SIZE (1..32))
             MAX-ACCESS  read-write
             STATUS      current
             DESCRIPTION
                 "The value of this object identifies the row
                 in the ADSL Line Alarm Configuration Profile Table,
                 (adslLineAlarmConfProfileTable), which applies to this
                 ADSL line, and channels if applicable.

                 For `dynamic' mode, in the case which the
                 alarm profile has not been set, the
                 value will be set to `DEFVAL'.

                 If the implementator of this MIB has chosen not
                 to implement `dynamic assignment' of profiles, this
                 object's MIN-ACCESS is read-only."
         ::= { adslLineEntry 5 }

         adslAtucPhysTable       OBJECT-TYPE
             SYNTAX          SEQUENCE OF AdslAtucPhysEntry
             MAX-ACCESS      not-accessible
             STATUS          current
             DESCRIPTION
                 "This table provides one row for each ATUC.
                 Each row contains the Physical Layer Parameters
                 table for that ATUC. ADSL physical interfaces are
                 those ifEntries where ifType is equal to adsl(94)."
         ::= { adslMibObjects 2 }

         adslAtucPhysEntry       OBJECT-TYPE
             SYNTAX          AdslAtucPhysEntry
             MAX-ACCESS      not-accessible
             STATUS          current
             DESCRIPTION     "An entry in the adslAtucPhysTable."
             INDEX           { ifIndex }
         ::= { adslAtucPhysTable 1 }

         AdslAtucPhysEntry ::=
             SEQUENCE {
             adslAtucInvSerialNumber         SnmpAdminString,
             adslAtucInvVendorID             SnmpAdminString,
             adslAtucInvVersionNumber        SnmpAdminString,
             adslAtucCurrSnrMgn              INTEGER,
             adslAtucCurrAtn                 Gauge32,
             adslAtucCurrStatus              BITS,
             adslAtucCurrOutputPwr           INTEGER,
             adslAtucCurrAttainableRate      Gauge32
             }

         -- inventory group
         --
         -- These items should describe the lowest level identifiable
         -- component, be it a stand-alone modem, a card in a rack,
         -- a child-board, etc.
         --
         adslAtucInvSerialNumber OBJECT-TYPE
             SYNTAX      SnmpAdminString (SIZE (0..32))
             MAX-ACCESS  read-only
             STATUS      current
             DESCRIPTION
                 "The vendor specific string that identifies the
                 vendor equipment."
         ::= { adslAtucPhysEntry 1 }

         adslAtucInvVendorID OBJECT-TYPE
             SYNTAX      SnmpAdminString (SIZE (0..16))
             MAX-ACCESS  read-only
             STATUS      current
             DESCRIPTION
                 "The vendor ID code is a copy of the binary
                 vendor identification field defined by the
                 PHY[10] and expressed as readable characters."

             REFERENCE "ANSI T1.413[10]"
         ::= { adslAtucPhysEntry 2 }

         adslAtucInvVersionNumber OBJECT-TYPE
             SYNTAX      SnmpAdminString (SIZE (0..16))
             MAX-ACCESS  read-only
             STATUS      current
             DESCRIPTION
                 "The vendor specific version number sent by this ATU
                 as part of the initialization messages.  It is a copy
                 of the binary version number field defined by the
                 PHY[10] and expressed as readable characters."
             REFERENCE "ANSI T1.413[10]"
         ::= { adslAtucPhysEntry 3 }

         -- current status group
         --
         adslAtucCurrSnrMgn OBJECT-TYPE
             SYNTAX      INTEGER (-640..640)
             UNITS       "tenth dB"
             MAX-ACCESS  read-only
             STATUS      current
             DESCRIPTION
                 "Noise Margin as seen by this ATU with respect to its
                 received signal in tenth dB."
         ::= { adslAtucPhysEntry 4 }

         adslAtucCurrAtn OBJECT-TYPE
             SYNTAX      Gauge32(0..630)
             UNITS       "tenth dB"
             MAX-ACCESS  read-only
             STATUS      current
             DESCRIPTION
                 "Measured difference in the total power transmitted by
                 the peer ATU and the total power received by this ATU."
         ::= { adslAtucPhysEntry 5 }

        adslAtucCurrStatus OBJECT-TYPE
             SYNTAX      BITS {
                               noDefect(0),
                               lossOfFraming(1),
                               lossOfSignal(2),
                               lossOfPower(3),
                               lossOfSignalQuality(4),
                               lossOfLink(5),
                               dataInitFailure(6),
                               configInitFailure(7),
                               protocolInitFailure(8),
                               noPeerAtuPresent(9)
                              }
             MAX-ACCESS  read-only
             STATUS      current
             DESCRIPTION
                 "Indicates current state of the ATUC line.  This is a
                 bit-map of possible conditions.  The various bit
                 positions are:

          0      noDefect             There no defects on the line

          1      lossOfFraming        ATUC failure due to not
                                      receiving valid frame.

          2      lossOfSignal         ATUC failure due to not
                                      receiving signal.

          3      lossOfPower          ATUC failure due to loss of
                                      power.
                                      Note: the Agent may still
                                      function.

          4      lossOfSignalQuality  Loss of Signal Quality is
                                      declared when the Noise Margin
                                      falls below the Minimum Noise
                                      Margin, or the bit-error-rate
                                      exceeds 10^-7.

          5      lossOfLink           ATUC failure due to inability
                                      to link with ATUR.

          6      dataInitFailure      ATUC failure during
                                      initialization due to bit
                                      errors corrupting startup
                                      exchange data.

          7      configInitFailure    ATUC failure during
                                      initialization due to peer
                                      ATU not able to support
                                      requested configuration

          8      protocolInitFailure  ATUC failure during
                                      initialization due to
                                      incompatible protocol used by
                                      the peer ATU.

          9      noPeerAtuPresent     ATUC failure during
                                      initialization due to no
                                      activation sequence detected
                                      from peer ATU.

                 This is intended to supplement ifOperStatus."
         ::= { adslAtucPhysEntry 6 }

         adslAtucCurrOutputPwr OBJECT-TYPE
             SYNTAX      INTEGER (-310..310)
             UNITS       "tenth dBm"
             MAX-ACCESS  read-only
             STATUS      current
             DESCRIPTION
                 "Measured total output power transmitted by this ATU.
                 This is the measurement that was reported during
                 the last activation sequence."
         ::= { adslAtucPhysEntry 7 }

         adslAtucCurrAttainableRate OBJECT-TYPE
             SYNTAX      Gauge32
             UNITS       "bps"
             MAX-ACCESS  read-only
             STATUS      current
             DESCRIPTION
                 "Indicates the maximum currently attainable data rate
                 by the ATU.  This value will be equal or greater than
                 the current line rate."
         ::= { adslAtucPhysEntry 8 }

         adslAturPhysTable        OBJECT-TYPE
             SYNTAX          SEQUENCE OF AdslAturPhysEntry
             MAX-ACCESS      not-accessible
             STATUS          current
             DESCRIPTION
                 "This table provides one row for each ATUR
                 Each row contains the Physical Layer Parameters
                 table for that ATUR. ADSL physical interfaces are
                 those ifEntries where ifType is equal to adsl(94)."
         ::= { adslMibObjects 3 }

         adslAturPhysEntry       OBJECT-TYPE
             SYNTAX          AdslAturPhysEntry
             MAX-ACCESS      not-accessible
             STATUS          current
             DESCRIPTION     "An entry in the adslAturPhysTable."
             INDEX           { ifIndex }
         ::= { adslAturPhysTable 1 }

         AdslAturPhysEntry ::=
             SEQUENCE {
             adslAturInvSerialNumber         SnmpAdminString,
             adslAturInvVendorID             SnmpAdminString,
             adslAturInvVersionNumber        SnmpAdminString,
             adslAturCurrSnrMgn              INTEGER,
             adslAturCurrAtn                 Gauge32,
             adslAturCurrStatus              BITS,
             adslAturCurrOutputPwr           INTEGER,
             adslAturCurrAttainableRate      Gauge32
             }

         -- inventory group
         --
         adslAturInvSerialNumber OBJECT-TYPE
             SYNTAX      SnmpAdminString (SIZE (0..32))
             MAX-ACCESS  read-only
             STATUS      current
             DESCRIPTION
                 "The vendor specific string that identifies the
                 vendor equipment."
         ::= { adslAturPhysEntry 1 }

         adslAturInvVendorID OBJECT-TYPE
             SYNTAX      SnmpAdminString (SIZE (0..16))
             MAX-ACCESS  read-only
             STATUS      current
             DESCRIPTION
                 "The vendor ID code is a copy of the binary
                 vendor identification field defined by the
                 PHY[10] and expressed as readable characters."
             REFERENCE "ANSI T1.413"
         ::= { adslAturPhysEntry 2 }

         adslAturInvVersionNumber OBJECT-TYPE
             SYNTAX      SnmpAdminString (SIZE (0..16))
             MAX-ACCESS  read-only
             STATUS      current
             DESCRIPTION
                 "The vendor specific version number sent by this ATU
                 as part of the initialization messages.  It is a copy
                 of the binary version number field defined by the
                 PHY[10] and expressed as readable characters."
             REFERENCE "ANSI T1.413"
         ::= { adslAturPhysEntry 3 }

         -- current status group
         --
         adslAturCurrSnrMgn OBJECT-TYPE
             SYNTAX      INTEGER (-640..640)
             UNITS       "tenth dB"
             MAX-ACCESS  read-only
             STATUS      current
             DESCRIPTION
                 "Noise Margin as seen by this ATU with respect to its
                 received signal in tenth dB."
         ::= { adslAturPhysEntry 4 }

         adslAturCurrAtn OBJECT-TYPE
             SYNTAX      Gauge32(0..630)
             UNITS       "tenth dB"
             MAX-ACCESS  read-only
             STATUS      current
             DESCRIPTION
                 "Measured difference in the total power transmitted by
                 the peer ATU and the total power received by this ATU."
         ::= { adslAturPhysEntry 5 }

        adslAturCurrStatus OBJECT-TYPE
             SYNTAX     BITS {
                              noDefect(0),
                              lossOfFraming(1),
                              lossOfSignal(2),
                              lossOfPower(3),
                              lossOfSignalQuality(4)
                             }
             MAX-ACCESS  read-only
             STATUS      current
             DESCRIPTION
                 "Indicates current state of the ATUR line.  This is a
                 bit-map of possible conditions.  Due to the isolation
                 of the ATUR when line problems occur, many state
                 conditions like loss of power, loss of quality signal,
                 and initialization errors,  can not be determined.
                 While trouble shooting ATUR, also use object,
                 adslAtucCurrStatus.  The various bit positions are:

          0      noDefect             There no defects on the line

          1      lossOfFraming        ATUR failure due to not
                                      receiving valid frame

          2      lossOfSignal         ATUR failure due to not
                                      receiving signal

          3      lossOfPower          ATUR failure due to loss of
                                      power

          4      lossOfSignalQuality  Loss of Signal Quality is
                                      declared when the Noise Margin
                                      falls below the Minimum Noise
                                      Margin, or the
                                      bit-error-rate exceeds 10^-7.

                 This is intended to supplement ifOperStatus."
         ::= { adslAturPhysEntry 6 }

         adslAturCurrOutputPwr OBJECT-TYPE
             SYNTAX      INTEGER (-310..310)
             UNITS       "tenth dBm"
             MAX-ACCESS  read-only
             STATUS      current
             DESCRIPTION
                 "Measured total output power transmitted by this ATU.
                 This is the measurement that was reported during
                 the last activation sequence."
         ::= { adslAturPhysEntry 7 }

         adslAturCurrAttainableRate OBJECT-TYPE
             SYNTAX      Gauge32
             UNITS       "bps"
             MAX-ACCESS  read-only
             STATUS      current
             DESCRIPTION
                 "Indicates the maximum currently attainable data rate
                 by the ATU.  This value will be equal or greater than
                 the current line rate."
         ::= { adslAturPhysEntry 8 }

         adslAtucChanTable       OBJECT-TYPE
             SYNTAX          SEQUENCE OF AdslAtucChanEntry
             MAX-ACCESS      not-accessible
             STATUS          current
             DESCRIPTION
                 "This table provides one row for each ATUC channel.
                 ADSL channel interfaces are those ifEntries
                 where ifType is equal to adslInterleave(124)
                 or adslFast(125)."
         ::= { adslMibObjects 4 }

         adslAtucChanEntry       OBJECT-TYPE
             SYNTAX          AdslAtucChanEntry
             MAX-ACCESS      not-accessible
             STATUS          current
             DESCRIPTION     "An entry in the adslAtucChanTable."
             INDEX           { ifIndex }
         ::= { adslAtucChanTable 1 }

         AdslAtucChanEntry ::=
             SEQUENCE {
             adslAtucChanInterleaveDelay     Gauge32,
             adslAtucChanCurrTxRate          Gauge32,
             adslAtucChanPrevTxRate          Gauge32,
             adslAtucChanCrcBlockLength      Gauge32
             }

         -- current group
         --
         adslAtucChanInterleaveDelay OBJECT-TYPE
             SYNTAX      Gauge32
             UNITS       "milli-seconds"
             MAX-ACCESS  read-only
             STATUS      current
             DESCRIPTION
                 "Interleave Delay for this channel.

                 Interleave delay applies only to the
                 interleave channel and defines the mapping
                 (relative spacing) between subsequent input
                 bytes at the interleaver input and their placement
                 in the bit stream at the interleaver output.
                 Larger numbers provide greater separation between
                 consecutive input bytes in the output bit stream
                 allowing for improved impulse noise immunity at
                 the expense of payload latency.

                 In the case where the ifType is Fast(125), use
                 noSuchObject."
         ::= { adslAtucChanEntry 1 }

         adslAtucChanCurrTxRate  OBJECT-TYPE
             SYNTAX      Gauge32
             UNITS       "bps"
             MAX-ACCESS  read-only
             STATUS      current
             DESCRIPTION
                 "Actual transmit rate on this channel."
         ::= { adslAtucChanEntry 2 }

         adslAtucChanPrevTxRate OBJECT-TYPE
             SYNTAX      Gauge32
             UNITS        "bps"
             MAX-ACCESS  read-only
             STATUS      current
             DESCRIPTION
                 "The rate at the time of the last
                 adslAtucRateChangeTrap event. It is also set at
                 initialization to prevent a trap being sent.

                 Rate changes less than adslAtucThresh(*)RateDown
                 or less than adslAtucThresh(*)RateUp will not
                 cause a trap or cause this object to change.
                 (*) == Fast or Interleave.
                 See AdslLineAlarmConfProfileEntry."
         ::= { adslAtucChanEntry 3 }

         adslAtucChanCrcBlockLength OBJECT-TYPE
             SYNTAX      Gauge32
             UNITS        "byte"
             MAX-ACCESS  read-only
             STATUS      current
             DESCRIPTION
                 "Indicates the length of the channel data-block
                 on which the CRC operates.  Refer to Line Code
                 Specific MIBs, [11] and [12] for more
                 information."
         ::= { adslAtucChanEntry 4 }
         
        adslAturChanTable       OBJECT-TYPE
             SYNTAX          SEQUENCE OF AdslAturChanEntry
             MAX-ACCESS      not-accessible
             STATUS          current
             DESCRIPTION
                 "This table provides one row for each ATUR channel.
                 ADSL channel interfaces are those ifEntries
                 where ifType is equal to adslInterleave(124)
                 or adslFast(125)."
         ::= { adslMibObjects 5 }
 
         adslAturChanEntry       OBJECT-TYPE
             SYNTAX          AdslAturChanEntry
             MAX-ACCESS      not-accessible
             STATUS          current
             DESCRIPTION     "An entry in the adslAturChanTable."
             INDEX           { ifIndex }
         ::= { adslAturChanTable 1 }

         AdslAturChanEntry ::=
             SEQUENCE {
             adslAturChanInterleaveDelay     Gauge32,
             adslAturChanCurrTxRate          Gauge32,
             adslAturChanPrevTxRate          Gauge32,
             adslAturChanCrcBlockLength      Gauge32
             }

         -- current group
         --
         adslAturChanInterleaveDelay OBJECT-TYPE
             SYNTAX      Gauge32
             UNITS       "milli-seconds"
             MAX-ACCESS  read-only
             STATUS      current
             DESCRIPTION
                 "Interleave Delay for this channel.

                 Interleave delay applies only to the
                 interleave channel and defines the mapping
                 (relative spacing) between subsequent input
                 bytes at the interleaver input and their placement
                 in the bit stream at the interleaver output.
                 Larger numbers provide greater separation between
                 consecutive input bytes in the output bit stream
                 allowing for improved impulse noise immunity at
                 the expense of payload latency.

                 In the case where the ifType is Fast(125), use
                 noSuchObject."
         ::= { adslAturChanEntry 1 }

         adslAturChanCurrTxRate  OBJECT-TYPE
             SYNTAX      Gauge32
             UNITS       "bps"
             MAX-ACCESS  read-only
             STATUS      current
             DESCRIPTION
                 "Actual transmit rate on this channel."
         ::= { adslAturChanEntry 2 }

         adslAturChanPrevTxRate OBJECT-TYPE
             SYNTAX      Gauge32
             UNITS       "bps"
             MAX-ACCESS  read-only
             STATUS      current
             DESCRIPTION
                "The rate at the time of the last
                 adslAturRateChangeTrap event. It is also set at
                 initialization to prevent a trap being sent.
                 Rate changes less than adslAturThresh(*)RateDown
                 or less than adslAturThresh(*)RateUp will not
                 cause a trap or cause this object to change.
                 (*) == Fast or Interleave.
                 See AdslLineAlarmConfProfileEntry."
         ::= { adslAturChanEntry 3 }

         adslAturChanCrcBlockLength OBJECT-TYPE
             SYNTAX      Gauge32
             MAX-ACCESS  read-only
             STATUS      current
             DESCRIPTION
                 "Indicates the length of the channel data-block
                 on which the CRC operates.  Refer to Line Code
                 Specific MIBs, [11] and [12] for more
                 information."
         ::= { adslAturChanEntry 4 }

         adslAtucPerfDataTable   OBJECT-TYPE
             SYNTAX          SEQUENCE OF AdslAtucPerfDataEntry
             MAX-ACCESS      not-accessible
             STATUS          current
             DESCRIPTION
                 "This table provides one row for each ATUC.
                 ADSL physical interfaces are
                 those ifEntries where ifType is equal to adsl(94)."
         ::= { adslMibObjects 6 }

         adslAtucPerfDataEntry       OBJECT-TYPE
             SYNTAX          AdslAtucPerfDataEntry
             MAX-ACCESS      not-accessible
             STATUS          current
             DESCRIPTION     "An entry in adslAtucPerfDataTable."
             INDEX           { ifIndex }
         ::= { adslAtucPerfDataTable 1 }

         AdslAtucPerfDataEntry ::=
             SEQUENCE {
             adslAtucPerfLofs                 Counter32,
             adslAtucPerfLoss                 Counter32,
             adslAtucPerfLols                 Counter32,
             adslAtucPerfLprs                 Counter32,
             adslAtucPerfESs                  Counter32,
             adslAtucPerfInits                Counter32,
             adslAtucPerfValidIntervals       INTEGER,
             adslAtucPerfInvalidIntervals     INTEGER,
             adslAtucPerfCurr15MinTimeElapsed AdslPerfTimeElapsed,
             adslAtucPerfCurr15MinLofs        PerfCurrentCount,
             adslAtucPerfCurr15MinLoss        PerfCurrentCount,
             adslAtucPerfCurr15MinLols        PerfCurrentCount,
             adslAtucPerfCurr15MinLprs        PerfCurrentCount,
             adslAtucPerfCurr15MinESs         PerfCurrentCount,
             adslAtucPerfCurr15MinInits       PerfCurrentCount,
             adslAtucPerfCurr1DayTimeElapsed  AdslPerfTimeElapsed,
             adslAtucPerfCurr1DayLofs         AdslPerfCurrDayCount,
             adslAtucPerfCurr1DayLoss         AdslPerfCurrDayCount,
             adslAtucPerfCurr1DayLols         AdslPerfCurrDayCount,
             adslAtucPerfCurr1DayLprs         AdslPerfCurrDayCount,
             adslAtucPerfCurr1DayESs          AdslPerfCurrDayCount,
             adslAtucPerfCurr1DayInits        AdslPerfCurrDayCount,
             adslAtucPerfPrev1DayMoniSecs     INTEGER,
             adslAtucPerfPrev1DayLofs         AdslPerfPrevDayCount,
             adslAtucPerfPrev1DayLoss         AdslPerfPrevDayCount,
             adslAtucPerfPrev1DayLols         AdslPerfPrevDayCount,
             adslAtucPerfPrev1DayLprs         AdslPerfPrevDayCount,
             adslAtucPerfPrev1DayESs          AdslPerfPrevDayCount,
             adslAtucPerfPrev1DayInits        AdslPerfPrevDayCount
             }

         -- Event Counters
         --
         -- Also see adslAtucIntervalTable for 15 minute interval
         -- elapsed counters.
         --
         adslAtucPerfLofs OBJECT-TYPE
             SYNTAX      Counter32
             MAX-ACCESS  read-only
             STATUS      current
             DESCRIPTION
                 "Count of the number of Loss of Framing failures since
                 agent reset."
         ::= { adslAtucPerfDataEntry 1 }

         adslAtucPerfLoss  OBJECT-TYPE
             SYNTAX      Counter32
             MAX-ACCESS  read-only
             STATUS      current
             DESCRIPTION
                 "Count of the number of Loss of Signal failures since
                 agent reset."
         ::= { adslAtucPerfDataEntry 2 }

         adslAtucPerfLols OBJECT-TYPE
             SYNTAX      Counter32
             MAX-ACCESS  read-only
             STATUS      current
             DESCRIPTION
                 "Count of the number of Loss of Link failures since
                 agent reset."
         ::= { adslAtucPerfDataEntry 3 }

         adslAtucPerfLprs OBJECT-TYPE
             SYNTAX      Counter32
             MAX-ACCESS  read-only
             STATUS      current
             DESCRIPTION
                 "Count of the number of Loss of Power failures since
                 agent reset."
         ::= { adslAtucPerfDataEntry 4 }

         adslAtucPerfESs OBJECT-TYPE
             SYNTAX      Counter32
             MAX-ACCESS  read-only
             STATUS      current
             DESCRIPTION
                 "Count of the number of Errored Seconds since agent
                 reset.  The errored second parameter is a count of
                 one-second intervals containing one or more crc
                 anomalies, or one or more los or sef defects."
         ::= { adslAtucPerfDataEntry 5 }

         adslAtucPerfInits OBJECT-TYPE
             SYNTAX      Counter32
             MAX-ACCESS  read-only
             STATUS      current
             DESCRIPTION
                 "Count of the line initialization attempts since
                 agent reset. Includes both successful and failed
                 attempts."
         ::= { adslAtucPerfDataEntry 6 }

         -- general 15 min interval information
         --

         adslAtucPerfValidIntervals OBJECT-TYPE
             SYNTAX      INTEGER(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adslAtucPerfDataEntry 7 }

         adslAtucPerfInvalidIntervals OBJECT-TYPE
             SYNTAX      INTEGER(0..96)
             MAX-ACCESS  read-only
             STATUS      current
             DESCRIPTION
                 "The number of intervals in the range from
                 0 to the value of adslAtucPerfValidIntervals
                 for which no data is available. This object
                 will typically be zero except in cases where
                 the data for some intervals are not available
                 (e.g., in proxy situations)."
         ::= { adslAtucPerfDataEntry 8 }

         -- 15 min current performance group
         --
         adslAtucPerfCurr15MinTimeElapsed OBJECT-TYPE
             SYNTAX      AdslPerfTimeElapsed(0..899)
             UNITS       "seconds"
             MAX-ACCESS  read-only
             STATUS      current
             DESCRIPTION
                 "Total elapsed seconds in this interval."
         ::= { adslAtucPerfDataEntry 9 }

         adslAtucPerfCurr15MinLofs OBJECT-TYPE
             SYNTAX      PerfCurrentCount
             UNITS       "seconds"
             MAX-ACCESS  read-only
             STATUS      current
             DESCRIPTION
                 "Count of seconds in the current 15 minute interval
                 when there was Loss of Framing."
         ::= { adslAtucPerfDataEntry 10 }

         adslAtucPerfCurr15MinLoss  OBJECT-TYPE
             SYNTAX      PerfCurrentCount
             UNITS       "seconds"
             MAX-ACCESS  read-only
             STATUS      current
             DESCRIPTION
                 "Count of seconds in the current 15 minute interval
                 when there was Loss of Signal."
         ::= { adslAtucPerfDataEntry 11 }

         adslAtucPerfCurr15MinLols  OBJECT-TYPE
             SYNTAX      PerfCurrentCount
             UNITS       "seconds"
             MAX-ACCESS  read-only
             STATUS      current
             DESCRIPTION
                 "Count of seconds in the current 15 minute interval
                 when there was Loss of Link."
         ::= { adslAtucPerfDataEntry 12 }

         adslAtucPerfCurr15MinLprs  OBJECT-TYPE
             SYNTAX      PerfCurrentCount
             UNITS       "seconds"
             MAX-ACCESS  read-only
             STATUS      current
             DESCRIPTION
                 "Count of seconds in the current 15 minute interval
                 when there was Loss of Power."
         ::= { adslAtucPerfDataEntry 13 }

         adslAtucPerfCurr15MinESs OBJECT-TYPE
             SYNTAX      PerfCurrentCount
             UNITS       "seconds"
             MAX-ACCESS  read-only
             STATUS      current
             DESCRIPTION
                 "Count of Errored Seconds in the current 15 minute
                 interval.  The errored second parameter is a count of
                 one-second intervals containing one or more crc
                 anomalies, or one or more los or sef defects."
         ::= { adslAtucPerfDataEntry 14 }

         adslAtucPerfCurr15MinInits  OBJECT-TYPE
             SYNTAX      PerfCurrentCount
             MAX-ACCESS  read-only
             STATUS      current
             DESCRIPTION
                 "Count of the line initialization attempts in the
                 current 15 minute interval. Includes both successful
                 and failed attempts."
         ::= { adslAtucPerfDataEntry 15 }

         -- 1-day current and previous performance group
         --
         adslAtucPerfCurr1DayTimeElapsed OBJECT-TYPE
             SYNTAX      AdslPerfTimeElapsed(0..86399)
             UNITS       "seconds"
             MAX-ACCESS  read-only
             STATUS      current
             DESCRIPTION
                 "Number of seconds that have elapsed since the
                 beginning of the current 1-day interval."
         ::= { adslAtucPerfDataEntry 16 }

         adslAtucPerfCurr1DayLofs  OBJECT-TYPE
             SYNTAX      AdslPerfCurrDayCount
             UNITS       "seconds"
             MAX-ACCESS  read-only
             STATUS      current
             DESCRIPTION
                 "Count of the number of seconds when there was Loss of
                 Framing during the current day as measured by
                 adslAtucPerfCurr1DayTimeElapsed."
         ::= { adslAtucPerfDataEntry 17 }

         adslAtucPerfCurr1DayLoss  OBJECT-TYPE
             SYNTAX      AdslPerfCurrDayCount
             UNITS       "seconds"
             MAX-ACCESS  read-only
             STATUS      current
             DESCRIPTION
                 "Count of the number of seconds when there was Loss of
                 Signal during the current day as measured by
                 adslAtucPerfCurr1DayTimeElapsed."
         ::= { adslAtucPerfDataEntry 18 }

         adslAtucPerfCurr1DayLols  OBJECT-TYPE
             SYNTAX      AdslPerfCurrDayCount
             UNITS       "seconds"
             MAX-ACCESS  read-only
             STATUS      current
             DESCRIPTION
                 "Count of the number of seconds when there was Loss of
                 Link during the current day as measured by
                 adslAtucPerfCurr1DayTimeElapsed."
         ::= { adslAtucPerfDataEntry 19 }

         adslAtucPerfCurr1DayLprs  OBJECT-TYPE
             SYNTAX      AdslPerfCurrDayCount
             UNITS       "seconds"
             MAX-ACCESS  read-only
             STATUS      current
             DESCRIPTION
                 "Count of the number of seconds when there was Loss of
                 Power during the current day as measured by
                 adslAtucPerfCurr1DayTimeElapsed."
         ::= { adslAtucPerfDataEntry 20 }

         adslAtucPerfCurr1DayESs OBJECT-TYPE
             SYNTAX      AdslPerfCurrDayCount
             UNITS       "seconds"
             MAX-ACCESS  read-only
             STATUS      current
             DESCRIPTION
                 "Count of Errored Seconds during the current day as
                 measured by adslAtucPerfCurr1DayTimeElapsed.
                 The errored second parameter is a count of
                 one-second intervals containing one or more crc
                 anomalies, or one or more los or sef defects."
         ::= { adslAtucPerfDataEntry 21 }

         adslAtucPerfCurr1DayInits  OBJECT-TYPE
             SYNTAX      AdslPerfCurrDayCount
             MAX-ACCESS  read-only
             STATUS      current
             DESCRIPTION
                 "Count of the line initialization attempts in the
                 day as measured by adslAtucPerfCurr1DayTimeElapsed.
                 Includes both successful and failed attempts."
         ::= { adslAtucPerfDataEntry 22 }

         adslAtucPerfPrev1DayMoniSecs OBJECT-TYPE
             SYNTAX      INTEGER(0..86400)
             UNITS       "seconds"
             MAX-ACCESS  read-only
             STATUS      current
             DESCRIPTION
                 "The amount of time in the previous 1-day interval
                 over which the performance monitoring information
                 is actually counted. This value will be the same as
                 the interval duration except in a situation where
                 performance monitoring data could not be collected
                 for any reason."
         ::= { adslAtucPerfDataEntry 23 }

         adslAtucPerfPrev1DayLofs  OBJECT-TYPE
             SYNTAX      AdslPerfPrevDayCount
             UNITS       "seconds"
             MAX-ACCESS  read-only
             STATUS      current
             DESCRIPTION
                 "Count of seconds in the interval when there was
                 Loss of Framing within the most recent previous
                 1-day period."
         ::= { adslAtucPerfDataEntry 24 }

         adslAtucPerfPrev1DayLoss  OBJECT-TYPE
             SYNTAX      AdslPerfPrevDayCount
             UNITS       "seconds"
             MAX-ACCESS  read-only
             STATUS      current
             DESCRIPTION
                 "Count of seconds in the interval when there was
                 Loss of Signal within the most recent previous
                 1-day period."
         ::= { adslAtucPerfDataEntry 25 }

         adslAtucPerfPrev1DayLols  OBJECT-TYPE
             SYNTAX      AdslPerfPrevDayCount
             UNITS       "seconds"
             MAX-ACCESS  read-only
             STATUS      current
             DESCRIPTION
                 "Count of seconds in the interval when there was
                 Loss of Link within the most recent previous
                 1-day period."
         ::= { adslAtucPerfDataEntry 26 }

         adslAtucPerfPrev1DayLprs  OBJECT-TYPE
             SYNTAX      AdslPerfPrevDayCount
             UNITS       "seconds"
             MAX-ACCESS  read-only
             STATUS      current
             DESCRIPTION
                 "Count of seconds in the interval when there was
                 Loss of Power within the most recent previous
                 1-day period."
         ::= { adslAtucPerfDataEntry 27 }

         adslAtucPerfPrev1DayESs OBJECT-TYPE
             SYNTAX      AdslPerfPrevDayCount
             UNITS       "seconds"
             MAX-ACCESS  read-only
             STATUS      current
             DESCRIPTION
                 "Count of Errored Seconds within the most recent
                 previous 1-day period. The errored second parameter is
                 a count of one-second intervals containing one or more
                 crc anomalies, or one or more los or sef defects."
         ::= { adslAtucPerfDataEntry 28 }

         adslAtucPerfPrev1DayInits  OBJECT-TYPE
             SYNTAX      AdslPerfPrevDayCount
             MAX-ACCESS  read-only
             STATUS      current
             DESCRIPTION
                 "Count of the line initialization attempts in the most
                 recent previous 1-day period. Includes both successful
                 and failed attempts."
         ::= { adslAtucPerfDataEntry 29 }

         adslAturPerfDataTable   OBJECT-TYPE
             SYNTAX          SEQUENCE OF AdslAturPerfDataEntry
             MAX-ACCESS      not-accessible
             STATUS          current
             DESCRIPTION
                 "This table provides one row for each ATUR.
                 ADSL physical interfaces are
                 those ifEntries where ifType is equal to adsl(94)."
         ::= { adslMibObjects 7 }

         adslAturPerfDataEntry       OBJECT-TYPE
             SYNTAX          AdslAturPerfDataEntry
             MAX-ACCESS      not-accessible
             STATUS          current
             DESCRIPTION     "An entry in adslAturPerfDataTable."
             INDEX           { ifIndex }
         ::= { adslAturPerfDataTable 1 }

         AdslAturPerfDataEntry ::=
             SEQUENCE {
             adslAturPerfLofs                 Counter32,
             adslAturPerfLoss                 Counter32,
             adslAturPerfLprs                 Counter32,
             adslAturPerfESs                  Counter32,
             adslAturPerfValidIntervals       INTEGER,
             adslAturPerfInvalidIntervals     INTEGER,
             adslAturPerfCurr15MinTimeElapsed AdslPerfTimeElapsed,
             adslAturPerfCurr15MinLofs        PerfCurrentCount,
             adslAturPerfCurr15MinLoss        PerfCurrentCount,
             adslAturPerfCurr15MinLprs        PerfCurrentCount,
             adslAturPerfCurr15MinESs         PerfCurrentCount,
             adslAturPerfCurr1DayTimeElapsed  AdslPerfTimeElapsed,
             adslAturPerfCurr1DayLofs         AdslPerfCurrDayCount,
             adslAturPerfCurr1DayLoss         AdslPerfCurrDayCount,
             adslAturPerfCurr1DayLprs         AdslPerfCurrDayCount,
             adslAturPerfCurr1DayESs          AdslPerfCurrDayCount,
             adslAturPerfPrev1DayMoniSecs     INTEGER,
             adslAturPerfPrev1DayLofs         AdslPerfPrevDayCount,
             adslAturPerfPrev1DayLoss         AdslPerfPrevDayCount,
             adslAturPerfPrev1DayLprs         AdslPerfPrevDayCount,
             adslAturPerfPrev1DayESs          AdslPerfPrevDayCount
             }

         -- Event (Raw) Counters
         --
         -- Also see adslAturIntervalTable for 15 minute interval
         -- elapsed counters.
         --
         adslAturPerfLofs OBJECT-TYPE
             SYNTAX      Counter32
             UNITS       "seconds"
             MAX-ACCESS  read-only
             STATUS      current
             DESCRIPTION
                 "Count of the number of Loss of Framing failures since
                 agent reset."
         ::= { adslAturPerfDataEntry 1 }

         adslAturPerfLoss  OBJECT-TYPE
             SYNTAX      Counter32
             UNITS       "seconds"
             MAX-ACCESS  read-only
             STATUS      current
             DESCRIPTION
                 "Count of the number of Loss of Signal failures since
                 agent reset."
         ::= { adslAturPerfDataEntry 2 }

        adslAturPerfLprs  OBJECT-TYPE
             SYNTAX      Counter32
             UNITS       "seconds"
             MAX-ACCESS  read-only
             STATUS      current
             DESCRIPTION
                 "Count of the number of Loss of Power failures since
                 agent reset."
         ::= { adslAturPerfDataEntry 3 }

         adslAturPerfESs  OBJECT-TYPE
             SYNTAX      Counter32
             UNITS       "seconds"
             MAX-ACCESS  read-only
             STATUS      current
             DESCRIPTION
                 "Count of the number of Errored Seconds since agent
                 reset.  The errored second parameter is a count of
                 one-second intervals containing one or more crc
                 anomalies, or one or more los or sef defects."
         ::= { adslAturPerfDataEntry 4 }

         -- general 15 min interval information
         --
         adslAturPerfValidIntervals OBJECT-TYPE
             SYNTAX      INTEGER(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adslAturPerfDataEntry 5 }

         adslAturPerfInvalidIntervals OBJECT-TYPE
             SYNTAX      INTEGER(0..96)
             MAX-ACCESS  read-only
             STATUS      current
             DESCRIPTION
                 "The number of intervals in the range from
                 0 to the value of adslAturPerfValidIntervals
                 for which no data is available. This object
                 will typically be zero except in cases where
                 the data for some intervals are not available
                 (e.g., in proxy situations)."
         ::= { adslAturPerfDataEntry 6 }

         -- 15 min current performance group
         --
         adslAturPerfCurr15MinTimeElapsed OBJECT-TYPE
             SYNTAX      AdslPerfTimeElapsed(0..899)
             UNITS       "seconds"
             MAX-ACCESS  read-only
             STATUS      current
             DESCRIPTION
                 "Total elapsed seconds in this interval."
         ::= { adslAturPerfDataEntry 7 }

         adslAturPerfCurr15MinLofs OBJECT-TYPE
             SYNTAX      PerfCurrentCount
             UNITS       "seconds"
             MAX-ACCESS  read-only
             STATUS      current
             DESCRIPTION
                 "Count of seconds in the current 15 minute interval
                 when there was Loss of Framing."
         ::= { adslAturPerfDataEntry 8 }

         adslAturPerfCurr15MinLoss  OBJECT-TYPE
             SYNTAX      PerfCurrentCount
             UNITS       "seconds"
             MAX-ACCESS  read-only
             STATUS      current
             DESCRIPTION
                 "Count of seconds in the current 15 minute interval
                 when there was Loss of Signal."
         ::= { adslAturPerfDataEntry 9 }

         adslAturPerfCurr15MinLprs  OBJECT-TYPE
             SYNTAX      PerfCurrentCount
             UNITS       "seconds"
             MAX-ACCESS  read-only
             STATUS      current
             DESCRIPTION
                 "Count of seconds in the current 15 minute interval
                 when there was Loss of Power."
         ::= { adslAturPerfDataEntry 10 }

         adslAturPerfCurr15MinESs OBJECT-TYPE
             SYNTAX      PerfCurrentCount
             UNITS       "seconds"
             MAX-ACCESS  read-only
             STATUS      current
             DESCRIPTION
                "Count of Errored Seconds in the current 15 minute
                interval.  The errored second parameter is a count of
                one-second intervals containing one or more crc
                anomalies, or one or more los or sef defects."

         ::= { adslAturPerfDataEntry 11 }

         -- 1-day current and previous performance group
         --
         adslAturPerfCurr1DayTimeElapsed OBJECT-TYPE
             SYNTAX      AdslPerfTimeElapsed(0..86399)
             UNITS       "seconds"
             MAX-ACCESS  read-only
             STATUS      current
             DESCRIPTION
                 "Number of seconds that have elapsed since the
                 beginning of the current 1-day interval."
         ::= { adslAturPerfDataEntry 12 }

         adslAturPerfCurr1DayLofs  OBJECT-TYPE
             SYNTAX      AdslPerfCurrDayCount
             UNITS       "seconds"
             MAX-ACCESS  read-only
             STATUS      current
             DESCRIPTION
                 "Count of the number of seconds when there was Loss
                 of Framing during the current day as measured by
                 adslAturPerfCurr1DayTimeElapsed."
         ::= { adslAturPerfDataEntry 13 }

         adslAturPerfCurr1DayLoss  OBJECT-TYPE
             SYNTAX      AdslPerfCurrDayCount
             UNITS       "seconds"
             MAX-ACCESS  read-only
             STATUS      current
             DESCRIPTION
                 "Count of the number of seconds when there was Loss
                 of Signal during the current day as measured by
                 adslAturPerfCurr1DayTimeElapsed."
         ::= { adslAturPerfDataEntry 14 }

         adslAturPerfCurr1DayLprs  OBJECT-TYPE
             SYNTAX      AdslPerfCurrDayCount
             UNITS       "seconds"
             MAX-ACCESS  read-only
             STATUS      current
             DESCRIPTION
                 "Count of the number of seconds when there was Loss
                 of Power during the current day as measured by
                 adslAturPerfCurr1DayTimeElapsed."
         ::= { adslAturPerfDataEntry 15 }

    adslAturPerfCurr1DayESs OBJECT-TYPE
             SYNTAX      AdslPerfCurrDayCount
             UNITS       "seconds"
             MAX-ACCESS  read-only
             STATUS      current
             DESCRIPTION
                 "Count of Errored Seconds during the current day as
                 measured by adslAturPerfCurr1DayTimeElapsed.
                 The errored second parameter is a count of
                 one-second intervals containing one or more crc
                 anomalies, or one or more los or sef defects."
         ::= { adslAturPerfDataEntry 16 }

         adslAturPerfPrev1DayMoniSecs OBJECT-TYPE
             SYNTAX      INTEGER(0..86400)
             UNITS       "seconds"
             MAX-ACCESS  read-only
             STATUS      current
             DESCRIPTION
                 "The amount of time in the previous 1-day interval
                 over which the performance monitoring information
                 is actually counted. This value will be the same as
                 the interval duration except in a situation where
                 performance monitoring data could not be collected
                 for any reason."
         ::= { adslAturPerfDataEntry 17 }

         adslAturPerfPrev1DayLofs  OBJECT-TYPE
             SYNTAX      AdslPerfPrevDayCount
             UNITS       "seconds"
             MAX-ACCESS  read-only
             STATUS      current
             DESCRIPTION
                 "Count of seconds in the interval when there was
                 Loss of Framing within the most recent previous
                 1-day period."
         ::= { adslAturPerfDataEntry 18 }

         adslAturPerfPrev1DayLoss  OBJECT-TYPE
             SYNTAX      AdslPerfPrevDayCount
             UNITS       "seconds"
             MAX-ACCESS  read-only
             STATUS      current
             DESCRIPTION
                 "Count of seconds in the interval when there was
                 Loss of Signal within the most recent previous
                 1-day period."
         ::= { adslAturPerfDataEntry 19 }

         adslAturPerfPrev1DayLprs  OBJECT-TYPE
             SYNTAX      AdslPerfPrevDayCount
             UNITS       "seconds"
             MAX-ACCESS  read-only
             STATUS      current
             DESCRIPTION
                 "Count of seconds in the interval when there was
                 Loss of Power within the most recent previous
                 1-day period."
         ::= { adslAturPerfDataEntry 20 }

         adslAturPerfPrev1DayESs OBJECT-TYPE
             SYNTAX      AdslPerfPrevDayCount
             UNITS       "seconds"
             MAX-ACCESS  read-only
             STATUS      current
             DESCRIPTION
                 "Count of Errored Seconds within the most recent
                 previous 1-day period. The errored second parameter is
                 a count of one-second intervals containing one or more
                 crc anomalies, or one or more los or sef defects."
         ::= { adslAturPerfDataEntry 21 }

         adslAtucIntervalTable   OBJECT-TYPE
             SYNTAX          SEQUENCE OF AdslAtucIntervalEntry
             MAX-ACCESS      not-accessible
             STATUS          current
             DESCRIPTION
                 "This table provides one row for each ATUC
                 performance data collection interval.
                 ADSL physical interfaces are
                 those ifEntries where ifType is equal to adsl(94)."
         ::= { adslMibObjects 8 }

         adslAtucIntervalEntry   OBJECT-TYPE
             SYNTAX          AdslAtucIntervalEntry
             MAX-ACCESS      not-accessible
             STATUS          current
             DESCRIPTION     "An entry in the adslAtucIntervalTable."
             INDEX           { ifIndex, adslAtucIntervalNumber }
         ::= { adslAtucIntervalTable 1 }

         AdslAtucIntervalEntry ::=
             SEQUENCE {
             adslAtucIntervalNumber          INTEGER,
             adslAtucIntervalLofs            PerfIntervalCount,
             adslAtucIntervalLoss            PerfIntervalCount,
             adslAtucIntervalLols            PerfIntervalCount,
             adslAtucIntervalLprs            PerfIntervalCount,
             adslAtucIntervalESs             PerfIntervalCount,
             adslAtucIntervalInits           PerfIntervalCount,
             adslAtucIntervalValidData       TruthValue
             }

         adslAtucIntervalNumber OBJECT-TYPE
             SYNTAX      INTEGER(1..96)
             MAX-ACCESS  not-accessible
             STATUS      current
             DESCRIPTION
                 "Performance Data Interval number 1 is the
                 the most recent previous interval; interval
                 96 is 24 hours ago.  Intervals 2..96 are
                 optional."
         ::= { adslAtucIntervalEntry 1 }

         adslAtucIntervalLofs OBJECT-TYPE
             SYNTAX      PerfIntervalCount
             UNITS       "seconds"
             MAX-ACCESS  read-only
             STATUS      current
             DESCRIPTION
                 "Count of seconds in the interval when there was Loss
                 of Framing."
         ::= { adslAtucIntervalEntry 2 }

         adslAtucIntervalLoss  OBJECT-TYPE
             SYNTAX      PerfIntervalCount
             UNITS       "seconds"
             MAX-ACCESS  read-only
             STATUS      current
             DESCRIPTION
                 "Count of seconds in the interval when there was Loss
                 of Signal."
         ::= { adslAtucIntervalEntry 3 }

         adslAtucIntervalLols  OBJECT-TYPE
             SYNTAX      PerfIntervalCount
             UNITS       "seconds"
             MAX-ACCESS  read-only
             STATUS      current
             DESCRIPTION
                 "Count of seconds in the interval when there was Loss
                 of Link."
         ::= { adslAtucIntervalEntry 4 }

         adslAtucIntervalLprs  OBJECT-TYPE
             SYNTAX      PerfIntervalCount
             UNITS       "seconds"
             MAX-ACCESS  read-only
             STATUS      current
             DESCRIPTION
                 "Count of seconds in the interval when there was Loss
                 of Power."
         ::= { adslAtucIntervalEntry 5 }

         adslAtucIntervalESs OBJECT-TYPE
             SYNTAX      PerfIntervalCount
             UNITS       "seconds"
             MAX-ACCESS  read-only
             STATUS      current
             DESCRIPTION
                 "Count of Errored Seconds in the interval.
                 The errored second parameter is a count of
                 one-second intervals containing one or more crc
                 anomalies, or one or more los or sef defects."
         ::= { adslAtucIntervalEntry 6 }

         adslAtucIntervalInits  OBJECT-TYPE
             SYNTAX      PerfIntervalCount
             MAX-ACCESS  read-only
             STATUS      current
             DESCRIPTION
                 "Count of the line initialization attempts
                 during the interval. Includes both successful
                 and failed attempts."
         ::= { adslAtucIntervalEntry 7 }

         adslAtucIntervalValidData OBJECT-TYPE
             SYNTAX TruthValue
             MAX-ACCESS read-only
             STATUS current
             DESCRIPTION
                 "This variable indicates if the data for this
                 interval is valid."
         ::= { adslAtucIntervalEntry 8 }

         adslAturIntervalTable   OBJECT-TYPE
             SYNTAX          SEQUENCE OF AdslAturIntervalEntry
             MAX-ACCESS      not-accessible
             STATUS          current
             DESCRIPTION
                 "This table provides one row for each ATUR
                 performance data collection interval.
                 ADSL physical interfaces are those
                 ifEntries where ifType is equal to adsl(94)."
         ::= { adslMibObjects 9 }

         adslAturIntervalEntry   OBJECT-TYPE
             SYNTAX          AdslAturIntervalEntry
             MAX-ACCESS      not-accessible
             STATUS          current
             DESCRIPTION     "An entry in the adslAturIntervalTable."
             INDEX           { ifIndex, adslAturIntervalNumber }
         ::= { adslAturIntervalTable 1 }

         AdslAturIntervalEntry ::=
             SEQUENCE {
             adslAturIntervalNumber          INTEGER,
             adslAturIntervalLofs            PerfIntervalCount,
             adslAturIntervalLoss            PerfIntervalCount,
             adslAturIntervalLprs            PerfIntervalCount,
             adslAturIntervalESs             PerfIntervalCount,
             adslAturIntervalValidData       TruthValue
             }

         adslAturIntervalNumber OBJECT-TYPE
             SYNTAX      INTEGER(1..96)
             MAX-ACCESS  not-accessible
             STATUS      current
             DESCRIPTION
                 "Performance Data Interval number 1 is the
                 the most recent previous interval; interval
                 96 is 24 hours ago.  Intervals 2..96 are
                 optional."
         ::= { adslAturIntervalEntry 1 }

         adslAturIntervalLofs OBJECT-TYPE
             SYNTAX      PerfIntervalCount
             UNITS       "seconds"
             MAX-ACCESS  read-only
             STATUS      current
             DESCRIPTION
                 "Count of seconds in the interval when there was
                 Loss of Framing."
         ::= { adslAturIntervalEntry 2 }

         adslAturIntervalLoss  OBJECT-TYPE
             SYNTAX      PerfIntervalCount
             UNITS       "seconds"
             MAX-ACCESS  read-only
             STATUS      current
             DESCRIPTION
                 "Count of seconds in the interval when there was
                 Loss of Signal."
         ::= { adslAturIntervalEntry 3 }

         adslAturIntervalLprs  OBJECT-TYPE
             SYNTAX      PerfIntervalCount
             UNITS       "seconds"
             MAX-ACCESS  read-only
             STATUS      current
             DESCRIPTION
                 "Count of seconds in the interval when there was
                 Loss of Power."
         ::= { adslAturIntervalEntry 4 }

         adslAturIntervalESs OBJECT-TYPE
             SYNTAX      PerfIntervalCount
             UNITS       "seconds"
             MAX-ACCESS  read-only
             STATUS      current
             DESCRIPTION
                 "Count of Errored Seconds in the interval.
                 The errored second parameter is a count of
                 one-second intervals containing one or more crc
                 anomalies, or one or more los or sef defects."
         ::= { adslAturIntervalEntry 5 }

         adslAturIntervalValidData OBJECT-TYPE
             SYNTAX TruthValue
             MAX-ACCESS read-only
             STATUS current
             DESCRIPTION
                 "This variable indicates if the data for this
                 interval is valid."
         ::= { adslAturIntervalEntry 6 }

         adslAtucChanPerfDataTable       OBJECT-TYPE
             SYNTAX          SEQUENCE OF AdslAtucChanPerfDataEntry
             MAX-ACCESS      not-accessible
             STATUS          current
             DESCRIPTION
                 "This table provides one row for each ATUC channel.
                 ADSL channel interfaces are those ifEntries
                 where ifType is equal to adslInterleave(124)
                 or adslFast(125)."
         ::= { adslMibObjects 10 }

         adslAtucChanPerfDataEntry       OBJECT-TYPE

             SYNTAX          AdslAtucChanPerfDataEntry
             MAX-ACCESS      not-accessible
             STATUS          current
             DESCRIPTION     "An entry in adslAtucChanPerfDataTable."
             INDEX           { ifIndex }
         ::= { adslAtucChanPerfDataTable 1 }

         AdslAtucChanPerfDataEntry ::=
          SEQUENCE {
          adslAtucChanReceivedBlks                 Counter32,
          adslAtucChanTransmittedBlks              Counter32,
          adslAtucChanCorrectedBlks                Counter32,
          adslAtucChanUncorrectBlks                Counter32,
          adslAtucChanPerfValidIntervals           INTEGER,
          adslAtucChanPerfInvalidIntervals         INTEGER,
          adslAtucChanPerfCurr15MinTimeElapsed     AdslPerfTimeElapsed,
          adslAtucChanPerfCurr15MinReceivedBlks    PerfCurrentCount,
          adslAtucChanPerfCurr15MinTransmittedBlks PerfCurrentCount,
          adslAtucChanPerfCurr15MinCorrectedBlks   PerfCurrentCount,
          adslAtucChanPerfCurr15MinUncorrectBlks   PerfCurrentCount,
          adslAtucChanPerfCurr1DayTimeElapsed      AdslPerfTimeElapsed,
          adslAtucChanPerfCurr1DayReceivedBlks     AdslPerfCurrDayCount,
          adslAtucChanPerfCurr1DayTransmittedBlks  AdslPerfCurrDayCount,
          adslAtucChanPerfCurr1DayCorrectedBlks    AdslPerfCurrDayCount,
          adslAtucChanPerfCurr1DayUncorrectBlks    AdslPerfCurrDayCount,
          adslAtucChanPerfPrev1DayMoniSecs         INTEGER,
          adslAtucChanPerfPrev1DayReceivedBlks     AdslPerfPrevDayCount,
          adslAtucChanPerfPrev1DayTransmittedBlks  AdslPerfPrevDayCount,
          adslAtucChanPerfPrev1DayCorrectedBlks    AdslPerfPrevDayCount,
          adslAtucChanPerfPrev1DayUncorrectBlks    AdslPerfPrevDayCount
         }
         -- performance group

         --
         -- Note: block is intended to be the length of the channel
         --       data-block on which the CRC operates. See
         --       adslAtucChanCrcBlockLength for more information.
         --
         adslAtucChanReceivedBlks OBJECT-TYPE
             SYNTAX      Counter32
             MAX-ACCESS  read-only
             STATUS      current
             DESCRIPTION
                 "Count of all encoded blocks received on this channel
                 since agent reset."
         ::= { adslAtucChanPerfDataEntry 1 }

         adslAtucChanTransmittedBlks  OBJECT-TYPE
             SYNTAX      Counter32
             MAX-ACCESS  read-only
             STATUS      current
             DESCRIPTION
                 "Count of all encoded blocks transmitted on this
                 channel since agent reset."
         ::= { adslAtucChanPerfDataEntry 2 }

         adslAtucChanCorrectedBlks  OBJECT-TYPE
             SYNTAX      Counter32
             MAX-ACCESS  read-only
             STATUS      current
             DESCRIPTION
                 "Count of all blocks received with errors that were
                 corrected since agent reset.  These blocks are passed
                 on as good data."
         ::= { adslAtucChanPerfDataEntry 3 }

         adslAtucChanUncorrectBlks  OBJECT-TYPE
             SYNTAX      Counter32
             MAX-ACCESS  read-only
             STATUS      current
             DESCRIPTION
                 "Count of all blocks received with uncorrectable
                 errors since agent reset."
         ::= { adslAtucChanPerfDataEntry 4 }

         -- general 15 min interval information
         --
         adslAtucChanPerfValidIntervals OBJECT-TYPE
             SYNTAX      INTEGER(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adslAtucChanPerfDataEntry 5 }

         adslAtucChanPerfInvalidIntervals OBJECT-TYPE
             SYNTAX      INTEGER(0..96)
             MAX-ACCESS  read-only
             STATUS      current
             DESCRIPTION
                 "The number of intervals in the range from
                 0 to the value of adslAtucChanPerfValidIntervals
                 for which no data is available. This object
                 will typically be zero except in cases where
                 the data for some intervals are not available
                 (e.g., in proxy situations)."
         ::= { adslAtucChanPerfDataEntry 6 }

         -- 15 min current performance group
         --
         adslAtucChanPerfCurr15MinTimeElapsed OBJECT-TYPE
             SYNTAX      AdslPerfTimeElapsed(0..899)
             UNITS       "seconds"
             MAX-ACCESS  read-only
             STATUS      current
             DESCRIPTION
                 "Total elapsed seconds in this interval."
         ::= { adslAtucChanPerfDataEntry 7 }

         adslAtucChanPerfCurr15MinReceivedBlks OBJECT-TYPE
             SYNTAX      PerfCurrentCount
             MAX-ACCESS  read-only
             STATUS      current
             DESCRIPTION
                 "Count of all encoded blocks received on this channel
                 within the current 15 minute interval."
         ::= { adslAtucChanPerfDataEntry 8 }

         adslAtucChanPerfCurr15MinTransmittedBlks OBJECT-TYPE
             SYNTAX      PerfCurrentCount
             MAX-ACCESS  read-only
             STATUS      current
             DESCRIPTION
                 "Count of all encoded blocks transmitted on this
                 channel within the current 15 minute interval."
         ::= { adslAtucChanPerfDataEntry 9 }

         adslAtucChanPerfCurr15MinCorrectedBlks  OBJECT-TYPE
             SYNTAX      PerfCurrentCount
             MAX-ACCESS  read-only
             STATUS      current
             DESCRIPTION
                 "Count of all blocks received with errors that were
                 corrected on this channel within the current 15 minute
                 interval."
         ::= { adslAtucChanPerfDataEntry 10 }

         adslAtucChanPerfCurr15MinUncorrectBlks  OBJECT-TYPE
             SYNTAX      PerfCurrentCount
             MAX-ACCESS  read-only
             STATUS      current
             DESCRIPTION
                 "Count of all blocks received with uncorrectable
                 errors on this channel within the current 15 minute
                 interval."
         ::= { adslAtucChanPerfDataEntry 11 }

         -- 1-day current and previous performance group
         --
         adslAtucChanPerfCurr1DayTimeElapsed OBJECT-TYPE
             SYNTAX      AdslPerfTimeElapsed(0..86399)
             UNITS       "seconds"
             MAX-ACCESS  read-only
             STATUS      current
             DESCRIPTION
                 "Number of seconds that have elapsed since the
                 beginning of the current 1-day interval."
         ::= { adslAtucChanPerfDataEntry 12 }

         adslAtucChanPerfCurr1DayReceivedBlks  OBJECT-TYPE
             SYNTAX      AdslPerfCurrDayCount
             MAX-ACCESS  read-only
             STATUS      current
             DESCRIPTION
                 "Count of all encoded blocks received on this
                 channel during the current day as measured by
                 adslAtucChanPerfCurr1DayTimeElapsed."
         ::= { adslAtucChanPerfDataEntry 13 }

         adslAtucChanPerfCurr1DayTransmittedBlks  OBJECT-TYPE
             SYNTAX      AdslPerfCurrDayCount
             MAX-ACCESS  read-only
             STATUS      current
             DESCRIPTION
                 "Count of all encoded blocks transmitted on this
                 channel during the current day as measured by
                 adslAtucChanPerfCurr1DayTimeElapsed."
         ::= { adslAtucChanPerfDataEntry 14 }

         adslAtucChanPerfCurr1DayCorrectedBlks  OBJECT-TYPE
             SYNTAX      AdslPerfCurrDayCount
             MAX-ACCESS  read-only
             STATUS      current
             DESCRIPTION
                 "Count of all blocks received with errors that were
                 corrected on this channel during the current day as
                 measured by adslAtucChanPerfCurr1DayTimeElapsed."
         ::= { adslAtucChanPerfDataEntry 15 }

         adslAtucChanPerfCurr1DayUncorrectBlks  OBJECT-TYPE
             SYNTAX      AdslPerfCurrDayCount
             MAX-ACCESS  read-only
             STATUS      current
             DESCRIPTION
                 "Count of all blocks received with uncorrectable
                 errors on this channel during the current day as
                 measured by adslAtucChanPerfCurr1DayTimeElapsed."
         ::= { adslAtucChanPerfDataEntry 16 }

         adslAtucChanPerfPrev1DayMoniSecs OBJECT-TYPE
             SYNTAX      INTEGER(0..86400)
             UNITS       "seconds"
             MAX-ACCESS  read-only
             STATUS      current
             DESCRIPTION
                 "The amount of time in the previous 1-day interval
                 over which the performance monitoring information
                 is actually counted. This value will be the same as
                 the interval duration except in a situation where
                 performance monitoring data could not be collected
                 for any reason."
         ::= { adslAtucChanPerfDataEntry 17 }

         adslAtucChanPerfPrev1DayReceivedBlks  OBJECT-TYPE
             SYNTAX      AdslPerfPrevDayCount
             MAX-ACCESS  read-only
             STATUS      current
             DESCRIPTION
                 "Count of all encoded blocks received on this
                 channel within the most recent previous 1-day
                 period."
         ::= { adslAtucChanPerfDataEntry 18 }

         adslAtucChanPerfPrev1DayTransmittedBlks  OBJECT-TYPE
             SYNTAX      AdslPerfPrevDayCount
             MAX-ACCESS  read-only
             STATUS      current
             DESCRIPTION
                 "Count of all encoded blocks transmitted on this
                 channel within the most recent previous 1-day
                 period."
         ::= { adslAtucChanPerfDataEntry 19 }

         adslAtucChanPerfPrev1DayCorrectedBlks  OBJECT-TYPE
             SYNTAX      AdslPerfPrevDayCount
             MAX-ACCESS  read-only
             STATUS      current
             DESCRIPTION
                 "Count of all blocks received with errors that were
                 corrected on this channel within the most recent
                 previous 1-day period."
         ::= { adslAtucChanPerfDataEntry 20 }

         adslAtucChanPerfPrev1DayUncorrectBlks  OBJECT-TYPE
             SYNTAX      AdslPerfPrevDayCount
             MAX-ACCESS  read-only
             STATUS      current
             DESCRIPTION
                 "Count of all blocks received with uncorrectable
                 errors on this channel within the most recent previous
                 1-day period."
         ::= { adslAtucChanPerfDataEntry 21 }

         adslAturChanPerfDataTable       OBJECT-TYPE
             SYNTAX          SEQUENCE OF AdslAturChanPerfDataEntry
             MAX-ACCESS      not-accessible
             STATUS          current
             DESCRIPTION
                 "This table provides one row for each ATUR channel.
                 ADSL channel interfaces are those ifEntries
                 where ifType is equal to adslInterleave(124)
                 or adslFast(125)."
         ::= { adslMibObjects 11 }

         adslAturChanPerfDataEntry       OBJECT-TYPE
             SYNTAX          AdslAturChanPerfDataEntry
             MAX-ACCESS      not-accessible
             STATUS          current
             DESCRIPTION     "An entry in adslAturChanPerfDataTable."
             INDEX           { ifIndex }
         ::= { adslAturChanPerfDataTable 1 }

         AdslAturChanPerfDataEntry ::=
          SEQUENCE {
          adslAturChanReceivedBlks                 Counter32,
          adslAturChanTransmittedBlks              Counter32,
          adslAturChanCorrectedBlks                Counter32,
          adslAturChanUncorrectBlks                Counter32,
          adslAturChanPerfValidIntervals           INTEGER,
          adslAturChanPerfInvalidIntervals         INTEGER,
          adslAturChanPerfCurr15MinTimeElapsed     AdslPerfTimeElapsed,
          adslAturChanPerfCurr15MinReceivedBlks    PerfCurrentCount,
          adslAturChanPerfCurr15MinTransmittedBlks PerfCurrentCount,
          adslAturChanPerfCurr15MinCorrectedBlks   PerfCurrentCount,
          adslAturChanPerfCurr15MinUncorrectBlks   PerfCurrentCount,
          adslAturChanPerfCurr1DayTimeElapsed      AdslPerfTimeElapsed,
          adslAturChanPerfCurr1DayReceivedBlks     AdslPerfCurrDayCount,
          adslAturChanPerfCurr1DayTransmittedBlks  AdslPerfCurrDayCount,
          adslAturChanPerfCurr1DayCorrectedBlks    AdslPerfCurrDayCount,
          adslAturChanPerfCurr1DayUncorrectBlks    AdslPerfCurrDayCount,
          adslAturChanPerfPrev1DayMoniSecs         INTEGER,
          adslAturChanPerfPrev1DayReceivedBlks     AdslPerfPrevDayCount,
          adslAturChanPerfPrev1DayTransmittedBlks  AdslPerfPrevDayCount,
          adslAturChanPerfPrev1DayCorrectedBlks    AdslPerfPrevDayCount,
          adslAturChanPerfPrev1DayUncorrectBlks    AdslPerfPrevDayCount
          }
         -- performance group
         --
         -- Note: block is intended to be the length of the channel
         --       data-block on which the CRC operates. See
         --       adslAturChanCrcBlockLength for more information.
         --
         adslAturChanReceivedBlks OBJECT-TYPE
             SYNTAX      Counter32
             MAX-ACCESS  read-only
             STATUS      current
             DESCRIPTION
                 "Count of all encoded blocks received on this channel
                 since agent reset."
         ::= { adslAturChanPerfDataEntry 1 }

         adslAturChanTransmittedBlks  OBJECT-TYPE
             SYNTAX      Counter32
             MAX-ACCESS  read-only
             STATUS      current
             DESCRIPTION
                 "Count of all encoded blocks transmitted on this
                 channel since agent reset."
         ::= { adslAturChanPerfDataEntry 2 }

         adslAturChanCorrectedBlks  OBJECT-TYPE
             SYNTAX      Counter32
             MAX-ACCESS  read-only
             STATUS      current
             DESCRIPTION
                 "Count of all blocks received with errors that were
                 corrected since agent reset.  These blocks are passed
                 on as good data."
         ::= { adslAturChanPerfDataEntry 3 }

         adslAturChanUncorrectBlks  OBJECT-TYPE
             SYNTAX      Counter32
             MAX-ACCESS  read-only
             STATUS      current
             DESCRIPTION
                 "Count of all blocks received with uncorrectable
                 errors since agent reset."
         ::= { adslAturChanPerfDataEntry 4 }

         -- general 15 min interval information
         --
         adslAturChanPerfValidIntervals OBJECT-TYPE
             SYNTAX      INTEGER(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adslAturChanPerfDataEntry 5 }

         adslAturChanPerfInvalidIntervals OBJECT-TYPE
             SYNTAX      INTEGER(0..96)
             MAX-ACCESS  read-only
             STATUS      current
             DESCRIPTION
                 "The number of intervals in the range from
                 0 to the value of adslAturChanPerfValidIntervals
                 for which no data is available. This object
                 will typically be zero except in cases where
                 the data for some intervals are not available
                 (e.g., in proxy situations)."
         ::= { adslAturChanPerfDataEntry 6 }

         -- 15 min current performance group
         --
         adslAturChanPerfCurr15MinTimeElapsed OBJECT-TYPE
             SYNTAX      AdslPerfTimeElapsed(0..899)
             UNITS       "seconds"
             MAX-ACCESS  read-only
             STATUS      current
             DESCRIPTION
                 "Total elapsed seconds in this interval.
                 A full interval is 900 seconds."
         ::= { adslAturChanPerfDataEntry 7 }

         adslAturChanPerfCurr15MinReceivedBlks OBJECT-TYPE
             SYNTAX      PerfCurrentCount
             MAX-ACCESS  read-only
             STATUS      current
             DESCRIPTION
                 "Count of all encoded blocks received on this
                 channel within the current 15 minute interval."
         ::= { adslAturChanPerfDataEntry 8 }

         adslAturChanPerfCurr15MinTransmittedBlks OBJECT-TYPE
             SYNTAX      PerfCurrentCount
             MAX-ACCESS  read-only
             STATUS      current
             DESCRIPTION
                 "Count of all encoded blocks transmitted on this
                 channel within the current 15 minute interval."
         ::= { adslAturChanPerfDataEntry 9 }

         adslAturChanPerfCurr15MinCorrectedBlks  OBJECT-TYPE
             SYNTAX      PerfCurrentCount
             MAX-ACCESS  read-only
             STATUS      current
             DESCRIPTION
                 "Count of all blocks received with errors that were
                 corrected on this channel within the current 15 minute
                 interval."
         ::= { adslAturChanPerfDataEntry 10 }

         adslAturChanPerfCurr15MinUncorrectBlks  OBJECT-TYPE
             SYNTAX      PerfCurrentCount
             MAX-ACCESS  read-only
             STATUS      current
             DESCRIPTION
                 "Count of all blocks received with uncorrectable
                 errors on this channel within the current 15 minute
                 interval."
         ::= { adslAturChanPerfDataEntry 11 }

         -- 1-day current and previous performance group
         --
         adslAturChanPerfCurr1DayTimeElapsed OBJECT-TYPE
             SYNTAX      AdslPerfTimeElapsed(0..86399)
             UNITS       "seconds"
             MAX-ACCESS  read-only
             STATUS      current
             DESCRIPTION
                 "Number of seconds that have elapsed since the
                 beginning of the current 1-day interval."
         ::= { adslAturChanPerfDataEntry 12 }

         adslAturChanPerfCurr1DayReceivedBlks  OBJECT-TYPE
             SYNTAX      AdslPerfCurrDayCount
             MAX-ACCESS  read-only
             STATUS      current
             DESCRIPTION
                 "Count of all encoded blocks received on this
                 channel during the current day as measured by
                 adslAturChanPerfCurr1DayTimeElapsed."
         ::= { adslAturChanPerfDataEntry 13 }

         adslAturChanPerfCurr1DayTransmittedBlks  OBJECT-TYPE
             SYNTAX      AdslPerfCurrDayCount
             MAX-ACCESS  read-only
             STATUS      current
             DESCRIPTION
                 "Count of all encoded blocks transmitted on this
                 channel during the current day as measured by
                 adslAturChanPerfCurr1DayTimeElapsed."

         ::= { adslAturChanPerfDataEntry 14 }

         adslAturChanPerfCurr1DayCorrectedBlks  OBJECT-TYPE
             SYNTAX      AdslPerfCurrDayCount
             MAX-ACCESS  read-only
             STATUS      current
             DESCRIPTION
                 "Count of all blocks received with errors that were
                 corrected on this channel during the current day as
                 measured by adslAturChanPerfCurr1DayTimeElapsed."
         ::= { adslAturChanPerfDataEntry 15 }

         adslAturChanPerfCurr1DayUncorrectBlks  OBJECT-TYPE
             SYNTAX      AdslPerfCurrDayCount
             MAX-ACCESS  read-only
             STATUS      current
             DESCRIPTION
                 "Count of all blocks received with uncorrectable
                 errors on this channel during the current day as
                 measured by adslAturChanPerfCurr1DayTimeElapsed."
         ::= { adslAturChanPerfDataEntry 16 }

         adslAturChanPerfPrev1DayMoniSecs OBJECT-TYPE
             SYNTAX      INTEGER(0..86400)
             UNITS       "seconds"
             MAX-ACCESS  read-only
             STATUS      current
             DESCRIPTION
                 "The amount of time in the previous 1-day interval
                 over which the performance monitoring information
                 is actually counted. This value will be the same as
                 the interval duration except in a situation where
                 performance monitoring data could not be collected
                 for any reason."
         ::= { adslAturChanPerfDataEntry 17 }

         adslAturChanPerfPrev1DayReceivedBlks  OBJECT-TYPE
             SYNTAX      AdslPerfPrevDayCount
             MAX-ACCESS  read-only
             STATUS      current
             DESCRIPTION
                 "Count of all encoded blocks received on this
                 channel within the most recent previous 1-day
                 period."
         ::= { adslAturChanPerfDataEntry 18 }

         adslAturChanPerfPrev1DayTransmittedBlks  OBJECT-TYPE
             SYNTAX      AdslPerfPrevDayCount
             MAX-ACCESS  read-only
             STATUS      current
             DESCRIPTION
                 "Count of all encoded blocks transmitted on this
                 channel within the most recent previous 1-day
                 period."
         ::= { adslAturChanPerfDataEntry 19 }

         adslAturChanPerfPrev1DayCorrectedBlks  OBJECT-TYPE
             SYNTAX      AdslPerfPrevDayCount
             MAX-ACCESS  read-only
             STATUS      current
             DESCRIPTION
                 "Count of all blocks received with errors that were
                 corrected on this channel within the most recent
                 previous 1-day period."
         ::= { adslAturChanPerfDataEntry 20 }

         adslAturChanPerfPrev1DayUncorrectBlks  OBJECT-TYPE
             SYNTAX      AdslPerfPrevDayCount
             MAX-ACCESS  read-only
             STATUS      current
             DESCRIPTION
                 "Count of all blocks received with uncorrectable
                 errors on this channel within the most recent previous
                 1-day period."
         ::= { adslAturChanPerfDataEntry 21 }

         adslAtucChanIntervalTable   OBJECT-TYPE
             SYNTAX          SEQUENCE OF AdslAtucChanIntervalEntry
             MAX-ACCESS      not-accessible
             STATUS          current
             DESCRIPTION
                 "This table provides one row for each ATUC channel's
                 performance data collection interval.
                 ADSL channel interfaces are those ifEntries
                 where ifType is equal to adslInterleave(124)
                 or adslFast(125)."
         ::= { adslMibObjects 12 }

         adslAtucChanIntervalEntry   OBJECT-TYPE
             SYNTAX          AdslAtucChanIntervalEntry
             MAX-ACCESS      not-accessible
             STATUS          current
             DESCRIPTION     "An entry in the adslAtucIntervalTable."
             INDEX           { ifIndex, adslAtucChanIntervalNumber }
         ::= { adslAtucChanIntervalTable 1 }

         AdslAtucChanIntervalEntry ::=
             SEQUENCE {
             adslAtucChanIntervalNumber          INTEGER,
             adslAtucChanIntervalReceivedBlks    PerfIntervalCount,
             adslAtucChanIntervalTransmittedBlks PerfIntervalCount,
             adslAtucChanIntervalCorrectedBlks   PerfIntervalCount,
             adslAtucChanIntervalUncorrectBlks   PerfIntervalCount,
             adslAtucChanIntervalValidData       TruthValue
             }
         adslAtucChanIntervalNumber OBJECT-TYPE
             SYNTAX      INTEGER(1..96)
             MAX-ACCESS  not-accessible
             STATUS      current
             DESCRIPTION
                 "Performance Data Interval number 1 is the
                 the most recent previous interval; interval
                 96 is 24 hours ago.  Intervals 2..96 are
                 optional."
         ::= { adslAtucChanIntervalEntry 1 }

         adslAtucChanIntervalReceivedBlks OBJECT-TYPE
             SYNTAX      PerfIntervalCount
             MAX-ACCESS  read-only
             STATUS      current
             DESCRIPTION
                 "Count of all encoded blocks received on this channel
                 during this interval."
         ::= { adslAtucChanIntervalEntry 2 }

         adslAtucChanIntervalTransmittedBlks  OBJECT-TYPE
             SYNTAX      PerfIntervalCount
             MAX-ACCESS  read-only
             STATUS      current
             DESCRIPTION
                 "Count of all encoded blocks transmitted on this
                 channel during this interval."
         ::= { adslAtucChanIntervalEntry 3 }

         adslAtucChanIntervalCorrectedBlks  OBJECT-TYPE
             SYNTAX      PerfIntervalCount
             MAX-ACCESS  read-only
             STATUS      current
             DESCRIPTION
                 "Count of all blocks received with errors that were
                 corrected on this channel during this interval."
         ::= { adslAtucChanIntervalEntry 4 }

         adslAtucChanIntervalUncorrectBlks  OBJECT-TYPE
             SYNTAX      PerfIntervalCount
             MAX-ACCESS  read-only
             STATUS      current
             DESCRIPTION
                 "Count of all blocks received with uncorrectable
                 errors on this channel during this interval."
         ::= { adslAtucChanIntervalEntry 5 }

         adslAtucChanIntervalValidData OBJECT-TYPE
             SYNTAX TruthValue
             MAX-ACCESS read-only
             STATUS current
             DESCRIPTION
                 "This variable indicates if the data for this
                 interval is valid."
         ::= { adslAtucChanIntervalEntry 6 }

         adslAturChanIntervalTable   OBJECT-TYPE
             SYNTAX          SEQUENCE OF AdslAturChanIntervalEntry
             MAX-ACCESS      not-accessible
             STATUS          current
             DESCRIPTION
                 "This table provides one row for each ATUR channel's
                 performance data collection interval.
                 ADSL channel interfaces are those ifEntries
                 where ifType is equal to adslInterleave(124)
                 or adslFast(125)."
         ::= { adslMibObjects 13 }

         adslAturChanIntervalEntry   OBJECT-TYPE
             SYNTAX          AdslAturChanIntervalEntry
             MAX-ACCESS      not-accessible
             STATUS          current
             DESCRIPTION     "An entry in the adslAturIntervalTable."
             INDEX           { ifIndex, adslAturChanIntervalNumber }
         ::= { adslAturChanIntervalTable 1 }

         AdslAturChanIntervalEntry ::=
             SEQUENCE {
             adslAturChanIntervalNumber               INTEGER,
             adslAturChanIntervalReceivedBlks         PerfIntervalCount,
             adslAturChanIntervalTransmittedBlks      PerfIntervalCount,
             adslAturChanIntervalCorrectedBlks        PerfIntervalCount,
             adslAturChanIntervalUncorrectBlks        PerfIntervalCount,
             adslAturChanIntervalValidData            TruthValue
             }
         adslAturChanIntervalNumber OBJECT-TYPE
             SYNTAX      INTEGER(1..96)
             MAX-ACCESS  not-accessible
             STATUS      current
             DESCRIPTION
                 "Performance Data Interval number 1 is the
                 the most recent previous interval; interval
                 96 is 24 hours ago.  Intervals 2..96 are
                 optional."
         ::= { adslAturChanIntervalEntry 1 }

         adslAturChanIntervalReceivedBlks OBJECT-TYPE
             SYNTAX      PerfIntervalCount
             MAX-ACCESS  read-only
             STATUS      current
             DESCRIPTION
                 "Count of all encoded blocks received on this channel
                 during this interval."
         ::= { adslAturChanIntervalEntry 2 }

         adslAturChanIntervalTransmittedBlks  OBJECT-TYPE
             SYNTAX      PerfIntervalCount
             MAX-ACCESS  read-only
             STATUS      current
             DESCRIPTION
                 "Count of all encoded blocks transmitted on this
                 channel during this interval."
         ::= { adslAturChanIntervalEntry 3 }

         adslAturChanIntervalCorrectedBlks  OBJECT-TYPE
             SYNTAX      PerfIntervalCount
             MAX-ACCESS  read-only
             STATUS      current
             DESCRIPTION
                 "Count of all blocks received with errors that were
                 corrected on this channel during this interval."
         ::= { adslAturChanIntervalEntry 4 }

         adslAturChanIntervalUncorrectBlks  OBJECT-TYPE
             SYNTAX      PerfIntervalCount
             MAX-ACCESS  read-only
             STATUS      current
             DESCRIPTION
                 "Count of all blocks received with uncorrectable
                 errors on this channel during this interval."
         ::= { adslAturChanIntervalEntry 5 }

         adslAturChanIntervalValidData OBJECT-TYPE
             SYNTAX TruthValue
             MAX-ACCESS read-only
             STATUS current
             DESCRIPTION
                 "This variable indicates if the data for this
                 interval is valid."
         ::= { adslAturChanIntervalEntry 6 }

         -- Profile Group
         --

         adslLineConfProfileTable    OBJECT-TYPE
             SYNTAX          SEQUENCE OF AdslLineConfProfileEntry
             MAX-ACCESS      not-accessible
             STATUS          current
             DESCRIPTION
                 "This table contains information on the ADSL line
                 configuration.  One entry in this table reflects a
                 profile defined by a manager which can be used to
                 configure the ADSL line."
         ::= { adslMibObjects 14}

         adslLineConfProfileEntry    OBJECT-TYPE
             SYNTAX          AdslLineConfProfileEntry
             MAX-ACCESS      not-accessible
             STATUS          current
             DESCRIPTION
                 "Each entry consists of a list of parameters that
                 represents the configuration of an ADSL modem.

                 When `dynamic' profiles are implemented, a default
                 profile will always exist.  This profile's name will
                 be set to `DEFVAL' and its parameters will be set
                 to vendor specific values, unless otherwise specified
                 in this document.

                 When `static' profiles are implemented, profiles
                 are automaticly created or destroyed as ADSL
                 physical lines are discovered and removed by
                 the system.  The name of the profile will be
                 equivalent to the decimal value of the line's
                 interface index.
                 "
             INDEX { IMPLIED adslLineConfProfileName}
         ::= { adslLineConfProfileTable 1}

         AdslLineConfProfileEntry ::=
             SEQUENCE {
             adslLineConfProfileName               SnmpAdminString,
             adslAtucConfRateMode                  INTEGER,
             adslAtucConfRateChanRatio             INTEGER,
             adslAtucConfTargetSnrMgn              INTEGER,
             adslAtucConfMaxSnrMgn                 INTEGER,
             adslAtucConfMinSnrMgn                 INTEGER,
             adslAtucConfDownshiftSnrMgn           INTEGER,
             adslAtucConfUpshiftSnrMgn             INTEGER,
             adslAtucConfMinUpshiftTime            INTEGER,
             adslAtucConfMinDownshiftTime          INTEGER,
             adslAtucChanConfFastMinTxRate         Unsigned32,
             adslAtucChanConfInterleaveMinTxRate   Unsigned32,
             adslAtucChanConfFastMaxTxRate         Unsigned32,
             adslAtucChanConfInterleaveMaxTxRate   Unsigned32,
             adslAtucChanConfMaxInterleaveDelay    INTEGER,
             adslAturConfRateMode                  INTEGER,
             adslAturConfRateChanRatio             INTEGER,
             adslAturConfTargetSnrMgn              INTEGER,
             adslAturConfMaxSnrMgn                 INTEGER,
             adslAturConfMinSnrMgn                 INTEGER,
             adslAturConfDownshiftSnrMgn           INTEGER,
             adslAturConfUpshiftSnrMgn             INTEGER,
             adslAturConfMinUpshiftTime            INTEGER,
             adslAturConfMinDownshiftTime          INTEGER,
             adslAturChanConfFastMinTxRate         Unsigned32,
             adslAturChanConfInterleaveMinTxRate   Unsigned32,
             adslAturChanConfFastMaxTxRate         Unsigned32,
             adslAturChanConfInterleaveMaxTxRate   Unsigned32,
             adslAturChanConfMaxInterleaveDelay    INTEGER,
             adslLineConfProfileRowStatus          RowStatus
         }

         adslLineConfProfileName    OBJECT-TYPE
                 SYNTAX          SnmpAdminString (SIZE (1..32))
                 MAX-ACCESS      not-accessible
                 STATUS          current
                 DESCRIPTION
                 "This object is used by the line configuration table
                 in order to identify a row of this table.

                 When `dynamic' profiles are implemented, the profile
                 name is user specified.  Also, the system will always
                 provide a default profile whose name is `DEFVAL'.

                 When `static' profiles are implemented, there is an
                 one-to-one relationship between each line and its
                 profile.  In which case, the profile name will
                 need to algorithmicly represent the Line's ifIndex.
                 Therefore, the profile's name is a decimalized string
                 of the ifIndex that is fixed-length (i.e., 10) with
                 leading zero(s).  For example, the profile name for
                 ifIndex which equals '15' will be '0000000015'."
         ::= { adslLineConfProfileEntry 1 }

         adslAtucConfRateMode OBJECT-TYPE
             SYNTAX      INTEGER {
                 fixed (1),              -- no rate adaptation
                 adaptAtStartup (2),     -- perform rate adaptation
                                         -- only at initialization
                 adaptAtRuntime (3)      -- perform rate adaptation at
                                         -- any time
             }
             MAX-ACCESS  read-create
             STATUS      current
             DESCRIPTION
                 "Defines what form of transmit rate adaptation is
                 configured on this modem.  See ADSL Forum TR-005 [3]
                 for more information."
         ::= { adslLineConfProfileEntry 2 }

         adslAtucConfRateChanRatio OBJECT-TYPE
             SYNTAX      INTEGER(0..100)
             UNITS        "%"
             MAX-ACCESS  read-create
             STATUS      current
             DESCRIPTION
                 "Configured allocation ratio of excess transmit
                 bandwidth between fast and interleaved channels.  Only
                 applies when two channel mode and RADSL are supported.
                 Distribute bandwidth on each channel in excess of the
                 corresponding ChanConfMinTxRate so that:
                 adslAtucConfRateChanRatio =

                         [Fast / (Fast + Interleaved)] * 100

                 In other words this value is the fast channel
                 percentage."
         ::= { adslLineConfProfileEntry 3 }

       adslAtucConfTargetSnrMgn OBJECT-TYPE
             SYNTAX      INTEGER (0..310)
             UNITS       "tenth dB"
             MAX-ACCESS  read-create
             STATUS      current
             DESCRIPTION
                 "Configured Target Signal/Noise Margin.
                 This is the Noise Margin the modem must achieve
                 with a BER of 10-7 or better to successfully complete
                 initialization."
         ::= { adslLineConfProfileEntry 4 }

       adslAtucConfMaxSnrMgn OBJECT-TYPE
             SYNTAX      INTEGER (0..310)
             UNITS       "tenth dB"
             MAX-ACCESS  read-create
             STATUS      current
             DESCRIPTION
                 "Configured Maximum acceptable Signal/Noise Margin.
                 If the Noise Margin is above this the modem should
                 attempt to reduce its power output to optimize its
                 operation."
         ::= { adslLineConfProfileEntry 5 }

         adslAtucConfMinSnrMgn  OBJECT-TYPE
             SYNTAX      INTEGER (0..310)
             UNITS       "tenth dB"
             MAX-ACCESS  read-create
             STATUS      current
             DESCRIPTION
                 "Configured Minimum acceptable Signal/Noise Margin.
                 If the noise margin falls below this level, the modem
                 should attempt to increase its power output.  If that
                 is not possible the modem will attempt to
                 re-initialize or shut down."
         ::= { adslLineConfProfileEntry 6 }

         adslAtucConfDownshiftSnrMgn  OBJECT-TYPE
             SYNTAX      INTEGER (0..310)
             UNITS       "tenth dB"
             MAX-ACCESS  read-create
             STATUS      current
             DESCRIPTION
                 "Configured Signal/Noise Margin for rate downshift.
                 If the noise margin falls below this level, the modem
                 should attempt to decrease its transmit rate.  In
                 the case that RADSL mode is not present,
                 the value will be `0'."
         ::= { adslLineConfProfileEntry 7 }

         adslAtucConfUpshiftSnrMgn  OBJECT-TYPE
             SYNTAX      INTEGER (0..310)
             UNITS       "tenth dB"
             MAX-ACCESS  read-create
             STATUS      current
             DESCRIPTION
                 "Configured Signal/Noise Margin for rate upshift.
                 If the noise margin rises above this level, the modem
                 should attempt to increase its transmit rate.    In
                 the case that RADSL is not present, the value will
                 be `0'."
         ::= { adslLineConfProfileEntry 8 }

         adslAtucConfMinUpshiftTime OBJECT-TYPE
             SYNTAX      INTEGER(0..16383)
             UNITS       "seconds"
             MAX-ACCESS  read-create
             STATUS      current
             DESCRIPTION
                 "Minimum time that the current margin is above
                 UpshiftSnrMgn before an upshift occurs.
                 In the case that RADSL is not present, the value will
                 be `0'."
         ::= { adslLineConfProfileEntry 9 }
        adslAtucConfMinDownshiftTime OBJECT-TYPE
             SYNTAX      INTEGER(0..16383)
             UNITS       "seconds"
             MAX-ACCESS  read-create
             STATUS      current
             DESCRIPTION
                 "Minimum time that the current margin is below
                 DownshiftSnrMgn before a downshift occurs.
                 In the case that RADSL mode is not present,
                 the value will be `0'."
         ::= { adslLineConfProfileEntry 10 }

         adslAtucChanConfFastMinTxRate  OBJECT-TYPE
             SYNTAX      Unsigned32
             UNITS       "bps"
             MAX-ACCESS  read-create
             STATUS      current
             DESCRIPTION
                 "Configured Minimum Transmit rate for `Fast' channels,
                 in bps.  See adslAtucConfRateChanRatio for information
                 regarding RADSL mode and ATUR transmit rate for
                 ATUC receive rates."
         ::= { adslLineConfProfileEntry 11 }

         adslAtucChanConfInterleaveMinTxRate OBJECT-TYPE
             SYNTAX      Unsigned32
             UNITS       "bps"
             MAX-ACCESS  read-create
             STATUS      current
             DESCRIPTION
                 "Configured Minimum Transmit rate for `Interleave'
                 channels, in bps.  See adslAtucConfRateChanRatio for
                 information regarding RADSL mode and see
                 ATUR transmit rate for receive rates."
         ::= { adslLineConfProfileEntry 12 }

         adslAtucChanConfFastMaxTxRate  OBJECT-TYPE
             SYNTAX      Unsigned32
             UNITS       "bps"
             MAX-ACCESS  read-create
             STATUS      current
             DESCRIPTION
                 "Configured Maximum Transmit rate for `Fast' channels,
                 in bps.  See adslAtucConfRateChanRatio for information
                 regarding RADSL mode and see ATUR transmit rate for
                 ATUC receive rates."
         ::= { adslLineConfProfileEntry 13 }

         adslAtucChanConfInterleaveMaxTxRate OBJECT-TYPE
             SYNTAX      Unsigned32
             UNITS       "bps"
             MAX-ACCESS  read-create
             STATUS      current
             DESCRIPTION
                 "Configured Maximum Transmit rate for `Interleave'
                 channels, in bps.  See adslAtucConfRateChanRatio for
                 information regarding RADSL mode and ATUR transmit
                 rate for ATUC receive rates."
         ::= { adslLineConfProfileEntry 14 }

         adslAtucChanConfMaxInterleaveDelay OBJECT-TYPE
             SYNTAX      INTEGER(0..255)
             UNITS        "milli-seconds"
             MAX-ACCESS  read-create
             STATUS      current
             DESCRIPTION
                 "Configured maximum Interleave Delay for this channel.

                 Interleave delay applies only to the interleave channel
                 and defines the mapping (relative spacing) between
                 subsequent input bytes at the interleaver input and
                 their placement in the bit stream at the interleaver
                 output.  Larger numbers provide greater separation
                 between consecutive input bytes in the output bit
                 stream allowing for improved impulse noise immunity
                 at the expense of payload latency."
         ::= { adslLineConfProfileEntry 15 }

         adslAturConfRateMode OBJECT-TYPE
             SYNTAX      INTEGER {
                 fixed (1),              -- no rate adaptation
                 adaptAtStartup (2),     -- perform rate adaptation
                                         -- only at initialization
                 adaptAtRuntime (3)      -- perform rate adaptation at
                                         -- any time
             }
             MAX-ACCESS  read-create
             STATUS      current
             DESCRIPTION
                 "Defines what form of transmit rate adaptation is
                 configured on this modem.  See ADSL Forum TR-005 [3]
                 for more information."
         ::= { adslLineConfProfileEntry 16 }

         adslAturConfRateChanRatio OBJECT-TYPE
             SYNTAX      INTEGER(0..100)
             UNITS        "%"
             MAX-ACCESS  read-create
             STATUS      current
             DESCRIPTION
                 "Configured allocation ratio of excess transmit
                 bandwidth between fast and interleaved channels.  Only
                 applies when two channel mode and RADSL are supported.
                 Distribute bandwidth on each channel in excess of the
                 corresponding ChanConfMinTxRate so that:
                 adslAturConfRateChanRatio =

                         [Fast / (Fast + Interleaved)] * 100

                 In other words this value is the fast channel
                 percentage."
         ::= { adslLineConfProfileEntry 17 }

       adslAturConfTargetSnrMgn OBJECT-TYPE
             SYNTAX      INTEGER (0..310)
             UNITS       "tenth dB"
             MAX-ACCESS  read-create
             STATUS      current
             DESCRIPTION
                 "Configured Target Signal/Noise Margin.
                 This is the Noise Margin the modem must achieve
                 with a BER of 10-7 or better to successfully complete
                 initialization."
         ::= { adslLineConfProfileEntry 18 }

       adslAturConfMaxSnrMgn OBJECT-TYPE
             SYNTAX      INTEGER (0..310)
             UNITS       "tenth dB"
             MAX-ACCESS  read-create
             STATUS      current
             DESCRIPTION
                 "Configured Maximum acceptable Signal/Noise Margin.
                 If the Noise Margin is above this the modem should
                 attempt to reduce its power output to optimize its
                 operation."
         ::= { adslLineConfProfileEntry 19 }

        adslAturConfMinSnrMgn  OBJECT-TYPE
             SYNTAX      INTEGER (0..310)
             UNITS       "tenth dB"
             MAX-ACCESS  read-create
             STATUS      current
             DESCRIPTION
                 "Configured Minimum acceptable Signal/Noise Margin.
                 If the noise margin falls below this level, the modem
                 should attempt to increase its power output.  If that
                 is not possible the modem will attempt to
                 re-initialize or shut down."
         ::= { adslLineConfProfileEntry 20 }

         adslAturConfDownshiftSnrMgn  OBJECT-TYPE
             SYNTAX      INTEGER (0..310)
             UNITS       "tenth dB"
             MAX-ACCESS  read-create
             STATUS      current
             DESCRIPTION
                 "Configured Signal/Noise Margin for rate downshift.
                 If the noise margin falls below this level, the modem
                 should attempt to decrease its transmit rate.
                 In the case that RADSL mode is not present,
                 the value will be `0'."
         ::= { adslLineConfProfileEntry 21 }

         adslAturConfUpshiftSnrMgn  OBJECT-TYPE
             SYNTAX      INTEGER (0..310)
             UNITS       "tenth dB"
             MAX-ACCESS  read-create
             STATUS      current
             DESCRIPTION
                 "Configured Signal/Noise Margin for rate upshift.
                 If the noise margin rises above this level, the modem
                 should attempt to increase its transmit rate.
                 In the case that RADSL is not present,
                 the value will be `0'."
         ::= { adslLineConfProfileEntry 22 }

         adslAturConfMinUpshiftTime OBJECT-TYPE
             SYNTAX      INTEGER(0..16383)
             UNITS       "seconds"
             MAX-ACCESS  read-create
             STATUS      current
             DESCRIPTION
                 "Minimum time that the current margin is above
                 UpshiftSnrMgn before an upshift occurs.
                 In the case that RADSL is not present, the value will
                 be `0'."
         ::= { adslLineConfProfileEntry 23 }

        adslAturConfMinDownshiftTime OBJECT-TYPE
             SYNTAX      INTEGER(0..16383)
             UNITS       "seconds"
             MAX-ACCESS  read-create
             STATUS      current
             DESCRIPTION
                 "Minimum time that the current margin is below
                 DownshiftSnrMgn before a downshift occurs.
                 In the case that RADSL mode is not present,
                 the value will be `0'."
         ::= { adslLineConfProfileEntry 24 }

         adslAturChanConfFastMinTxRate  OBJECT-TYPE
             SYNTAX      Unsigned32
             UNITS       "bps"
             MAX-ACCESS  read-create
             STATUS      current
             DESCRIPTION
                 "Configured Minimum Transmit rate for `Fast' channels,
                 in bps.  See adslAturConfRateChanRatio for information
                 regarding RADSL mode and ATUC transmit rate
                 for ATUR receive rates."
         ::= { adslLineConfProfileEntry 25 }

         adslAturChanConfInterleaveMinTxRate OBJECT-TYPE
             SYNTAX      Unsigned32
             UNITS       "bps"
             MAX-ACCESS  read-create
             STATUS      current
             DESCRIPTION
                 "Configured Minimum Transmit rate for `Interleave'
                 channels, in bps.  See adslAturConfRateChanRatio for
                 information regarding RADSL mode and ATUC transmit rate
                 for ATUR receive rates."
         ::= { adslLineConfProfileEntry 26 }

         adslAturChanConfFastMaxTxRate  OBJECT-TYPE
             SYNTAX      Unsigned32
             UNITS       "bps"
             MAX-ACCESS  read-create
             STATUS      current
             DESCRIPTION
                 "Configured Maximum Transmit rate for `Fast' channels,
                 in bps.  See adslAturConfRateChanRatio for information
                 regarding RADSL mode and ATUC transmit rate
                 for ATUR receive rates."
         ::= { adslLineConfProfileEntry 27 }

         adslAturChanConfInterleaveMaxTxRate OBJECT-TYPE
             SYNTAX      Unsigned32
             UNITS       "bps"
             MAX-ACCESS  read-create
             STATUS      current
             DESCRIPTION
                 "Configured Maximum Transmit rate for `Interleave'
                 channels, in bps.  See adslAturConfRateChanRatio for
                 information regarding RADSL mode and see
                 ATUC transmit rate for ATUR receive rates."
         ::= { adslLineConfProfileEntry 28 }

         adslAturChanConfMaxInterleaveDelay OBJECT-TYPE
             SYNTAX      INTEGER(0..255)
             UNITS        "milli-seconds"
             MAX-ACCESS  read-create
             STATUS      current
             DESCRIPTION
                 "Configured maximum Interleave Delay for this channel.

                 Interleave delay applies only to the interleave channel
                 and defines the mapping (relative spacing) between
                 subsequent input bytes at the interleaver input and
                 their placement in the bit stream at the interleaver
                 output.  Larger numbers provide greater separation
                 between consecutive input bytes in the output bit
                 stream allowing for improved impulse noise immunity
                 at the expense of payload latency."
         ::= { adslLineConfProfileEntry 29 }

         adslLineConfProfileRowStatus OBJECT-TYPE
             SYNTAX          RowStatus
             MAX-ACCESS      read-create
             STATUS          current
             DESCRIPTION
                 "This object is used to create a new row or modify or
                 delete an existing row in this table.
                 A profile activated by setting this object to
                 `active'.  When `active' is set, the system
                 will validate the profile.

                 Before a profile can be deleted or taken out of
                 service, (by setting this object to `destroy' or
                 `outOfService') it must be first unreferenced
                 from all associated lines.

                 If the implementator of this MIB has chosen not
                 to implement `dynamic assignment' of profiles, this
                 object's MIN-ACCESS is read-only and its value
                 is always to be `active'."
         ::= { adslLineConfProfileEntry 30 }

         adslLineAlarmConfProfileTable    OBJECT-TYPE
             SYNTAX          SEQUENCE OF AdslLineAlarmConfProfileEntry
             MAX-ACCESS      not-accessible
             STATUS          current
             DESCRIPTION
                 "This table contains information on the ADSL line
                 configuration.  One entry in this table reflects a
                 profile defined by a manager which can be used to
                 configure the modem for a physical line"
         ::= { adslMibObjects 15}

         adslLineAlarmConfProfileEntry    OBJECT-TYPE
             SYNTAX          AdslLineAlarmConfProfileEntry
             MAX-ACCESS      not-accessible
             STATUS          current
             DESCRIPTION
                 "Each entry consists of a list of parameters that
                 represents the configuration of an ADSL modem.

                 When `dynamic' profiles are implemented, a default
                 profile will always exist.  This profile's name will
                 be set to `DEFVAL' and its parameters will be set to
                 vendor specific values, unless otherwise specified
                 in this document.

                 When `static' profiles are implemented, profiles
                 are automaticly created or destroyed as ADSL
                 physical lines are discovered and removed by
                 the system.  The name of the profile will be
                 equivalent to the decimal value of the line's
                 interface index.
                 "
             INDEX { IMPLIED adslLineAlarmConfProfileName}
         ::= { adslLineAlarmConfProfileTable 1}

         AdslLineAlarmConfProfileEntry ::=
             SEQUENCE {
             adslLineAlarmConfProfileName          SnmpAdminString,
             adslAtucThresh15MinLofs               INTEGER,
             adslAtucThresh15MinLoss               INTEGER,
             adslAtucThresh15MinLols               INTEGER,
             adslAtucThresh15MinLprs               INTEGER,
             adslAtucThresh15MinESs                INTEGER,
             adslAtucThreshFastRateUp              Unsigned32,
             adslAtucThreshInterleaveRateUp        Unsigned32,
             adslAtucThreshFastRateDown            Unsigned32,
             adslAtucThreshInterleaveRateDown      Unsigned32,
             adslAtucInitFailureTrapEnable         INTEGER,
             adslAturThresh15MinLofs               INTEGER,
             adslAturThresh15MinLoss               INTEGER,
             adslAturThresh15MinLprs               INTEGER,
             adslAturThresh15MinESs                INTEGER,
             adslAturThreshFastRateUp              Unsigned32,
             adslAturThreshInterleaveRateUp        Unsigned32,
             adslAturThreshFastRateDown            Unsigned32,
             adslAturThreshInterleaveRateDown      Unsigned32,
             adslLineAlarmConfProfileRowStatus     RowStatus
             }

         adslLineAlarmConfProfileName    OBJECT-TYPE
             SYNTAX          SnmpAdminString (SIZE (1..32))
             MAX-ACCESS      not-accessible
             STATUS          current
             DESCRIPTION
                 "This object is used by the line alarm configuration
                 table in order to identify a row of this table.

                 When `dynamic' profiles are implemented, the profile
                 name is user specified.  Also, the system will always
                 provide a default profile whose name is `DEFVAL'.

                 When `static' profiles are implemented, there is an
                 one-to-one relationship between each line and its
                 profile.  In which case, the profile name will
                 need to algorithmicly represent the Line's ifIndex.
                 Therefore, the profile's name is a decimalized string
                 of the ifIndex that is fixed-length (i.e., 10) with
                 leading zero(s).  For example, the profile name for
                 ifIndex which equals '15' will be '0000000015'."
         ::= { adslLineAlarmConfProfileEntry 1}

         adslAtucThresh15MinLofs OBJECT-TYPE
             SYNTAX      INTEGER(0..900)
             UNITS       "seconds"
             MAX-ACCESS  read-create
             STATUS      current
             DESCRIPTION
                 "The number of Loss of Frame Seconds
                 encountered by an ADSL interface within any given 15
                 minutes performance data collection period, which
                 causes the SNMP agent to send an
                 adslAtucPerfLofsThreshTrap.
                 One trap will be sent per interval per interface.
                 A value of `0' will disable the trap."
         ::= { adslLineAlarmConfProfileEntry 2}

         adslAtucThresh15MinLoss  OBJECT-TYPE
             SYNTAX      INTEGER(0..900)
             UNITS       "seconds"
             MAX-ACCESS  read-create
             STATUS      current
             DESCRIPTION
                 "The number of Loss of Signal Seconds
                 encountered by an ADSL interface within any given 15
                 minutes performance data collection period, which
                 causes the SNMP agent to send an
                 adslAtucPerfLossThreshTrap.
                 One trap will be sent per interval per interface.
                 A value of `0' will disable the trap."
         ::= { adslLineAlarmConfProfileEntry 3}

         adslAtucThresh15MinLols  OBJECT-TYPE
             SYNTAX      INTEGER(0..900)
             UNITS       "seconds"
             MAX-ACCESS  read-create
             STATUS      current
             DESCRIPTION
                 "The number of Loss of Link Seconds
                 encountered by an ADSL interface within any given 15
                 minutes performance data collection period, which
                 causes the SNMP agent to send an
                 adslAtucPerfLolsThreshTrap.
                 One trap will be sent per interval per interface.
                 A value of `0' will disable the trap."
         ::= { adslLineAlarmConfProfileEntry 4}

         adslAtucThresh15MinLprs  OBJECT-TYPE
             SYNTAX      INTEGER(0..900)
             UNITS       "seconds"
             MAX-ACCESS  read-create
             STATUS      current
             DESCRIPTION
                 "The number of Loss of Power Seconds
                 encountered by an ADSL interface within any given 15
                 minutes performance data collection period, which
                 causes the SNMP agent to send an
                 adslAtucPerfLprsThreshTrap.
                 One trap will be sent per interval per interface.
                 A value of `0' will disable the trap."
         ::= { adslLineAlarmConfProfileEntry 5}

         adslAtucThresh15MinESs  OBJECT-TYPE
             SYNTAX      INTEGER(0..900)
             UNITS       "seconds"
             MAX-ACCESS  read-create
             STATUS      current
             DESCRIPTION
                 "The number of Errored Seconds
                 encountered by an ADSL interface within any given 15
                 minutes performance data collection period, which
                 causes the SNMP agent to send an
                 adslAtucPerfESsThreshTrap.
                 One trap will be sent per interval per interface.
                 A value of `0' will disable the trap."
         ::= { adslLineAlarmConfProfileEntry 6}

         adslAtucThreshFastRateUp OBJECT-TYPE
             SYNTAX      Unsigned32
             UNITS       "bps"
             MAX-ACCESS  read-create
             STATUS      current
             DESCRIPTION
                 "Applies to `Fast' channels only.
                 Configured change in rate causing an
                 adslAtucRateChangeTrap. A trap is produced when:
                 ChanCurrTxRate >= ChanPrevTxRate plus the value of
                 this object. A value of `0' will disable the trap."
         ::= { adslLineAlarmConfProfileEntry 7}

         adslAtucThreshInterleaveRateUp OBJECT-TYPE
             SYNTAX      Unsigned32
             UNITS       "bps"
             MAX-ACCESS  read-create
             STATUS      current
             DESCRIPTION
                 "Applies to `Interleave' channels only.
                 Configured change in rate causing an
                 adslAtucRateChangeTrap.  A trap is produced when:
                 ChanCurrTxRate >= ChanPrevTxRate plus the value of
                 this object. A value of `0' will disable the trap."
         ::= { adslLineAlarmConfProfileEntry 8}

         adslAtucThreshFastRateDown OBJECT-TYPE
             SYNTAX      Unsigned32
             UNITS       "bps"
             MAX-ACCESS  read-create
             STATUS      current
             DESCRIPTION
                 "Applies to `Fast' channels only.
                 Configured change in rate causing an
                 adslAtucRateChangeTrap.  A trap is produced when:
                 ChanCurrTxRate <= ChanPrevTxRate minus the value of
                 this object. A value of `0' will disable the trap."
         ::= { adslLineAlarmConfProfileEntry 9 }

         adslAtucThreshInterleaveRateDown OBJECT-TYPE
             SYNTAX      Unsigned32
             UNITS       "bps"
             MAX-ACCESS  read-create
             STATUS      current
             DESCRIPTION
                 "Applies to `Interleave' channels only.
                 Configured change in rate causing an
                 adslAtucRateChangeTrap.  A trap is produced when:
                 ChanCurrTxRate <= ChanPrevTxRate minus the value of
                 this object. A value of `0' will disable the trap."
         ::= { adslLineAlarmConfProfileEntry 10 }

         adslAtucInitFailureTrapEnable OBJECT-TYPE
             SYNTAX      INTEGER {
                 enable (1),
                 disable (2)
             }
             MAX-ACCESS  read-create
             STATUS      current
             DESCRIPTION
                 "Enables and disables the InitFailureTrap.  This
                 object is defaulted disable(2)."
         DEFVAL { disable }
         ::= { adslLineAlarmConfProfileEntry 11 }

         adslAturThresh15MinLofs OBJECT-TYPE
             SYNTAX      INTEGER(0..900)
             UNITS       "seconds"
             MAX-ACCESS  read-create
             STATUS      current
             DESCRIPTION
                 "The number of Loss of Frame Seconds
                 encountered by an ADSL interface within any given 15
                 minutes performance data collection period, which
                 causes the SNMP agent to send an
                 adslAturPerfLofsThreshTrap.
                 One trap will be sent per interval per interface.
                 A value of `0' will disable the trap."
         ::= { adslLineAlarmConfProfileEntry 12 }

         adslAturThresh15MinLoss  OBJECT-TYPE
             SYNTAX      INTEGER(0..900)
             UNITS       "seconds"
             MAX-ACCESS  read-create
             STATUS      current
             DESCRIPTION
                 "The number of Loss of Signal Seconds
                 encountered by an ADSL interface within any given 15
                 minutes performance data collection period, which
                 causes the SNMP agent to send an
                 adslAturPerfLossThreshTrap.
                 One trap will be sent per interval per interface.
                 A value of `0' will disable the trap."
         ::= { adslLineAlarmConfProfileEntry 13 }

         adslAturThresh15MinLprs  OBJECT-TYPE
             SYNTAX      INTEGER(0..900)
             UNITS       "seconds"
             MAX-ACCESS  read-create
             STATUS      current
             DESCRIPTION
                 "The number of Loss of Power Seconds
                 encountered by an ADSL interface within any given 15
                 minutes performance data collection period, which
                 causes the SNMP agent to send an
                 adslAturPerfLprsThreshTrap.
                 One trap will be sent per interval per interface.
                 A value of `0' will disable the trap."
         ::= { adslLineAlarmConfProfileEntry 14 }

         adslAturThresh15MinESs  OBJECT-TYPE
             SYNTAX      INTEGER(0..900)
             UNITS       "seconds"
             MAX-ACCESS  read-create
             STATUS      current
             DESCRIPTION
                 "The number of Errored Seconds
                 encountered by an ADSL interface within any given 15
                 minutes performance data collection period, which
                 causes the SNMP agent to send an
                 adslAturPerfESsThreshTrap.
                 One trap will be sent per interval per interface.
                 A value of `0' will disable the trap."
         ::= { adslLineAlarmConfProfileEntry 15 }

         adslAturThreshFastRateUp OBJECT-TYPE
             SYNTAX      Unsigned32
             UNITS       "bps"
             MAX-ACCESS  read-create
             STATUS      current
             DESCRIPTION
                 "Applies to `Fast' channels only.
                 Configured change in rate causing an
                 adslAturRateChangeTrap.  A trap is produced when:
                 ChanCurrTxRate >= ChanPrevTxRate plus the value of
                 this object. A value of `0' will disable the trap."
         ::= { adslLineAlarmConfProfileEntry 16 }

         adslAturThreshInterleaveRateUp OBJECT-TYPE
             SYNTAX      Unsigned32
             UNITS       "bps"
             MAX-ACCESS  read-create
             STATUS      current
             DESCRIPTION
                 "Applies to `Interleave' channels only.
                 configured change in rate causing an
                 adslAturRateChangeTrap.  A trap is produced when:
                 ChanCurrTxRate >= ChanPrevTxRate plus the value of
                 this object. A value of `0' will disable the trap."
         ::= { adslLineAlarmConfProfileEntry 17 }

         adslAturThreshFastRateDown OBJECT-TYPE
             SYNTAX      Unsigned32
             UNITS       "bps"
             MAX-ACCESS  read-create
             STATUS      current
             DESCRIPTION
                 "Applies to `Fast' channels only.
                 Configured change in rate causing an
                 adslAturRateChangeTrap.  A trap is produced when:
                 ChanCurrTxRate <= ChanPrevTxRate minus the value of
                 this object. A value of `0' will disable the trap."
         ::= { adslLineAlarmConfProfileEntry 18 }

         adslAturThreshInterleaveRateDown OBJECT-TYPE
             SYNTAX      Unsigned32
             UNITS       "bps"
             MAX-ACCESS  read-create
             STATUS      current
             DESCRIPTION
                 "Applies to `Interleave' channels only.
                 Configured change in rate causing an
                 adslAturRateChangeTrap.  A trap is produced when:
                 ChanCurrTxRate <= ChanPrevTxRate minus the value of
                 this object. A value of `0' will disable the trap."
         ::= { adslLineAlarmConfProfileEntry 19 }

         adslLineAlarmConfProfileRowStatus OBJECT-TYPE
             SYNTAX          RowStatus
             MAX-ACCESS      read-create
             STATUS          current
             DESCRIPTION
                 "This object is used to create a new row or modify or
                 delete an existing row in this table.

                 A profile activated by setting this object to
                 `active'.  When `active' is set, the system
                 will validate the profile.

                 Before a profile can be deleted or taken out of
                 service, (by setting this object to `destroy' or
                 `outOfService') it must be first unreferenced
                 from all associated lines.

                 If the implementator of this MIB has chosen not
                 to implement `dynamic assignment' of profiles, this
                 object's MIN-ACCESS is read-only and its value
                 is always to be `active'."
         ::= { adslLineAlarmConfProfileEntry 20 }

         -- Line Code Specific Tables

         -- These are place holders for the Line Code Specific MIBs
         -- once they become available.

--         adslLCSMib  OBJECT IDENTIFIER ::= { adslMibObjects 16 }

   -- trap definitions

   adslTraps OBJECT IDENTIFIER ::= { adslLineMib 2 }

   adslAtucTraps OBJECT IDENTIFIER ::= { adslTraps 1 }

         adslAtucPerfLofsThreshTrap      NOTIFICATION-TYPE
             OBJECTS { adslAtucPerfCurr15MinLofs,
                       adslAtucThresh15MinLofs }
             STATUS  current
             DESCRIPTION
                 "Loss of Framing 15-minute interval threshold reached."
         ::= { adslAtucTraps 0 1 }

         adslAtucPerfLossThreshTrap      NOTIFICATION-TYPE
             OBJECTS { adslAtucPerfCurr15MinLoss,
                       adslAtucThresh15MinLoss }
             STATUS  current
             DESCRIPTION
                 "Loss of Signal 15-minute interval threshold reached."
         ::= { adslAtucTraps 0 2 }

         adslAtucPerfLprsThreshTrap      NOTIFICATION-TYPE
             OBJECTS { adslAtucPerfCurr15MinLprs,
                       adslAtucThresh15MinLprs }
             STATUS  current
             DESCRIPTION
                 "Loss of Power 15-minute interval threshold reached."
         ::= { adslAtucTraps 0 3 }

         adslAtucPerfESsThreshTrap       NOTIFICATION-TYPE
             OBJECTS { adslAtucPerfCurr15MinESs,
                       adslAtucThresh15MinESs }
             STATUS  current
             DESCRIPTION
                 "Errored Second 15-minute interval threshold reached."
         ::= { adslAtucTraps 0 4 }

         adslAtucRateChangeTrap  NOTIFICATION-TYPE
             OBJECTS { adslAtucChanCurrTxRate,
                       adslAtucChanPrevTxRate }
             STATUS  current
             DESCRIPTION
                 "The ATUCs transmit rate has changed (RADSL mode only)"
         ::= { adslAtucTraps 0 5 }

         adslAtucPerfLolsThreshTrap      NOTIFICATION-TYPE
             OBJECTS { adslAtucPerfCurr15MinLols,
                       adslAtucThresh15MinLols }
             STATUS  current
             DESCRIPTION
                 "Loss of Link 15-minute interval threshold reached."
         ::= { adslAtucTraps 0 6 }

         adslAtucInitFailureTrap NOTIFICATION-TYPE
             OBJECTS { adslAtucCurrStatus }
             STATUS  current
             DESCRIPTION
                 "ATUC initialization failed. See adslAtucCurrStatus
                 for potential reasons."
         ::= { adslAtucTraps 0 7 }

   adslAturTraps OBJECT IDENTIFIER ::= { adslTraps 2 }

         adslAturPerfLofsThreshTrap      NOTIFICATION-TYPE
             OBJECTS { adslAturPerfCurr15MinLofs,
                       adslAturThresh15MinLofs }
             STATUS  current
             DESCRIPTION
                 "Loss of Framing 15-minute interval threshold reached."
         ::= { adslAturTraps 0 1 }

         adslAturPerfLossThreshTrap      NOTIFICATION-TYPE
             OBJECTS { adslAturPerfCurr15MinLoss,
                       adslAturThresh15MinLoss }
             STATUS  current
             DESCRIPTION
                 "Loss of Signal 15-minute interval threshold reached."
         ::= { adslAturTraps 0 2 }

         adslAturPerfLprsThreshTrap      NOTIFICATION-TYPE
             OBJECTS { adslAturPerfCurr15MinLprs,
                       adslAturThresh15MinLprs }
             STATUS  current
             DESCRIPTION
                 "Loss of Power 15-minute interval threshold reached."
         ::= { adslAturTraps 0 3 }

         adslAturPerfESsThreshTrap       NOTIFICATION-TYPE
             OBJECTS { adslAturPerfCurr15MinESs,
                       adslAturThresh15MinESs }
             STATUS  current
             DESCRIPTION
                 "Errored Second 15-minute interval threshold reached."
         ::= { adslAturTraps 0 4 }

         adslAturRateChangeTrap  NOTIFICATION-TYPE
             OBJECTS { adslAturChanCurrTxRate,
                       adslAturChanPrevTxRate }
             STATUS  current
             DESCRIPTION
                 "The ATURs transmit rate has changed (RADSL mode only)"
         ::= { adslAturTraps 0 5 }

         -- no adslAturPerfLolsThreshTrap possible { 0 6 }

         -- no adslAturInitFailureTrap possible { 0 7 }

   -- conformance information


   END

-- mini ADSL private MIB
ZXDSLAM-MIB DEFINITIONS ::= BEGIN
IMPORTS
        MODULE-IDENTITY, TimeTicks, OBJECT-TYPE,
	NOTIFICATION-TYPE, enterprises, Counter32,IpAddress FROM SNMPv2-SMI
        RowStatus, DateAndTime,TEXTUAL-CONVENTION FROM SNMPv2-TC
-- liqx del this line 0129      	atmVcCrossConnectIndex FROM ATM-MIB
	AtmVpIdentifier, AtmVcIdentifier FROM ATM-TC-MIB
	InterfaceIndex, ifIndex FROM IF-MIB;
-- ifEntry FROM IF-MIB;
-- 	PhysicalIndex FROM ENTITY-MIB;

-- ZTE
zte MODULE-IDENTITY
LAST-UPDATED "2703200000Z"
ORGANIZATION ""
CONTACT-INFO ""
DESCRIPTION  "Initial Version"
::= { enterprises 3902 } 

-- ADSL product
zxAdsl OBJECT IDENTIFIER ::= { zte 1004 }

-- access line
zxAdslAn OBJECT IDENTIFIER ::= { zxAdsl 3 }

-- self develop
zxAdslAnOwn OBJECT IDENTIFIER ::= { zxAdslAn 1 }

-- mini DSLAM ADSL8416
zxDslam OBJECT IDENTIFIER ::= { zxAdslAnOwn 2 }

zxDslamAim  OBJECT IDENTIFIER ::= { zxDslam 1 }
zxDslamTrap OBJECT IDENTIFIER ::= { zxDslam 2 }
                      
DisplayString ::= OCTET STRING

ZTEdsl8426SubCardType ::= TEXTUAL-CONVENTION
   STATUS    current
   DESCRIPTION
     "This is the referenced type of a sub card
     of the 8426"
   SYNTAX    INTEGER
           {
           other(0),
           adsl(1),
           shdsl(2),
           adslOisdn(3)
           }

-- Part 1: ATM networking
-- card table
--
--zxDslamCardTable OBJECT-TYPE
--	SYNTAX		SEQUENCE OF ZxDslamCardEntry
--	MAX-ACCESS	not-accessible
--	STATUS		current
--	DESCRIPTION	"A list of card entries."
--	::= { zxDslamAim 1 }
--
--zxDslamCardEntry OBJECT-TYPE
--	SYNTAX		ZxDslamCardEntry
--	MAX-ACCESS	not-accessible
--	STATUS		current
--	DESCRIPTION	
--        "An card entry containing objects describing the card in some slot."
--	INDEX	{ zxDslamCardIndex }
--	::= { zxDslamCardTable 1 }
--
--ZxDslamCardEntry ::= SEQUENCE {
--    zxDslamCardIndex	INTEGER,
--    zxDslamCardType	INTEGER,
--    zxDslamCardFrame  INTEGER,
--    zxDslamCardShelf  INTEGER,
--    zxDslamCardSlot	INTEGER,
--    zxDslamCardPortNum INTEGER,
--    zxDslamCardstandbyStatus INTEGER,
--    zxDslamCardDescr	DisplayString,
--    zxDslamCardAdminStatus	INTEGER,
--    zxDslamCardOperStatus	INTEGER,
--    zxDslamCardLastChange	TimeTicks,
--    zxDslamHardwareVersion    DisplayString, 	
--    zxDslamSoftwareVersion    DisplayString
--    zxDslamCardEntPhysicalIndex	PhysicalIndex            
--	}
--
--zxDslamCardIndex OBJECT-TYPE
--    SYNTAX	INTEGER
--    MAX-ACCESS  not-accessible
--    STATUS      current
--    DESCRIPTION
--          "The index for this entry."
--	::= { zxDslamCardEntry 1 }
--
--zxDslamCardType OBJECT-TYPE
--	SYNTAX	INTEGER {
--                unknown(0),  
--                core(1),
--                wan-ds3(2),
--                wan-sdh(3),
--                power(4),
--	          atuc-ti(5),   ATUC card
--        	  atuc-al(6),   ATUC card
--        	  other(7) ,
--        	  corea (8),
--                corec(9),
--                wana1(10),
--                wanad(11),
--                wane(12),
--                esu(13),
--                atucd(14),
--                atuce(15),
--                atucf(16),
--                atucg(17),
--                atuch(18),
--                atuci(19)
--            }
--	MAX-ACCESS	read-only
--	STATUS		current
--	DESCRIPTION	
--   		"The type of card, distinguished according to 
--		service type carried or function."
--	::= { zxDslamCardEntry 2 }
--
--zxDslamCardFrame   OBJECT-TYPE   
--  SYNTAX  INTEGER
--  MAX-ACCESS  read-only
--  STATUS current
--  DESCRIPTION	
--		"The number of frame which contained this card."
--	::= { zxDslamCardEntry 3 }
--	
--zxDslamCardShelf   OBJECT-TYPE   
--  SYNTAX  INTEGER
--  MAX-ACCESS read-only
--  STATUS current
--  DESCRIPTION	
--		"The number of shelf which contained this card."
--	::= { zxDslamCardEntry 4 }
--	
--zxDslamCardSlot	OBJECT-TYPE
-- 	SYNTAX		INTEGER
-- 	MAX-ACCESS	read-only
-- 	STATUS		current
-- 	DESCRIPTION	
--		"The number of slot which contained this card."
-- 	::= { zxDslamCardEntry 5 }
--
--zxDslamCardPortNum   OBJECT-TYPE
--    SYNTAX   INTEGER
--	MAX-ACCESS read-only
--	STATUS    current
--	DESCRIPTION	
--		"The number of port which contained in this card."
-- 	::= { zxDslamCardEntry 6 }
--
--zxDslamCardstandbyStatus   OBJECT-TYPE
--	SYNTAX	INTEGER {
--	                  unknown(0),
--                    standby(1), 
--                    providingService(2),
--                    other(3)
--                }
--	MAX-ACCESS	read-write
--	STATUS		current
--	DESCRIPTION	
--		"The type of card, distinguished according to 
--		service type carried  or function."
--	::= { zxDslamCardEntry 7 }
--
--zxDslamCardDescr OBJECT-TYPE
--	SYNTAX		DisplayString (SIZE (0..255))
--	MAX-ACCESS	read-only
--	STATUS		current
--    	DESCRIPTION	
--		"A textual string containing information about the card.
--		This string should include the manufacturer, 
--		the product name, type, function and version of the hardware."
--	::= { zxDslamCardEntry 8 }
--
--zxDslamCardAdminStatus	OBJECT-TYPE
--	SYNTAX	INTEGER {
--				up(1),		 ready
--				down(2),	 deactiivate
--				testing(3)	 in some test mode
--			}
--	MAX-ACCESS	read-write
--	STATUS		current
--	DESCRIPTION	
--		"The desired state of the card. 
--		The down (2) and testing (3) state indicate	
--		the card doesn't present service currently."
--	::= { zxDslamCardEntry 9 }
--	
--zxDslamCardOperStatus	OBJECT-TYPE
--	SYNTAX	INTEGER {
--				up(1),		 ready
--				down(2),	 fault occur or pulled out from the slot
--				testing(3)	 in some test mode
--			}
--	MAX-ACCESS	read-only
--	STATUS		current
--	DESCRIPTION	
--		"The current operational state of the card. 
--		The down (2) and testing (3) mode indicate that 
--		no service can be presented by the card."
--	::= { zxDslamCardEntry 10 }
--
--zxDslamCardLastChange	OBJECT-TYPE
--	SYNTAX		TimeTicks
--	MAX-ACCESS	read-only
--	STATUS		current
--	DESCRIPTION	
--			"The value of sysUpTime at the time 
--			the card entered its current operational state. 
--			If the current state was entered prior to the last 
--			reinitialization of the	local network management subsystem, 
--			then this object contains a zero value."
--	::= { zxDslamCardEntry 11 }
--	
--zxDslamHardwareVersion  OBJECT-TYPE
--	SYNTAX		DisplayString (SIZE (0..32))
--	MAX-ACCESS	read-only
--	STATUS		current
--        DESCRIPTION	"the hardware Version of this card"
--	::= { zxDslamCardEntry 12 } 
--	
--	
--zxDslamSoftwareVersion  OBJECT-TYPE
--	SYNTAX		DisplayString (SIZE (0..32))
--	MAX-ACCESS	read-only
--	STATUS		current
--        DESCRIPTION	"the software Version of this card"
--	::= { zxDslamCardEntry 13 } 
--	
--


-- liqx chg zxDslamPortIfIndexMappingTable to zxDslamMapIfIndexToPortTable 

zxDslamMapIfIndexToPortTable OBJECT-TYPE
	SYNTAX		SEQUENCE OF ZxDslamMapIfIndexToPortEntry
	MAX-ACCESS		not-accessible
	STATUS		current
	DESCRIPTION
		"zxDslamMapIfIndexToPortTable  is used to show the mapping from 
		ifIndex to Port."
	::= {zxDslamAim 2 }

zxDslamMapIfIndexToPortEntry	OBJECT-TYPE
	SYNTAX		ZxDslamMapIfIndexToPortEntry
	MAX-ACCESS		not-accessible
	STATUS		current
	DESCRIPTION
		"An entry in the zxDslamMapIfIndexToPortTable. There is one 
		 entry  in the table corresponding to each active row in the
		 ifTable for which there is a non-zero cpn and ifindex."
--	INDEX	{ zxDslamMappingFrame,zxDslamMappingShelf,
--	zxDslamMappingSlot,zxDslamMappingPort,zxDslamPortMappingifIndex}
	INDEX	{ zxDslamMapIfIndex}
	::= {zxDslamMapIfIndexToPortTable 1 }

ZxDslamMapIfIndexToPortEntry	::= SEQUENCE {
--	zxDslamMappingFrame INTEGER,
--	zxDslamMappingShelf INTEGER,
--	zxDslamMappingSlot  INTEGER,
    zxDslamMapIfIndex   InterfaceIndex,
    zxDslamMapPort      INTEGER
}

--zxDslamMappingFrame    OBJECT-TYPE
--    SYNTAX  INTEGER
--    MAX-ACCESS  not-accessible
--    STATUS      current
--    DESCRIPTION
--            "The sub-index for this entry."
--  ::= {zxDslamPortIfIndexMappingEntry 1 } 
--zxDslamMappingShelf    OBJECT-TYPE
--    SYNTAX  INTEGER
--    MAX-ACCESS  not-accessible
--    STATUS      current
--    DESCRIPTION
--            "The sub-index for this entry."
--  ::= {zxDslamPortIfIndexMappingEntry 2 } 
--zxDslamMappingSlot     OBJECT-TYPE
--    SYNTAX  INTEGER
--    MAX-ACCESS  not-accessible
--    STATUS      current
--    DESCRIPTION
--            "The sub-index for this entry."
--  ::= {zxDslamPortIfIndexMappingEntry 3 } 
zxDslamMapPort     OBJECT-TYPE
    SYNTAX  INTEGER
    MAX-ACCESS  read-only
    STATUS      current
    DESCRIPTION
            "The sub-index for this entry."
  ::= {zxDslamMapIfIndexToPortEntry 2 }             
  
zxDslamMapIfIndex	OBJECT-TYPE
	SYNTAX			InterfaceIndex
	MAX-ACCESS		not-accessible
	STATUS			current
	DESCRIPTION
		 "The value of InterfaceIndex of the same circuitnum."
	::= {zxDslamMapIfIndexToPortEntry 1 } 

-- sys date and time	
zxDslamSysDateAndTime	OBJECT-TYPE
	SYNTAX		DateAndTime
	MAX-ACCESS	read-write
	STATUS		current
	DESCRIPTION	"The system time of ZX Dslam "
	::= { zxDslamAim 3 }

-- DSLAM card number
--zxDslamCardNumber  OBJECT-TYPE
--  SYNTAX		INTEGER
--  MAX-ACCESS read-only
--  STATUS  current
--  DESCRIPTION	"The  Cards number of ZX Dslam "
--  ::= {zxDslamAim 4 }

-- Mapping of VCX and  subscriber name 
zxDslamVcxSubscriberMapTable OBJECT-TYPE
  SYNTAX		SEQUENCE OF ZxDslamVcxSubscriberMapEntry
  MAX-ACCESS		not-accessible
  STATUS		current
  DESCRIPTION
	"zxDslamSubscriberVcxIndexMapTab  is used to show the mapping from 
	Vcx	to subscriber name."
  ::= {zxDslamAim 4 }

zxDslamVcxSubscriberMapEntry OBJECT-TYPE
    SYNTAX		ZxDslamVcxSubscriberMapEntry
	MAX-ACCESS		not-accessible
	STATUS		current
	DESCRIPTION
		"An entry in the zxDslamVcxSubscriberMapTable. There is one 
		 entry  in the table corresponding to each active row in the
		 AtmVcCrossConnectTable, there is subscriber name."
	INDEX	{atmVcCrossConnectLiIndex }
	::= {zxDslamVcxSubscriberMapTable 1 } 
-- liqx chg the atmVcCrossConnectIndex to atmVcCrossConnectLiIndex above on 0129

ZxDslamVcxSubscriberMapEntry ::= SEQUENCE {
	atmVcCrossConnectLiIndex	INTEGER,
	zxDslamVcxSubscribeName     DisplayString,
	zxDslamPppSubscribeName     DisplayString,
	zxDslamPppSubBindPortEnable INTEGER
}
-- liqx add the atmVcCrossConnectLiIndex line above on 0129

atmVcCrossConnectLiIndex OBJECT-TYPE
     SYNTAX         INTEGER (1..2147483647)
     MAX-ACCESS     not-accessible
     STATUS         current
     DESCRIPTION
      "A unique value to identify this VC cross-connect.
       For each VCL associated with this cross-connect,
       the agent reports this cross-connect index value
       in the atmVclCrossConnectIdentifier attribute of
       the corresponding atmVclTable entries."
     ::= { zxDslamVcxSubscriberMapEntry 1 }
-- liqx add the atmVcCrossConnectLiIndex obj-def above on 0129

zxDslamVcxSubscribeName OBJECT-TYPE
  SYNTAX	DisplayString(SIZE(0..32))
  MAX-ACCESS read-write
  STATUS  current
  DESCRIPTION	"The  subscriber name of vcx "
  ::= {zxDslamVcxSubscriberMapEntry 2 }   
-- liqx chg the 1 to 2 above on 0129

zxDslamPppSubscribeName OBJECT-TYPE
  SYNTAX	DisplayString(SIZE(0..127))
  MAX-ACCESS read-write
  STATUS  current
  DESCRIPTION	"The  subscriber name of PPP "
  ::= {zxDslamVcxSubscriberMapEntry 3 } 

zxDslamPppSubBindPortEnable OBJECT-TYPE
  SYNTAX      INTEGER { enabled(1), disabled(2) }
  MAX-ACCESS read-write
  STATUS  current
  DESCRIPTION	"Bind a adsl port to a PPP usrName or not "
  ::= {zxDslamVcxSubscriberMapEntry 4 } 
    
-- liqx add the CMDParmTable(5)
zxDslamCMDParmTable  OBJECT-TYPE
     SYNTAX         SEQUENCE OF ZxDslamCMDParmEntry
     MAX-ACCESS     not-accessible
     STATUS         current
     DESCRIPTION
        	"The ZXDslam CMDParm table. "
     ::= {zxDslamAim 5 }

zxDslamCMDParmEntry	    OBJECT-TYPE
     SYNTAX         ZxDslamCMDParmEntry   
     MAX-ACCESS     not-accessible
     STATUS         current
     DESCRIPTION
		"An entry in the ZXDslam CMDParm table  "
     INDEX  {  zxDslamCMDParmIndex }	
     ::= { zxDslamCMDParmTable  1}

ZxDslamCMDParmEntry  ::= SEQUENCE  {
     zxDslamCMDParmIndex		INTEGER ,
     zxDslamCMDParmIPAddr		DisplayString,
     zxDslamCMDParmFileName	    DisplayString,
     zxDslamCMDParmFtpUser	    DisplayString,
     zxDslamCMDParmFtpPwd	    DisplayString,
     zxDslamCMDParmVerDiscr	    DisplayString,
     zxDslamCMDParmPartType		INTEGER ,
     zxDslamCMDParmVerID		INTEGER                
  }
	
zxDslamCMDParmIndex		OBJECT-TYPE
        SYNTAX          INTEGER(0..1)
        MAX-ACCESS     not-accessible
	STATUS         current
	DESCRIPTION
		" The Identifier of the CMDParm."
	::= { zxDslamCMDParmEntry	1}

zxDslamCMDParmIPAddr OBJECT-TYPE
	SYNTAX		DisplayString (SIZE (0..16))
	MAX-ACCESS	read-write
	STATUS		current
        DESCRIPTION	"the Dslam command parm."
	::= { zxDslamCMDParmEntry	2}

zxDslamCMDParmFileName OBJECT-TYPE
	SYNTAX		DisplayString (SIZE (0..24))
	MAX-ACCESS	read-write
	STATUS		current
        DESCRIPTION	"the Dslam command parm."
	::= { zxDslamCMDParmEntry	3}

zxDslamCMDParmFtpUser OBJECT-TYPE
	SYNTAX		DisplayString (SIZE (0..12))
	MAX-ACCESS	read-write
	STATUS		current
        DESCRIPTION	"the Dslam command parm."
	::= { zxDslamCMDParmEntry	4}

zxDslamCMDParmFtpPwd OBJECT-TYPE
	SYNTAX		DisplayString (SIZE (0..12))
	MAX-ACCESS	read-write
	STATUS		current
        DESCRIPTION	"the Dslam command parm."
	::= { zxDslamCMDParmEntry	5}	

zxDslamCMDParmVerDiscr OBJECT-TYPE
	SYNTAX		DisplayString (SIZE (0..128))
	MAX-ACCESS	read-write
	STATUS		current
        DESCRIPTION	"the Dslam command parm."
	::= { zxDslamCMDParmEntry	6}

zxDslamCMDParmPartType		OBJECT-TYPE
        SYNTAX          INTEGER(0..31)	
        MAX-ACCESS     read-write
	STATUS         current
	DESCRIPTION
		" The Identifier of the CMDParm.  systemflag\adslflag\atmpvcflag\imaflag\vlanflag vs 1\2\4\8\16"
	::= { zxDslamCMDParmEntry	7}

zxDslamCMDParmVerID		OBJECT-TYPE
        SYNTAX          INTEGER(0..4096)
        MAX-ACCESS     read-write
	STATUS         current
	DESCRIPTION
		" The Identifier of the CMDParm."
	::= { zxDslamCMDParmEntry	8}
	
-- commandTable
zxDslamCommandTable OBJECT-TYPE
     SYNTAX         SEQUENCE OF ZxDslamCommandEntry
     MAX-ACCESS     not-accessible
     STATUS         current
     DESCRIPTION
        	"The ZXDslam command Execute table. "
     ::= {zxDslamAim 6 }

zxDslamCommandEntry		OBJECT-TYPE
     SYNTAX         ZxDslamCommandEntry
     MAX-ACCESS     not-accessible
     STATUS         current
     DESCRIPTION
		"An entry in the ZXDslam command Execute table  "
     INDEX  {  zxDslamCommandType }	
     ::= { zxDslamCommandTable  1}

ZxDslamCommandEntry  ::= SEQUENCE  {
     zxDslamCommandType			INTEGER ,
     zxDslamCommandLastChange	TimeTicks ,
     zxDslamCommandStatus	    INTEGER
  }

-- liqx chg the value fellow:
zxDslamCommandType OBJECT-TYPE
     SYNTAX          INTEGER 	{	
        saveRamToFlash(1),
		saveFlashToRam(2),
		readConfigFromPc(3),
		downloadFlashConfigDatatoPC(4),
		downLoadVer(5),
		updateVer(6),
		switchVer(7),
		adslChipFastTest(8),
		sysReboot(9),
		readDefConfToRam(10),
		adslChipFullTest(11),
		setDefVlan(12),
		bakFun1(13),
		bakFun2(14),
		bakFun3(15),
		bakFun4(16),
		bakFun5(17),
		bakFun6(18)
	        }
	MAX-ACCESS     read-only
	STATUS         current
	DESCRIPTION
			" The operation type of the commands."
	::= { zxDslamCommandEntry	1}
	

zxDslamCommandLastChange	OBJECT-TYPE
	SYNTAX         TimeTicks
	MAX-ACCESS     read-only
	STATUS         current
	DESCRIPTION
		  "The value of MIB-II's sysUpTime at the time this
                   Command is excuted.	When the command hasn't been excuted,
	           the value is always  zero. " 
          ::= { zxDslamCommandEntry	2 }

zxDslamCommandStatus		OBJECT-TYPE
        SYNTAX    INTEGER 	{	
         			cmdNeverExecuted(0),
 				lastCmdSuccessfulExecuted(1),
				lastCmdFailed(2),
				executing(3),
				execute(4)
				}
	MAX-ACCESS     read-write
	STATUS         current
	DESCRIPTION
		" Indicates the status of this type of command
			When the command hasn't been excuted,
		        the value is always  zero. 	
		        If want to execute the command , the manager should 
			        set the value to Execute(4)	."
	DEFVAL { 0 }
	::= {zxDslamCommandEntry 3}

-- sys ver
zxDslamSystemVersion OBJECT-TYPE
	SYNTAX		DisplayString (SIZE (0..640))
	MAX-ACCESS	read-only
	STATUS		current
        DESCRIPTION	"the Dslam System Version of this card."
::= {zxDslamAim 7 }

-- Manager IP
zxDslamSnmpManagerServerIpAddress OBJECT-TYPE
	SYNTAX		IpAddress
	MAX-ACCESS	read-write
	STATUS		current
        DESCRIPTION	"The IpAddress of the Snmp Manager Server for Trap."
::= {zxDslamAim 8 }

-- trap community
zxDslamSnmpManagerServerTrapComm OBJECT-TYPE
	SYNTAX		DisplayString (SIZE (0..64))
	MAX-ACCESS	read-write
	STATUS		current
        DESCRIPTION	"The community of the Snmp Manager Server for Trap."
::= {zxDslamAim 9 }

-- Fan tray
--zxDslamFanTable  OBJECT-TYPE
--     SYNTAX         SEQUENCE OF ZxDslamFanEntry
--     MAX-ACCESS     not-accessible
--     STATUS         current
--     DESCRIPTION
--        	"The ZXDslam fan table. "
--     ::= {zxDslamAim 9 }
--
--zxDslamFanEntry	    OBJECT-TYPE
--     SYNTAX         ZxDslamFanEntry   
--     MAX-ACCESS     not-accessible
--     STATUS         current
--     DESCRIPTION
--		"An entry in the ZXDslam fan table  "
--     INDEX  {  zxDslamFanIndex }	
--     ::= { zxDslamFanTable  1}
--
--ZxDslamFanEntry  ::= SEQUENCE  {
--     zxDslamFanIndex		INTEGER ,
--     zxDslamFanLastChange	TimeTicks ,
--     zxDslamFanOperStatus	    INTEGER
--  }
--	
--zxDslamFanIndex		OBJECT-TYPE
--        SYNTAX          INTEGER
--        MAX-ACCESS     not-accessible
--	STATUS         current
--	DESCRIPTION
--		" The Identifier of the fan."
--	::= { zxDslamFanEntry	1}
--	
--
--zxDslamFanLastChange	OBJECT-TYPE
--	SYNTAX         TimeTicks
--	MAX-ACCESS     read-only
--	STATUS         current
--	DESCRIPTION
--		  "The value of MIB-II's sysUpTime at the time this
--                   entry changes.	When the fan hasn't been changed,
--	           the value is always  zero. " 
--          ::= { zxDslamFanEntry	2 }
--
--zxDslamFanOperStatus	    OBJECT-TYPE
--        SYNTAX    INTEGER 	{	
--         	               up(1),
--         	               down(2)
--				}
--	MAX-ACCESS     read-only
--	STATUS         current
--	DESCRIPTION
--		" Indicates the status of this fan."
--	DEFVAL { 2 }
--	::= {zxDslamFanEntry 3}

-- opration output
zxAgentOpOutput OBJECT-TYPE
        SYNTAX	DisplayString (SIZE (0..127))
        MAX-ACCESS read-only
        STATUS  current
        DESCRIPTION	"The  output of agent "
  ::= {zxDslamAim  10}

-- adsl chip test output
zxAdslChipTestRep OBJECT-TYPE
        SYNTAX	DisplayString (SIZE (0..255))
        MAX-ACCESS read-only
        STATUS  current
        DESCRIPTION	"The  output of adsl chip test "
  ::= {zxDslamAim  11}
  
-- power
--zxDslamPowerTable OBJECT-TYPE
--     SYNTAX         SEQUENCE OF ZxDslamPowerEntry  
--     MAX-ACCESS     not-accessible
--     STATUS         current
--     DESCRIPTION
--        	"The ZXDslam power table. "
--     ::= {zxDslamAim 11 }
--
--zxDslamPowerEntry   OBJECT-TYPE
--     SYNTAX         ZxDslamPowerEntry   
--     MAX-ACCESS     not-accessible
--     STATUS         current
--     DESCRIPTION
--		"An entry in the ZXDslam Power table  "
--     INDEX  {  zxDslamPowerIndex }  
--     ::= { zxDslamPowerTable  1}

--ZxDslamPowerEntry  ::= SEQUENCE  {    
--     zxDslamPowerIndex		INTEGER ,
--     zxDslamPowerLastChange	TimeTicks ,
--     zxDslamPowerOperStatus	INTEGER
--  }
	
--zxDslamPowerIndex	OBJECT-TYPE
--        SYNTAX          INTEGER
--        MAX-ACCESS      not-accessible
--	STATUS          current
--	DESCRIPTION
--		" The Identifier of the power."
--	::= { zxDslamPowerEntry	1}
--	
--
--zxDslamPowerLastChange	OBJECT-TYPE
--	SYNTAX         TimeTicks
--	MAX-ACCESS     read-only
--	STATUS         current
--	DESCRIPTION
--		  "The value of MIB-II's sysUpTime at the time this
--                   power changes. When the power hasn't been changed,
--	           the value is always  zero. " 
--          ::= { zxDslamPowerEntry 2 }
--
--  zxDslamPowerOperStatus		OBJECT-TYPE 
--	SYNTAX    INTEGER  {	
--				up(1), 
--	 			down(2) 
--			   } 
--	MAX-ACCESS     read-only 
--	STATUS         current 
--	DESCRIPTION 
--		"Indicates the status of this power." 
--	DEFVAL { down } 
--	::= {zxDslamPowerEntry 3}
--	
-- authenticationtrap
    zxAuthTrapEnable OBJECT-TYPE         
	SYNTAX		INTEGER { enable(1),disable(0) }
	MAX-ACCESS 	read-write
  	STATUS  	current 
	DESCRIPTION	
		"enable or disable authentication trap" 
	DEFVAL {1} 
	::={zxDslamAim  12}
  

-- iftable for sdh
--    zxDslamifTable        OBJECT-TYPE
--       SYNTAX      SEQUENCE OF ZxDslamIfEntry
--       MAX-ACCESS  not-accessible
--       STATUS      current
--       DESCRIPTION
--               "A list of interface entries for sdh interface(ifType = ifType = VAL_ifType_sonet ,
--                VAL_ifType_sonetPath).  This table contains additional objects for the interface table of sdh interface."
--       ::= { zxDslamAim 13 }
--
--     zxDslamifEntry        OBJECT-TYPE
--       SYNTAX      ZxDslamIfEntry
--       MAX-ACCESS  not-accessible
--       STATUS      current
--       DESCRIPTION
--               "An entry containing additional management information
--               applicable to a sdh 155M interface."
--       AUGMENTS    { ifEntry }
--       ::= { zxDslamifTable 1 }
--       
--      ZxDslamIfEntry  ::= SEQUENCE  {    
--        zxDslamIfTxOperStatus	INTEGER,
--        zxDslamIfRxOperStatus	INTEGER
--      }
--     
--      zxDslamIfTxOperStatus OBJECT-TYPE
--         SYNTAX  INTEGER {
--                   up(1),         ready to pass packets
--                   down(2),
--                   testing(3)    in some test mode
--               }
--        MAX-ACCESS  read-only
--        STATUS      current
--        DESCRIPTION
--               "The current Tx direction operational state of the sdh  interface.
--               If sdh interface recieve LRDI or PRDI signal ,it will change to be down"
--        ::= { zxDslamifEntry 1 }
--       
--      zxDslamIfRxOperStatus OBJECT-TYPE
--        SYNTAX  INTEGER {
--                   up(1),         ready to pass packets
--                   down(2),
--                   testing(3)    in some test mode
--               }
--       MAX-ACCESS  read-only
--       STATUS      current
--       DESCRIPTION
--               "The current rx direction operational state of the sdh  interface.
--               if sdh interface can't receive the signal from its peer(LOS) , it will 
--               change to be down "
--       ::= { zxDslamifEntry 2 }

-- li add
     bridgeAgeTime  OBJECT-TYPE
          SYNTAX         INTEGER (30..30000)
          MAX-ACCESS     read-write
          STATUS         current
          DESCRIPTION
           "the aging time of the bridge transmiting table"
          ::= {zxDslamAim 13 }

     atmPVCIndexNext  OBJECT-TYPE
          SYNTAX         INTEGER (0..2147483647)
          MAX-ACCESS     read-only
          STATUS         current
          DESCRIPTION
           "This object contains an appropriate value to
            be used for atmPVCIndex when creating
            entries in the atmPVCTable.  The value
            0 indicates that no unassigned entries are
            available. To obtain the atmPVCIndex
            value for a new entry, the manager issues a
            management protocol retrieval operation to obtain
            the current value of this object.  After each
            retrieval, the agent should modify the value to
            the next unassigned index.
            After a manager retrieves a value the agent will
            determine through its local policy when this index
            value will be made available for reuse."
          ::= {zxDslamAim 14 }

--  The ATM Interface PVC Table(15) 

     atmPVCTable         OBJECT-TYPE
          SYNTAX         SEQUENCE OF AtmPVCEntry
          MAX-ACCESS     not-accessible
          STATUS         current
          DESCRIPTION
           "The PVC table."
          ::= { zxDslamAim 15 }

     atmPVCEntry         OBJECT-TYPE
          SYNTAX         AtmPVCEntry
          MAX-ACCESS     not-accessible
          STATUS         current
          DESCRIPTION
           "An entry in the PVC table."
          INDEX  {atmPVCIndex}
          ::= { atmPVCTable  1}

     AtmPVCEntry    ::= SEQUENCE  {
          atmPVCIndex			INTEGER,
     	  atmPort			INTEGER,
          atmVclVpi                     AtmVpIdentifier,
          atmVclVci                     AtmVcIdentifier,
          atmVclRowStatus               RowStatus
     }
     
     atmPVCIndex            OBJECT-TYPE
          SYNTAX         INTEGER
          MAX-ACCESS     not-accessible
          STATUS         current
          DESCRIPTION
           "The index that indicates one PVC."
          ::= { atmPVCEntry 1}
          
     atmPort             OBJECT-TYPE
          SYNTAX         INTEGER
          MAX-ACCESS     read-write
          STATUS         current
          DESCRIPTION
           "The port of this PVC"
          ::= { atmPVCEntry 2}
          
     atmVclVpi           OBJECT-TYPE
          SYNTAX         AtmVpIdentifier
          MAX-ACCESS     read-write
          STATUS         current
          DESCRIPTION
           "The VPI value of the VCL. MUST BE 0-255 in ADSL8416. "
          ::= { atmPVCEntry 3}

     atmVclVci           OBJECT-TYPE
          SYNTAX         AtmVcIdentifier
          MAX-ACCESS     read-write
          STATUS         current
          DESCRIPTION
           "The VCI value of the VCL. MUST BE 1-65535 in ADSL8416. "
          ::= { atmPVCEntry 4}

     atmVclRowStatus     OBJECT-TYPE
          SYNTAX         RowStatus
          MAX-ACCESS     read-create
          STATUS         current
          DESCRIPTION
           "This object is used to create, delete or modify a row in this table."
          DEFVAL { createAndWait }
          ::= {atmPVCEntry 5}

--     tgtIpAddrTable         OBJECT-TYPE
--          SYNTAX         SEQUENCE OF TgtIpAddrEntry
--          MAX-ACCESS     not-accessible
--          STATUS         current
--          DESCRIPTION
--           "The tgtIpAddr table."
--          ::= { zxDslamAim 16 }
--
--     tgtIpAddrEntry         OBJECT-TYPE
--          SYNTAX         TgtIpAddrEntry
--          MAX-ACCESS     not-accessible
--          STATUS         current
--          DESCRIPTION
--           "An entry in the tgtIpAddr table."
--          INDEX  {tgtIpAddrIndex}
--          ::= { tgtIpAddrTable  1}
--          
--     TgtIpAddrEntry    ::= SEQUENCE  {
--          tgtIpAddrIndex		INTEGER,
--          tgtIpAddress          DisplayString,
--          tgtIpMaskAddr          DisplayString
--       }
--
--     tgtIpAddrIndex            OBJECT-TYPE
--          SYNTAX         INTEGER
--          MAX-ACCESS     not-accessible
--          STATUS         current
--          DESCRIPTION
--           "The index that indicates one tgtIpAddr."
--          ::= { tgtIpAddrEntry 1}
--
--          tgtIpAddress   OBJECT-TYPE
--          SYNTAX         DisplayString (SIZE (0..15))
--          MAX-ACCESS     read-write
--          STATUS         current
--          DESCRIPTION
--           "the ip of the NE"
--          ::= { tgtIpAddrEntry 2 }
--
--          tgtIpMaskAddr   OBJECT-TYPE
--          SYNTAX         DisplayString (SIZE (0..15))
--          MAX-ACCESS     read-write
--          STATUS         current
--          DESCRIPTION
--           "the ip of the NE"
--          ::= { tgtIpAddrEntry 3 }
                    
     tgtGateway         OBJECT-TYPE
          SYNTAX         DisplayString (SIZE (0..15))
          MAX-ACCESS     read-write
          STATUS         current
          DESCRIPTION
           "the gateway of the NE"
          ::= { zxDslamAim 17 }

--  The route Table(18) 

     routeTable         OBJECT-TYPE
          SYNTAX         SEQUENCE OF RouteEntry
          MAX-ACCESS     not-accessible
          STATUS         current
          DESCRIPTION
           "The route table."
          ::= { zxDslamAim 18 }

     routeEntry         OBJECT-TYPE
          SYNTAX         RouteEntry
          MAX-ACCESS     not-accessible
          STATUS         current
          DESCRIPTION
           "An entry in the route table."
          INDEX  {routeIndex}
          ::= { routeTable  1}

     RouteEntry    ::= SEQUENCE  {
          routeIndex		INTEGER,
     	  desAddr			DisplayString,
          gatewayAddr       DisplayString,
          maskAddr          DisplayString,
          routeRowStatus    RowStatus
     }
     
     routeIndex            OBJECT-TYPE
          SYNTAX         INTEGER
          MAX-ACCESS     not-accessible
          STATUS         current
          DESCRIPTION
           "The index that indicates one route."
          ::= { routeEntry 1}
          
     desAddr         OBJECT-TYPE
          SYNTAX         DisplayString (SIZE (0..15))
          MAX-ACCESS     read-create
          STATUS         current
          DESCRIPTION
           "the destination of the route entry"
          ::= { routeEntry 2 }

     gatewayAddr         OBJECT-TYPE
          SYNTAX         DisplayString (SIZE (0..15))
          MAX-ACCESS     read-create
          STATUS         current
          DESCRIPTION
           "the destination of the route entry"
          ::= { routeEntry 3 }
      
     maskAddr         OBJECT-TYPE
          SYNTAX         DisplayString (SIZE (0..15))
          MAX-ACCESS     read-create
          STATUS         current
          DESCRIPTION
           "the mask of the route entry"
          ::= { routeEntry 4 }

     routeRowStatus     OBJECT-TYPE
          SYNTAX         RowStatus
          MAX-ACCESS     read-create
          STATUS         current
          DESCRIPTION
           "This object is used to create, delete or modify a row in this table."
          DEFVAL { createAndWait }
          ::= {routeEntry 5}
                        
--  The nms range Table(19) 

     nmsIpRangeTable         OBJECT-TYPE
          SYNTAX         SEQUENCE OF NmsIpRangeEntry
          MAX-ACCESS     not-accessible
          STATUS         current
          DESCRIPTION
           "The nms Ip range table."
          ::= { zxDslamAim 19 }

     nmsIpRangeEntry         OBJECT-TYPE
          SYNTAX         NmsIpRangeEntry
          MAX-ACCESS     not-accessible
          STATUS         current
          DESCRIPTION
           "An entry in the route table."
          INDEX  {nmsIpRangeIndex}
          ::= { nmsIpRangeTable  1}

     NmsIpRangeEntry    ::= SEQUENCE  {
          nmsIpRangeIndex		INTEGER,
     	  nmsAddr			DisplayString,
          nmsReadCommunity         DisplayString,
          nmsReceiveTrap		INTEGER,
          writeCommunity     DisplayString,
          nmsRowStatus    RowStatus
     }
     
     nmsIpRangeIndex            OBJECT-TYPE
          SYNTAX         INTEGER
          MAX-ACCESS     not-accessible
          STATUS         current
          DESCRIPTION
           "The index that indicates one nms."
          ::= { nmsIpRangeEntry 1}
          
     nmsAddr         OBJECT-TYPE
          SYNTAX         DisplayString (SIZE (0..15))
          MAX-ACCESS     read-create
          STATUS         current
          DESCRIPTION
           "the ip address of the nms entry"
          ::= { nmsIpRangeEntry 2 }

     nmsReadCommunity         OBJECT-TYPE
          SYNTAX         DisplayString (SIZE (0..23))
          MAX-ACCESS     read-create
          STATUS         current
          DESCRIPTION
           "the snmp community of the nms entry"
          ::= { nmsIpRangeEntry 3 }

     nmsReceiveTrap         OBJECT-TYPE
          SYNTAX         INTEGER {enable (1),disable (0) }
          MAX-ACCESS     read-create
          STATUS         current
          DESCRIPTION
           "the config of the nms on trap receiving"
          ::= { nmsIpRangeEntry 4 }

     writeCommunity         OBJECT-TYPE
          SYNTAX         DisplayString (SIZE (0..23))
          MAX-ACCESS     read-create
          STATUS         current
          DESCRIPTION
           "the trap community of the nms entry"
          ::= { nmsIpRangeEntry 5 }
          
     nmsRowStatus     OBJECT-TYPE
          SYNTAX         RowStatus
          MAX-ACCESS     read-create
          STATUS         current
          DESCRIPTION
           "This object is used to create, delete or modify a row in this table."
          DEFVAL { createAndWait }
          ::= {nmsIpRangeEntry 6}

--  The ima version(20)
     zxNMfilterSwitch  OBJECT-TYPE
          SYNTAX         INTEGER {open (1),close (0) }
          MAX-ACCESS     read-only
          STATUS         current
          DESCRIPTION
           "switch of NMS' access filter by IP "
          ::= {zxDslamAim 20 }
 
--  The high part of ifs' traffic(21)
     ifHighTrafficTable         OBJECT-TYPE
          SYNTAX         SEQUENCE OF IfHighTrafficEntry
          MAX-ACCESS     not-accessible
          STATUS         current
          DESCRIPTION
           "The auxi traffic table."
          ::= { zxDslamAim 21 }

     ifHighTrafficEntry         OBJECT-TYPE
          SYNTAX         IfHighTrafficEntry
          MAX-ACCESS     not-accessible
          STATUS         current
          DESCRIPTION
           "An entry in the auxi traffictable."
          INDEX  {ifIndex}
          ::= { ifHighTrafficTable  1}

     IfHighTrafficEntry    ::= SEQUENCE  {
          highPartIfTraffic		Counter32,
          highPartIfOutTraffic		Counter32
     }
     
     highPartIfTraffic            OBJECT-TYPE
          SYNTAX         Counter32
          MAX-ACCESS     read-only
          STATUS         current
          DESCRIPTION
           "The high half of ifs' traffic."
          ::= { ifHighTrafficEntry 1}

     highPartIfOutTraffic            OBJECT-TYPE
          SYNTAX         Counter32
          MAX-ACCESS     read-only
          STATUS         current
          DESCRIPTION
           "The high half of ifs' out traffic."
          ::= { ifHighTrafficEntry 2}   
                 
-- the IMA PVC Mode(22)
imaPvcMode OBJECT-TYPE
	SYNTAX        INTEGER{
			onepvc(1),
			twentysixpvc(2)
	}
	MAX-ACCESS read-write
	STATUS current
	DESCRIPTION
		"set the mode of ima pvc"
          ::= { zxDslamAim 22 }

--  The IMA Interface PVC Table(23) 

     imaPVCTable         OBJECT-TYPE
          SYNTAX         SEQUENCE OF ImaPVCEntry
          MAX-ACCESS     not-accessible
          STATUS         current
          DESCRIPTION
           "The IMA PVC table."
          ::= { zxDslamAim 23 }

     imaPVCEntry         OBJECT-TYPE
          SYNTAX         ImaPVCEntry
          MAX-ACCESS     not-accessible
          STATUS         current
          DESCRIPTION
           "An entry in the PVC table."
          INDEX  {imaPVCIndex}
          ::= { imaPVCTable  1}

     ImaPVCEntry    ::= SEQUENCE  {
          imaPVCIndex		INTEGER,
     	  imaGrpNum			INTEGER,
          imaVclVpi         AtmVpIdentifier,
          imaVclVci         AtmVcIdentifier
     }
     
     imaPVCIndex            OBJECT-TYPE
          SYNTAX         INTEGER
          MAX-ACCESS     not-accessible
          STATUS         current
          DESCRIPTION
           "The index that indicates one PVC."
          ::= { imaPVCEntry 1}
          
     imaGrpNum             OBJECT-TYPE
          SYNTAX         INTEGER
          MAX-ACCESS     read-write
          STATUS         current
          DESCRIPTION
           "The port of this PVC"
          ::= { imaPVCEntry 2}
          
     imaVclVpi           OBJECT-TYPE
          SYNTAX         AtmVpIdentifier
          MAX-ACCESS     read-write
          STATUS         current
          DESCRIPTION
           "The VPI value of the VCL. MUST BE 0--255 in ADSL8416. "
          ::= { imaPVCEntry 3}

     imaVclVci           OBJECT-TYPE
          SYNTAX         AtmVcIdentifier
          MAX-ACCESS     read-write
          STATUS         current
          DESCRIPTION
           "The VCI value of the VCL. MUST BE 1--65535 in ADSL8416. "
          ::= { imaPVCEntry 4}

-- ZTE adsl product id(24)
zxAdslProductID OBJECT-TYPE
	SYNTAX        INTEGER{
			adsl8426(1),
			adsl8416(2)
	}
	MAX-ACCESS read-only
	STATUS current
	DESCRIPTION
		"The ID decribes ZTE ADSL product type "
          ::= { zxDslamAim 24 }

-- VLAN mode 3 flag(25)
isVlanInModeThree OBJECT-TYPE
	SYNTAX        INTEGER{
			no(1),
			yes(2)
	}
	MAX-ACCESS read-only
	STATUS current
	DESCRIPTION
		"to identify if vlan is in default vlan three mode"
          ::= { zxDslamAim 25 }

-- sub card type(26 27 28)
subCardOneType OBJECT-TYPE
	SYNTAX     ZTEdsl8426SubCardType   
	MAX-ACCESS read-only
	STATUS current
	DESCRIPTION
		"to identify the 1st sub card type"
          ::= { zxDslamAim 26 }

subCardTwoType OBJECT-TYPE
	SYNTAX     ZTEdsl8426SubCardType   
	MAX-ACCESS read-only
	STATUS current
	DESCRIPTION
		"to identify the 2nd sub card type"
          ::= { zxDslamAim 27 }

subCardThreeType OBJECT-TYPE
	SYNTAX     ZTEdsl8426SubCardType   
	MAX-ACCESS read-only
	STATUS current
	DESCRIPTION
		"to identify the 3rd sub card type"
          ::= { zxDslamAim 28 }
                                          
-- Part 2:TRAP
-- zxDslamTrap 
--zxDslamCardUp	NOTIFICATION-TYPE
--    OBJECTS   {  zxDslamCardOperStatus }
--    STATUS    current
--    DESCRIPTION 
--		"A cardUp trap signifies that the SNMP agent has detectd 
--		that the cardOperStatus object for the card has transitioned 
--		out of the down state.This trap indicates that some card has 
--		recovered from fault or been inserted into one switch slot"
--     ::= { zxDslamTrap 0 1 }

--zxDslamCardDown 	NOTIFICATION-TYPE
--    OBJECTS   { zxDslamCardOperStatus }
--    STATUS    current
--    DESCRIPTION	
--		"A cardDown trap signifies that the SNMP agent has deected that 
--		the cardOperStatus object for the card has transitioned into 
--		the down state. This trap indicates that some card has occured 
--		fault or been pulled out from one switch slot."
--     ::= { zxDslamTrap 0 2 }
     
zxDslamCommandTabStatusLastChange NOTIFICATION-TYPE
    OBJECTS   { zxDslamCommandStatus }
    STATUS    current
    DESCRIPTION	
		"This trap signifies that the SNMP agent has detected that 
		the zxDslamCommandStatus object for the command has been changed."
     ::= { zxDslamTrap 0 3 }

--zxDslamCoreStandbyStatusChange NOTIFICATION-TYPE
--    OBJECTS   { zxDslamCardstandbyStatus }
--    STATUS    current
--    DESCRIPTION	
--		"This trap signifies that the SNMP agent has detected that the	
--		zxDslamCardstandbyStatus object for the core card has been changed."
--     ::= { zxDslamTrap 0 4 }
     
--zxDslamFanOperStatusChange NOTIFICATION-TYPE
--    OBJECTS   { zxDslamFanOperStatus}
--    STATUS    current
--    DESCRIPTION	
--		"This trap signifies that the SNMP agent has detected that the	
--		zxDslamFanOperStatus object for the fan has been changed."
--     ::= { zxDslamTrap 0 5 }
     
--zxDslamPowerOperStatusChange NOTIFICATION-TYPE
--    OBJECTS   { zxDslamPowerOperStatus }
--    STATUS    current
--    DESCRIPTION	
--		"This trap signifies that the SNMP agent has detected that the	
--		zxDslamPowerOperStatus object for the power has been changed."
--     ::= { zxDslamTrap 0 6 }
     
     
END
ZX-QVLAN-MIB DEFINITIONS ::= BEGIN

IMPORTS
           MODULE-IDENTITY, OBJECT-TYPE, Unsigned32, Integer32, Counter32, Gauge32,
           NOTIFICATION-TYPE, enterprises
              FROM SNMPv2-SMI
           MODULE-COMPLIANCE, OBJECT-GROUP, NOTIFICATION-GROUP
              FROM SNMPv2-CONF
           TEXTUAL-CONVENTION, DateAndTime, MacAddress, RowStatus,TruthValue
              FROM SNMPv2-TC
           InterfaceIndex, InterfaceIndexOrZero, ifIndex
              FROM IF-MIB
    		SnmpAdminString
        	  FROM SNMP-FRAMEWORK-MIB;
              
zxQvlanMib MODULE-IDENTITY
           LAST-UPDATED "9902111830Z"
           ORGANIZATION "The ATM Forum"
           CONTACT-INFO
              "ATM Forum
              World Headquarters
              2570 West El Camino Real
              Suite 304
              Mountain View, CA 94040-1313
              USA
              Phone: +1 415 949 6700
              Fax: +1 415 949 6705
              email: info@ atmforum. com"
           DESCRIPTION
              "The MIB module for managing ATM Forum Inverse Multiplexing
              for ATM (IMA) interfaces."
           REVISION          "9902111830Z"
           DESCRIPTION
              "Updated and repaired version of the IMA-MIB released with the
              IMA v1.1 specification (af-phy-0086.001)."
           REVISION          "9701092245Z"
           DESCRIPTION
              "Initial incomplete version of the IMA-MIB as published in the
              IMA v1.0 specification (af-phy-0086.000)."
           ::= { zxAdsl 11 }

zte OBJECT IDENTIFIER ::= { enterprises 3902 }
zxAdsl OBJECT IDENTIFIER ::= { zte 1004 }

zxqBridgeMIBObjects OBJECT IDENTIFIER ::= { zxQvlanMib 1 }
-- -------------------------------------------------------------
-- Textual Conventions
-- -------------------------------------------------------------
-- li add the fellowing TC
EnabledStatus ::= TEXTUAL-CONVENTION
    STATUS      current
    DESCRIPTION
        "A simple status value for the object."
    SYNTAX      INTEGER {
	enabled(1), disabled(2) }

PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING

VlanIndex ::= TEXTUAL-CONVENTION
    STATUS      current
    DESCRIPTION
        "A value used to index per-VLAN tables: values of 0 and
        4095 are not permitted; if the value is between 1 and
        4094 inclusive, it represents an IEEE 802.1Q VLAN-ID with
        global scope within a given bridged domain (see VlanId
        textual convention).  If the value is greater than 4095
        then it represents a VLAN with scope local to the
        particular agent, i.e. one without a global VLAN-ID
        assigned to it. Such VLANs are outside the scope of
        IEEE 802.1Q but it is convenient to be able to manage them
        in the same way using this MIB."
    SYNTAX      Unsigned32
 
VlanId ::= TEXTUAL-CONVENTION
    STATUS      current
    DESCRIPTION
        "A 12-bit VLAN ID used in the VLAN Tag header."
    SYNTAX      INTEGER (1..4096)

-- -------------------------------------------------------------
-- groups in the Q-BRIDGE MIB
-- -------------------------------------------------------------
 
dot1qBase       OBJECT IDENTIFIER ::= { zxqBridgeMIBObjects 1 }
-- li dot1qTp         OBJECT IDENTIFIER ::= { qBridgeMIBObjects 2 }
-- li dot1qStatic     OBJECT IDENTIFIER ::= { qBridgeMIBObjects 3 }
dot1qVlan       OBJECT IDENTIFIER ::= { zxqBridgeMIBObjects 4 }
 
-- -------------------------------------------------------------
--  
-- -------------------------------------------------------------
-- dot1qBase group
-- -------------------------------------------------------------

dot1qVlanVersionNumber OBJECT-TYPE
    SYNTAX      INTEGER {
                    version1(1)
                }
    MAX-ACCESS  read-only
    STATUS      current
    DESCRIPTION
        "The version number of IEEE 802.1Q that this device
        supports."
    REFERENCE
        "IEEE 802.1Q/D11 Section 12.10.1.1"
    ::= { dot1qBase 1 }

dot1qMaxVlanId OBJECT-TYPE
    SYNTAX      VlanId
    MAX-ACCESS  read-only
    STATUS      current
    DESCRIPTION
        "The maximum IEEE 802.1Q VLAN ID that this device
        supports."
    REFERENCE
        "IEEE 802.1Q/D11 Section 9.3.2.3"
    ::= { dot1qBase 2 }

dot1qMaxSupportedVlans OBJECT-TYPE
    SYNTAX      Unsigned32
    MAX-ACCESS  read-only
    STATUS      current
    DESCRIPTION
        "The maximum number of IEEE 802.1Q VLANs that this
        device supports."
    REFERENCE
        "IEEE 802.1Q/D11 Section 12.10.1.1"
    ::= { dot1qBase 3 }

dot1qNumVlans OBJECT-TYPE
    SYNTAX      Unsigned32
    MAX-ACCESS  read-only
    STATUS      current
    DESCRIPTION
        "The current number of IEEE 802.1Q VLANs that are
        configured in this device."
    REFERENCE
        "IEEE 802.1Q/D11 Section 12.7.1.1"
    ::= { dot1qBase 4 }

-- li dot1qGvrpStatus OBJECT-TYPE
-- li     SYNTAX      EnabledStatus
-- li     MAX-ACCESS  read-write
-- li     STATUS      current
-- li     DESCRIPTION
-- li         "The administrative status requested by management for
-- li         GVRP.  The value enabled(1) indicates that GVRP should
-- li         be enabled on this device, on all ports for which it has
-- li         not been specifically disabled.  When disabled(2), GVRP
-- li         is disabled on all ports and all GVRP packets will be
-- li         forwarded transparently.  This object affects all GVRP
-- li         Applicant and Registrar state machines.  A transition
-- li         from disabled(2) to enabled(1) will cause a reset of all
-- li         GVRP state machines on all ports."
-- li     DEFVAL      { enabled }
-- li     ::= { dot1qBase 5 }
-- li 
-- -------------------------------------------------------------
-- the dot1qTp group
-- -------------------------------------------------------------
-- li 
-- -------------------------------------------------------------
-- the current Filtering Database Table
-- -------------------------------------------------------------
-- li 
-- li dot1qFdbTable OBJECT-TYPE
-- li     SYNTAX      SEQUENCE OF Dot1qFdbEntry
-- li     MAX-ACCESS  not-accessible
-- li     STATUS      current
-- li     DESCRIPTION
-- li         "A table that contains configuration and control
-- li         information for each Filtering Database currently
-- li         operating on this device.  Entries in this table appear
-- li         automatically when VLANs are assigned FDB IDs in the
-- li         dot1qVlanCurrentTable."
-- li     ::= { dot1qTp 1 }
-- li 
-- li dot1qFdbEntry OBJECT-TYPE
-- li     SYNTAX      Dot1qFdbEntry
-- li     MAX-ACCESS  not-accessible
-- li     STATUS      current
-- li     DESCRIPTION
-- li         "Information about a specific Filtering Database."
-- li     INDEX   { dot1qFdbId }
-- li     ::= { dot1qFdbTable 1 }
-- li 
-- li Dot1qFdbEntry ::=
-- li     SEQUENCE {
-- li         dot1qFdbId
-- li             Unsigned32,
-- li         dot1qFdbDynamicCount
-- li             Counter32
-- li     }
-- li 
-- li dot1qFdbId OBJECT-TYPE
-- li     SYNTAX       Unsigned32
-- li     MAX-ACCESS   not-accessible
-- li     STATUS       current
-- li     DESCRIPTION
-- li         "The identity of this Filtering Database."
-- li     ::= { dot1qFdbEntry 1 }
-- li 
-- li dot1qFdbDynamicCount OBJECT-TYPE
-- li     SYNTAX       Counter32
-- li     MAX-ACCESS   read-only
-- li     STATUS       current
-- li     DESCRIPTION
-- li         "The current number of dynamic entries in this
-- li         Filtering Database."
-- li     REFERENCE
-- li         "IEEE 802.1Q/D11 Section 12.7.1.1.3"
-- li     ::= { dot1qFdbEntry 2 }
-- li 
-- -------------------------------------------------------------
-- Multiple Forwarding Databases for 802.1Q Transparent devices
-- This table is an alternative to the dot1dTpFdbTable,
-- previously defined for 802.1D devices which only support a
-- single Forwarding Database.
-- -------------------------------------------------------------
-- li 
-- li dot1qTpFdbTable OBJECT-TYPE
-- li     SYNTAX      SEQUENCE OF Dot1qTpFdbEntry
-- li     MAX-ACCESS  not-accessible
-- li     STATUS      current
-- li     DESCRIPTION
-- li         "A table that contains information about unicast entries
-- li         for which the device has forwarding and/or filtering
-- li         information.  This information is used by the
-- li         transparent bridging function in determining how to
-- li         propagate a received frame."
-- li     REFERENCE
-- li         "IEEE 802.1Q/D11 Section 12.7.7"
-- li     ::= { dot1qTp 2 }
-- li 
-- li dot1qTpFdbEntry OBJECT-TYPE
-- li     SYNTAX      Dot1qTpFdbEntry
-- li     MAX-ACCESS  not-accessible
-- li     STATUS      current
-- li     DESCRIPTION
-- li         "Information about a specific unicast MAC address for
-- li         which the device has some forwarding and/or filtering
-- li         information."
-- li     INDEX   { dot1qFdbId, dot1qTpFdbAddress }
-- li     ::= { dot1qTpFdbTable 1 }
-- li 
-- li Dot1qTpFdbEntry ::=
-- li     SEQUENCE {
-- li         dot1qTpFdbAddress
-- li             MacAddress,
-- li         dot1qTpFdbPort
-- li             INTEGER,
-- li         dot1qTpFdbStatus
-- li             INTEGER
-- li     }
-- li 
-- li dot1qTpFdbAddress OBJECT-TYPE
-- li     SYNTAX      MacAddress
-- li     MAX-ACCESS  not-accessible
-- li     STATUS      current
-- li 
-- li     DESCRIPTION
-- li         "A unicast MAC address for which the device has
-- li         forwarding and/or filtering information."
-- li     ::= { dot1qTpFdbEntry 1 }
-- li 
-- li dot1qTpFdbPort OBJECT-TYPE
-- li     SYNTAX      INTEGER (0..65535)
-- li     MAX-ACCESS  read-only
-- li     STATUS      current
-- li     DESCRIPTION
-- li         "Either the value '0', or the port number of the port on
-- li         which a frame having a source address equal to the value
-- li         of the corresponding instance of dot1qTpFdbAddress has
-- li         been seen.  A value of '0' indicates that the port
-- li         number has not been learned but that the device does
-- li         have some forwarding/filtering information about this
-- li         address (e.g. in the dot1qStaticUnicastTable).
-- li         Implementors are encouraged to assign the port value to
-- li         this object whenever it is learned even for addresses
-- li         for which the corresponding value of dot1qTpFdbStatus is
-- li         not learned(3)."
-- li     ::= { dot1qTpFdbEntry 2 }
-- li 
-- li dot1qTpFdbStatus OBJECT-TYPE
-- li     SYNTAX      INTEGER {
-- li                     other(1),
-- li                     invalid(2),
-- li                     learned(3),
-- li                     self(4),
-- li                     mgmt(5)
-- li                 }
-- li     MAX-ACCESS  read-only
-- li     STATUS      current
-- li     DESCRIPTION
-- li         "The status of this entry.  The meanings of the values
-- li         are:
-- li             other(1) - none of the following.  This may include
-- li                 the case where some other MIB object (not the
-- li                 corresponding instance of dot1qTpFdbPort, nor an
-- li                 entry in the dot1qStaticUnicastTable) is being
-- li                 used to determine if and how frames addressed to
-- li                 the value of the corresponding instance of
-- li                 dot1qTpFdbAddress are being forwarded.
-- li             invalid(2) - this entry is no longer valid (e.g., it
-- li                 was learned but has since aged out), but has not
-- li                 yet been flushed from the table.
-- li             learned(3) - the value of the corresponding instance
-- li                 of dot1qTpFdbPort was learned and is being used.
-- li 
-- li             self(4) - the value of the corresponding instance of
-- li                 dot1qTpFdbAddress represents one of the device's
-- li                 addresses.  The corresponding instance of
-- li                 dot1qTpFdbPort indicates which of the device's
-- li                 ports has this address.
-- li             mgmt(5) - the value of the corresponding instance of
-- li                 dot1qTpFdbAddress is also the value of an
-- li                 existing instance of dot1qStaticAddress."
-- li     ::= { dot1qTpFdbEntry 3 }
-- li 
-- -------------------------------------------------------------
-- Dynamic Group Registration Table
-- -------------------------------------------------------------
-- li 
-- li dot1qTpGroupTable OBJECT-TYPE
-- li     SYNTAX      SEQUENCE OF Dot1qTpGroupEntry
-- li     MAX-ACCESS  not-accessible
-- li     STATUS      current
-- li     DESCRIPTION
-- li         "A table containing filtering information for VLANs
-- li         configured into the bridge by (local or network)
-- li         management, or learnt dynamically, specifying the set of
-- li         ports to which frames received on a VLAN for this FDB
-- li         and containing a specific Group destination address are
-- li         allowed to be forwarded."
-- li     ::= { dot1qTp 3 }
-- li 
-- li dot1qTpGroupEntry OBJECT-TYPE
-- li     SYNTAX      Dot1qTpGroupEntry
-- li     MAX-ACCESS  not-accessible
-- li     STATUS      current
-- li     DESCRIPTION
-- li         "Filtering information configured into the bridge by
-- li         management, or learnt dynamically, specifying the set of
-- li         ports to which frames received on a VLAN and containing
-- li         a specific Group destination address, are allowed to be
-- li         forwarded.  The subset of these ports learnt dynamically
-- li         is also provided."
-- li     INDEX   { dot1qVlanIndex, dot1qTpGroupAddress }
-- li     ::= { dot1qTpGroupTable 1 }
-- li 
-- li Dot1qTpGroupEntry ::=
-- li     SEQUENCE {
-- li         dot1qTpGroupAddress
-- li             MacAddress,
-- li         dot1qTpGroupEgressPorts
-- li             PortList,
-- li         dot1qTpGroupLearnt
-- li 
-- li             PortList
-- li     }
-- li 
-- li dot1qTpGroupAddress OBJECT-TYPE
-- li     SYNTAX      MacAddress
-- li     MAX-ACCESS  not-accessible
-- li     STATUS      current
-- li     DESCRIPTION
-- li         "The destination Group MAC address in a frame to which
-- li         this entry's filtering information applies."
-- li     ::= { dot1qTpGroupEntry 1 }
-- li 
-- li dot1qTpGroupEgressPorts OBJECT-TYPE
-- li     SYNTAX      PortList
-- li     MAX-ACCESS  read-only
-- li     STATUS      current
-- li     DESCRIPTION
-- li         "The complete set of ports, in this VLAN, to which
-- li         frames destined for this Group MAC address are currently
-- li         being explicitly forwarded.  This does not include ports
-- li         for which this address is only implicitly forwarded, in
-- li         the dot1qForwardAllPorts list."
-- li     ::= { dot1qTpGroupEntry 2 }
-- li 
-- li dot1qTpGroupLearnt OBJECT-TYPE
-- li     SYNTAX      PortList
-- li     MAX-ACCESS  read-only
-- li     STATUS      current
-- li     DESCRIPTION
-- li         "The subset of ports in dot1qTpGroupEgressPorts which
-- li         were learnt by GMRP or some other dynamic mechanism, in
-- li         this Filtering database."
-- li     ::= { dot1qTpGroupEntry 3 }
-- li 
-- -------------------------------------------------------------
-- Service Requirements Group
-- -------------------------------------------------------------
-- li 
-- li dot1qForwardAllTable OBJECT-TYPE
-- li     SYNTAX      SEQUENCE OF Dot1qForwardAllEntry
-- li     MAX-ACCESS  not-accessible
-- li     STATUS      current
-- li     DESCRIPTION
-- li         "A table containing forwarding information for each
-- li         VLAN, specifying the set of ports to which forwarding of
-- li         all multicasts applies, configured statically by
-- li         management or dynamically by GMRP.  An entry appears in
-- li         this table for all VLANs that are currently
-- li 
-- li         instantiated."
-- li     REFERENCE
-- li         "IEEE 802.1Q/D11 Section 12.7.2, 12.7.7"
-- li     ::= { dot1qTp 4 }
-- li 
-- li dot1qForwardAllEntry OBJECT-TYPE
-- li     SYNTAX      Dot1qForwardAllEntry
-- li     MAX-ACCESS  not-accessible
-- li     STATUS      current
-- li     DESCRIPTION
-- li         "Forwarding information for a VLAN, specifying the set
-- li         of ports to which all multicasts should be forwarded,
-- li         configured statically by management or dynamically by
-- li         GMRP."
-- li     INDEX   { dot1qVlanIndex }
-- li     ::= { dot1qForwardAllTable 1 }
-- li 
-- li Dot1qForwardAllEntry ::=
-- li     SEQUENCE {
-- li         dot1qForwardAllPorts
-- li             PortList,
-- li         dot1qForwardAllStaticPorts
-- li             PortList,
-- li         dot1qForwardAllForbiddenPorts
-- li             PortList
-- li     }
-- li 
-- li dot1qForwardAllPorts OBJECT-TYPE
-- li     SYNTAX      PortList
-- li     MAX-ACCESS  read-only
-- li     STATUS      current
-- li     DESCRIPTION
-- li         "The complete set of ports in this VLAN to which all
-- li         multicast group-addressed frames are to be forwarded.
-- li         This includes ports for which this need has been
-- li         determined dynamically by GMRP, or configured statically
-- li         by management."
-- li     ::= { dot1qForwardAllEntry 1 }
-- li 
-- li dot1qForwardAllStaticPorts OBJECT-TYPE
-- li     SYNTAX      PortList
-- li     MAX-ACCESS  read-write
-- li     STATUS      current
-- li 
-- li     DESCRIPTION
-- li         "The set of ports configured by management in this VLAN
-- li         to which all multicast group-addressed frames are to be
-- li         forwarded.  Ports entered in this list will also appear
-- li         in the complete set shown by dot1qForwardAllPorts.  This
-- li         value will be restored after the device is reset.  This
-- li         only applies to ports that are members of the VLAN,
-- li         defined by dot1qVlanCurrentEgressPorts.  A port may not
-- li         be added in this set if it is already a member of the
-- li         set of ports in dot1qForwardAllForbiddenPorts.  The
-- li         default value is a string of ones of appropriate length,
-- li         to indicate standard non-EFS behaviour, i.e.  forward
-- li         all multicasts to all ports."
-- li     ::= { dot1qForwardAllEntry 2 }
-- li 
-- li dot1qForwardAllForbiddenPorts OBJECT-TYPE
-- li     SYNTAX      PortList
-- li     MAX-ACCESS  read-write
-- li     STATUS      current
-- li     DESCRIPTION
-- li         "The set of ports configured by management in this VLAN
-- li         for which the Service Requirement attribute Forward All
-- li         Multicast Groups may not be dynamically registered by
-- li         GMRP.  This value will be restored after the device is
-- li         reset.  A port may not be added in this set if it is
-- li         already a member of the set of ports in
-- li         dot1qForwardAllStaticPorts.  The default value is a
-- li         string of zeros of appropriate length."
-- li     ::= { dot1qForwardAllEntry 3 }
-- li 
-- li dot1qForwardUnregisteredTable OBJECT-TYPE
-- li     SYNTAX      SEQUENCE OF Dot1qForwardUnregisteredEntry
-- li     MAX-ACCESS  not-accessible
-- li     STATUS      current
-- li     DESCRIPTION
-- li         "A table containing forwarding information for each
-- li         VLAN, specifying the set of ports to which forwarding of
-- li         multicast group-addressed frames for which there is no
-- li         more specific forwarding information applies.  This is
-- li         configured statically by management and determined
-- li         dynamically by GMRP.  An entry appears in this table for
-- li         all VLANs that are currently instantiated."
-- li     REFERENCE
-- li         "IEEE 802.1Q/D11 Section 12.7.2, 12.7.7"
-- li     ::= { dot1qTp 5 }
-- li 
-- li dot1qForwardUnregisteredEntry OBJECT-TYPE
-- li     SYNTAX      Dot1qForwardUnregisteredEntry
-- li 
-- li     MAX-ACCESS  not-accessible
-- li     STATUS      current
-- li     DESCRIPTION
-- li         "Forwarding information for a VLAN, specifying the set
-- li         of ports to which all multicasts for which there is no
-- li         more specific forwarding information shall be forwarded.
-- li         This is configured statically by management or
-- li         dynamically by GMRP."
-- li     INDEX   { dot1qVlanIndex }
-- li     ::= { dot1qForwardUnregisteredTable 1 }
-- li 
-- li Dot1qForwardUnregisteredEntry ::=
-- li     SEQUENCE {
-- li         dot1qForwardUnregisteredPorts
-- li             PortList,
-- li         dot1qForwardUnregisteredStaticPorts
-- li             PortList,
-- li         dot1qForwardUnregisteredForbiddenPorts
-- li             PortList
-- li     }
-- li 
-- li dot1qForwardUnregisteredPorts OBJECT-TYPE
-- li     SYNTAX      PortList
-- li     MAX-ACCESS  read-only
-- li     STATUS      current
-- li     DESCRIPTION
-- li         "The complete set of ports in this VLAN to which
-- li         multicast group-addressed frames for which there is no
-- li         more specific forwarding information will be forwarded.
-- li         This includes ports for which this need has been
-- li         determined dynamically by GMRP, or configured statically
-- li         by management."
-- li     ::= { dot1qForwardUnregisteredEntry 1 }
-- li 
-- li dot1qForwardUnregisteredStaticPorts OBJECT-TYPE
-- li     SYNTAX      PortList
-- li     MAX-ACCESS  read-write
-- li     STATUS      current
-- li     DESCRIPTION
-- li         "The set of ports configured by management, in this
-- li         VLAN, to which multicast group-addressed frames for
-- li         which there is no more specific forwarding information
-- li         are to be forwarded.  Ports entered in this list will
-- li         also appear in the complete set shown by
-- li         dot1qForwardUnregisteredPorts.  This value will be
-- li         restored after the device is reset.  A port may not be
-- li         added in this set if it is already a member of the set
-- li         of ports in dot1qForwardUnregisteredForbiddenPorts.  The
-- li 
-- li         default value is a string of zeros of appropriate
-- li         length, although this has no effect with the default
-- li         value of dot1qForwardAllStaticPorts."
-- li     ::= { dot1qForwardUnregisteredEntry 2 }
-- li 
-- li dot1qForwardUnregisteredForbiddenPorts OBJECT-TYPE
-- li     SYNTAX      PortList
-- li     MAX-ACCESS  read-write
-- li     STATUS      current
-- li     DESCRIPTION
-- li         "The set of ports configured by management in this VLAN
-- li         for which the Service Requirement attribute Forward
-- li         Unregistered Multicast Groups may not be dynamically
-- li         registered by GMRP.  This value will be restored after
-- li         the device is reset.  A port may not be added in this
-- li         set if it is already a member of the set of ports in
-- li         dot1qForwardUnregisteredStaticPorts.  The default value
-- li         is a string of zeros of appropriate length."
-- li     ::= { dot1qForwardUnregisteredEntry 3 }
-- li 
-- -------------------------------------------------------------
-- The Static (Destination-Address Filtering) Database
-- -------------------------------------------------------------
-- li 
-- li dot1qStaticUnicastTable OBJECT-TYPE
-- li     SYNTAX      SEQUENCE OF Dot1qStaticUnicastEntry
-- li     MAX-ACCESS  not-accessible
-- li     STATUS      current
-- li     DESCRIPTION
-- li         "A table containing filtering information for Unicast
-- li         MAC addresses for each Filtering Database, configured
-- li         into the device by (local or network) management
-- li         specifying the set of ports to which frames received
-- li         from specific ports and containing specific unicast
-- li         destination addresses are allowed to be forwarded.  A
-- li         value of zero in this table as the port number from
-- li         which frames with a specific destination address are
-- li         received, is used to specify all ports for which there
-- li         is no specific entry in this table for that particular
-- li         destination address.  Entries are valid for unicast
-- li         addresses only."
-- li     REFERENCE
-- li         "IEEE 802.1Q/D11 Section 12.7.7,
-- li         ISO/IEC 15802-3 Section 7.9.1"
-- li     ::= { dot1qStatic 1 }
-- li 
-- li dot1qStaticUnicastEntry OBJECT-TYPE
-- li     SYNTAX      Dot1qStaticUnicastEntry
-- li     MAX-ACCESS  not-accessible
-- li     STATUS      current
-- li     DESCRIPTION
-- li         "Filtering information configured into the device by
-- li         (local or network) management specifying the set of
-- li         ports to which frames received from a specific port and
-- li         containing a specific unicast destination address are
-- li         allowed to be forwarded."
-- li     INDEX   {
-- li         dot1qFdbId,
-- li         dot1qStaticUnicastAddress,
-- li         dot1qStaticUnicastReceivePort
-- li     }
-- li     ::= { dot1qStaticUnicastTable 1 }
-- li 
-- li Dot1qStaticUnicastEntry ::=
-- li     SEQUENCE {
-- li         dot1qStaticUnicastAddress
-- li             MacAddress,
-- li         dot1qStaticUnicastReceivePort
-- li             INTEGER,
-- li         dot1qStaticUnicastAllowedToGoTo
-- li             PortList,
-- li         dot1qStaticUnicastStatus
-- li             INTEGER
-- li     }
-- li 
-- li dot1qStaticUnicastAddress OBJECT-TYPE
-- li     SYNTAX      MacAddress
-- li     MAX-ACCESS  not-accessible
-- li     STATUS      current
-- li     DESCRIPTION
-- li         "The destination MAC address in a frame to which this
-- li         entry's filtering information applies.  This object must
-- li         take the value of a unicast address."
-- li     ::= { dot1qStaticUnicastEntry 1 }
-- li 
-- li dot1qStaticUnicastReceivePort OBJECT-TYPE
-- li     SYNTAX      INTEGER (0..65535)
-- li     MAX-ACCESS  not-accessible
-- li     STATUS      current
-- li     DESCRIPTION
-- li         "Either the value '0', or the port number of the port
-- li         from which a frame must be received in order for this
-- li         entry's filtering information to apply.  A value of zero
-- li         indicates that this entry applies on all ports of the
-- li 
-- li         device for which there is no other applicable entry."
-- li     ::= { dot1qStaticUnicastEntry 2 }
-- li 
-- li dot1qStaticUnicastAllowedToGoTo OBJECT-TYPE
-- li     SYNTAX      PortList
-- li     MAX-ACCESS  read-write
-- li     STATUS      current
-- li     DESCRIPTION
-- li         "The set of ports for which a frame with a specific
-- li         unicast address will be flooded in the event that it
-- li         has not been learned.  It also specifies the set of
-- li         ports a specific unicast address may be dynamically
-- li         learnt on.  The dot1qTpFdbTable will have an equivalent
-- li         entry with a dot1qTpFdbPort value of '0' until this
-- li         address has been learnt, when it will be updated with
-- li         the port the address has been seen on.  This only
-- li         applies to ports that are members of the VLAN, defined
-- li         by dot1qVlanCurrentEgressPorts.  The default value of
-- li         this object is a string of ones of appropriate length."
-- li     REFERENCE
-- li         "IEEE 802.1Q/D11 Table 8-5, ISO/IEC 15802-3 Table 7-5"
-- li     ::= { dot1qStaticUnicastEntry 3 }
-- li 
-- li dot1qStaticUnicastStatus OBJECT-TYPE
-- li     SYNTAX      INTEGER {
-- li                     other(1),
-- li                     invalid(2),
-- li                     permanent(3),
-- li                     deleteOnReset(4),
-- li                     deleteOnTimeout(5)
-- li                 }
-- li     MAX-ACCESS  read-write
-- li     STATUS      current
-- li     DESCRIPTION
-- li         "This object indicates the status of this entry.
-- li             other(1) - this entry is currently in use but
-- li                 the conditions under which it will remain
-- li                 so differ from the following values.
-- li             invalid(2) - writing this value to the object
-- li                 removes the corresponding entry.
-- li             permanent(3) - this entry is currently in use
-- li                 and will remain so after the next reset of
-- li                 the bridge.
-- li             deleteOnReset(4) - this entry is currently in
-- li                 use and will remain so until the next
-- li                 reset of the bridge.
-- li 
-- li             deleteOnTimeout(5) - this entry is currently in
-- li                 use and will remain so until it is aged out."
-- li     DEFVAL      { permanent }
-- li     ::= { dot1qStaticUnicastEntry 4 }
-- li 
-- li dot1qStaticMulticastTable OBJECT-TYPE
-- li     SYNTAX      SEQUENCE OF Dot1qStaticMulticastEntry
-- li     MAX-ACCESS  not-accessible
-- li     STATUS      current
-- li     DESCRIPTION
-- li         "A table containing filtering information for Multicast
-- li         and Broadcast MAC addresses for each VLAN, configured
-- li         into the device by (local or network) management
-- li         specifying the set of ports to which frames received
-- li         from specific ports and containing specific Multicast
-- li         and Broadcast destination addresses are allowed to be
-- li         forwarded.  A value of zero in this table as the port
-- li         number from which frames with a specific destination
-- li         address are received, is used to specify all ports for
-- li         which there is no specific entry in this table for that
-- li         particular destination address.  Entries are valid for
-- li         Multicast and Broadcast addresses only."
-- li     REFERENCE
-- li         "IEEE 802.1Q/D11 Section 12.7.7,
-- li         ISO/IEC 15802-3 Section 7.9.1"
-- li     ::= { dot1qStatic 2 }
-- li 
-- li dot1qStaticMulticastEntry OBJECT-TYPE
-- li     SYNTAX      Dot1qStaticMulticastEntry
-- li     MAX-ACCESS  not-accessible
-- li     STATUS      current
-- li     DESCRIPTION
-- li         "Filtering information configured into the device by
-- li         (local or network) management specifying the set of
-- li         ports to which frames received from this specific port
-- li         for this VLAN and containing this Multicast or Broadcast
-- li         destination address are allowed to be forwarded."
-- li     INDEX   {
-- li         dot1qVlanIndex,
-- li         dot1qStaticMulticastAddress,
-- li         dot1qStaticMulticastReceivePort
-- li     }
-- li     ::= { dot1qStaticMulticastTable 1 }
-- li 
-- li Dot1qStaticMulticastEntry ::=
-- li     SEQUENCE {
-- li         dot1qStaticMulticastAddress
-- li             MacAddress,
-- li         dot1qStaticMulticastReceivePort
-- li             INTEGER,
-- li         dot1qStaticMulticastStaticEgressPorts
-- li             PortList,
-- li         dot1qStaticMulticastForbiddenEgressPorts
-- li             PortList,
-- li         dot1qStaticMulticastStatus
-- li             INTEGER
-- li     }
-- li 
-- li dot1qStaticMulticastAddress OBJECT-TYPE
-- li     SYNTAX      MacAddress
-- li     MAX-ACCESS  not-accessible
-- li     STATUS      current
-- li     DESCRIPTION
-- li         "The destination MAC address in a frame to which this
-- li         entry's filtering information applies.  This object must
-- li         take the value of a Multicast or Broadcast address."
-- li     ::= { dot1qStaticMulticastEntry 1 }
-- li 
-- li dot1qStaticMulticastReceivePort OBJECT-TYPE
-- li     SYNTAX      INTEGER (0..65535)
-- li     MAX-ACCESS  not-accessible
-- li     STATUS      current
-- li     DESCRIPTION
-- li         "Either the value '0', or the port number of the port
-- li         from which a frame must be received in order for this
-- li         entry's filtering information to apply.  A value of zero
-- li         indicates that this entry applies on all ports of the
-- li         device for which there is no other applicable entry."
-- li     ::= { dot1qStaticMulticastEntry 2 }
-- li 
-- li dot1qStaticMulticastStaticEgressPorts OBJECT-TYPE
-- li     SYNTAX      PortList
-- li     MAX-ACCESS  read-write
-- li     STATUS      current
-- li 
-- li     DESCRIPTION
-- li         "The set of ports to which frames received from a
-- li         specific port and destined for a specific Multicast or
-- li         Broadcast MAC address must be forwarded, regardless of
-- li         any dynamic information e.g. from GMRP.  A port may not
-- li         be added in this set if it is already a member of the
-- li         set of ports in dot1qStaticMulticastForbiddenEgressPorts.
-- li         The default value of this object is a string of ones of
-- li         appropriate length."
-- li     ::= { dot1qStaticMulticastEntry 3 }
-- li 
-- li dot1qStaticMulticastForbiddenEgressPorts OBJECT-TYPE
-- li     SYNTAX      PortList
-- li     MAX-ACCESS  read-write
-- li     STATUS      current
-- li     DESCRIPTION
-- li         "The set of ports to which frames received from a
-- li         specific port and destined for a specific Multicast or
-- li         Broadcast MAC address must not be forwarded, regardless
-- li         of any dynamic information e.g. from GMRP.  A port may
-- li         not be added in this set if it is already a member of the
-- li         set of ports in dot1qStaticMulticastStaticEgressPorts.
-- li         The default value of this object is a string of zeros of
-- li         appropriate length."
-- li     ::= { dot1qStaticMulticastEntry 4 }
-- li 
-- li dot1qStaticMulticastStatus OBJECT-TYPE
-- li     SYNTAX      INTEGER {
-- li                     other(1),
-- li                     invalid(2),
-- li                     permanent(3),
-- li                     deleteOnReset(4),
-- li                     deleteOnTimeout(5)
-- li                 }
-- li     MAX-ACCESS  read-write
-- li     STATUS      current
-- li     DESCRIPTION
-- li         "This object indicates the status of this entry.
-- li             other(1) - this entry is currently in use but
-- li                 the conditions under which it will remain
-- li                 so differ from the following values.
-- li             invalid(2) - writing this value to the object
-- li                 removes the corresponding entry.
-- li             permanent(3) - this entry is currently in use
-- li                 and will remain so after the next reset of
-- li                 the bridge.
-- li 
-- li             deleteOnReset(4) - this entry is currently in
-- li                 use and will remain so until the next
-- li                 reset of the bridge.
-- li             deleteOnTimeout(5) - this entry is currently in
-- li                 use and will remain so until it is aged out."
-- li     DEFVAL      { permanent }
-- li     ::= { dot1qStaticMulticastEntry 5 }
-- li 
-- -------------------------------------------------------------
-- The Current VLAN Database
-- -------------------------------------------------------------
-- li 
-- li dot1qVlanNumDeletes OBJECT-TYPE
-- li     SYNTAX     Counter32
-- li     MAX-ACCESS read-only
-- li     STATUS     current
-- li     DESCRIPTION
-- li         "The number of times a VLAN entry has been deleted from
-- li         the dot1qVlanCurrentTable (for any reason).  If an entry
-- li         is deleted, then inserted, and then deleted, this
-- li         counter will be incremented by 2."
-- li     ::= { dot1qVlan 1 }
-- li 
-- li dot1qVlanCurrentTable OBJECT-TYPE
-- li     SYNTAX      SEQUENCE OF Dot1qVlanCurrentEntry
-- li     MAX-ACCESS  not-accessible
-- li     STATUS      current
-- li     DESCRIPTION
-- li         "A table containing current configuration information
-- li         for each VLAN currently configured into the device by
-- li         (local or network) management, or dynamically created
-- li         as a result of GVRP requests received."
-- li     ::= { dot1qVlan 2 }
-- li 
-- li dot1qVlanCurrentEntry OBJECT-TYPE
-- li     SYNTAX      Dot1qVlanCurrentEntry
-- li     MAX-ACCESS  not-accessible
-- li     STATUS      current
-- li     DESCRIPTION
-- li         "Information for a VLAN configured into the device by
-- li         (local or network) management, or dynamically created
-- li         as a result of GVRP requests received."
-- li     INDEX   { dot1qVlanTimeMark, dot1qVlanIndex }
-- li     ::= { dot1qVlanCurrentTable 1 }
-- li 
-- li Dot1qVlanCurrentEntry ::=
-- li     SEQUENCE {
-- li         dot1qVlanTimeMark
-- li             TimeFilter,
-- li         dot1qVlanIndex
-- li             VlanIndex,
-- li         dot1qVlanFdbId
-- li             Unsigned32,
-- li         dot1qVlanCurrentEgressPorts
-- li             PortList,
-- li         dot1qVlanCurrentUntaggedPorts
-- li             PortList,
-- li         dot1qVlanStatus
-- li             INTEGER,
-- li         dot1qVlanCreationTime
-- li             TimeTicks
-- li     }
-- li 
-- li dot1qVlanTimeMark OBJECT-TYPE
-- li     SYNTAX      TimeFilter
-- li     MAX-ACCESS  not-accessible
-- li     STATUS      current
-- li     DESCRIPTION
-- li         "A TimeFilter for this entry.  See the TimeFilter
-- li         textual convention to see how this works."
-- li     ::= { dot1qVlanCurrentEntry 1 }
-- li 
-- li dot1qVlanIndex OBJECT-TYPE
-- li     SYNTAX      VlanIndex
-- li     MAX-ACCESS  not-accessible
-- li     STATUS      current
-- li     DESCRIPTION
-- li         "The VLAN-ID or other identifier refering to this VLAN."
-- li     ::= { dot1qVlanCurrentEntry 2 }
-- li 
-- li dot1qVlanFdbId OBJECT-TYPE
-- li     SYNTAX      Unsigned32
-- li     MAX-ACCESS  read-only
-- li     STATUS      current
-- li     DESCRIPTION
-- li         "The Filtering Database used by this VLAN.  This is one
-- li         of the dot1qFdbId values in the dot1qFdbTable.  This
-- li         value is allocated automatically by the device whenever
-- li         the VLAN is created: either dynamically by GVRP, or by
-- li 
-- li         management, in dot1qVlanStaticTable.  Allocation of this
-- li         value follows the learning constraints defined for this
-- li         VLAN in dot1qLearningConstraintsTable."
-- li     ::= { dot1qVlanCurrentEntry 3 }
-- li 
-- li dot1qVlanCurrentEgressPorts OBJECT-TYPE
-- li     SYNTAX      PortList
-- li     MAX-ACCESS  read-only
-- li     STATUS      current
-- li     DESCRIPTION
-- li         "The set of ports which are transmitting traffic for
-- li         this VLAN as either tagged or untagged frames."
-- li     REFERENCE
-- li         "IEEE 802.1Q/D11 Section 12.10.2.1"
-- li     ::= { dot1qVlanCurrentEntry 4 }
-- li 
-- li dot1qVlanCurrentUntaggedPorts OBJECT-TYPE
-- li     SYNTAX      PortList
-- li     MAX-ACCESS  read-only
-- li     STATUS      current
-- li     DESCRIPTION
-- li         "The set of ports which are transmitting traffic for
-- li         this VLAN as untagged frames."
-- li     REFERENCE
-- li         "IEEE 802.1Q/D11 Section 12.10.2.1"
-- li     ::= { dot1qVlanCurrentEntry 5 }
-- li 
-- li dot1qVlanStatus OBJECT-TYPE
-- li     SYNTAX      INTEGER {
-- li                     other(1),
-- li                     permanent(2),
-- li                     dynamicGvrp(3)
-- li                 }
-- li     MAX-ACCESS  read-only
-- li     STATUS      current
-- li     DESCRIPTION
-- li         "This object indicates the status of this entry.
-- li             other(1) - this entry is currently in use but the
-- li                 conditions under which it will remain so differ
-- li                 from the following values.
-- li             permanent(2) - this entry, corresponding to an entry
-- li                 in dot1qVlanStaticTable, is currently in use and
-- li                 will remain so after the next reset of the
-- li                 device.  The port lists for this entry include
-- li                 ports from the equivalent dot1qVlanStaticTable
-- li                 entry and ports learnt dynamically.
-- li             dynamicGvrp(3) - this entry is currently in use
-- li 
-- li                 and will remain so until removed by GVRP.  There
-- li                 is no static entry for this VLAN and it will be
-- li                 removed when the last port leaves the VLAN."
-- li     ::= { dot1qVlanCurrentEntry 6 }
-- li 
-- li dot1qVlanCreationTime OBJECT-TYPE
-- li     SYNTAX      TimeTicks
-- li     MAX-ACCESS  read-only
-- li     STATUS      current
-- li     DESCRIPTION
-- li         "The value of sysUpTime when this VLAN was created."
-- li     ::= { dot1qVlanCurrentEntry 7 }
-- li 
-- -------------------------------------------------------------
-- The Static VLAN Database
-- -------------------------------------------------------------

dot1qVlanStaticTable OBJECT-TYPE
    SYNTAX      SEQUENCE OF Dot1qVlanStaticEntry
    MAX-ACCESS  not-accessible
    STATUS      current
    DESCRIPTION
        "A table containing static configuration information for
        each VLAN configured into the device by (local or
        network) management.  All entries are permanent and will
        be restored after the device is reset."
    ::= { dot1qVlan 3 }

dot1qVlanStaticEntry OBJECT-TYPE
    SYNTAX      Dot1qVlanStaticEntry
    MAX-ACCESS  not-accessible
    STATUS      current
    DESCRIPTION
        "Static information for a VLAN configured into the
        device by (local or network) management."
    INDEX   { dot1qVlanIndex }
    ::= { dot1qVlanStaticTable 1 }

Dot1qVlanStaticEntry ::=
    SEQUENCE {
        dot1qVlanIndex
            Unsigned32,
        dot1qVlanStaticName
            SnmpAdminString,
        dot1qVlanStaticEgressPorts
            PortList,
        dot1qVlanForbiddenEgressPorts
            PortList,
        dot1qVlanStaticUntaggedPorts
            PortList,
        dot1qVlanStaticRowStatus
            RowStatus
    }

-- li add the fellowing object and then chg the corrospongding part
dot1qVlanIndex OBJECT-TYPE
	SYNTAX      Unsigned32
    MAX-ACCESS  not-accessible
    STATUS      current
    DESCRIPTION
        "The VLAN-ID or other identifier refering to this VLAN."
    ::= { dot1qVlanStaticEntry 1 }

dot1qVlanStaticName OBJECT-TYPE
    SYNTAX      SnmpAdminString (SIZE (0..32))
    MAX-ACCESS  read-create
    STATUS      current
    DESCRIPTION
        "An administratively assigned string, which may be used
        to identify the VLAN."
    REFERENCE
        "IEEE 802.1Q/D11 Section 12.10.2.1"
    ::= { dot1qVlanStaticEntry 2 }

dot1qVlanStaticEgressPorts OBJECT-TYPE
    SYNTAX      PortList
    MAX-ACCESS  read-create
    STATUS      current
    DESCRIPTION
        "The set of ports which are permanently assigned to the
        egress list for this VLAN by management.  Changes to a
        bit in this object affect the per-port per-VLAN
        Registrar control for Registration Fixed for the
        relevant GVRP state machine on each port.  A port may
        not be added in this set if it is already a member of
        the set of ports in dot1qVlanForbiddenEgressPorts.  The
        default value of this object is a string of zeros of
        appropriate length, indicating not fixed."
    REFERENCE
        "IEEE 802.1Q/D11 Section 12.7.7.3, 11.2.3.2.3"
    ::= { dot1qVlanStaticEntry 3 }

dot1qVlanForbiddenEgressPorts OBJECT-TYPE
    SYNTAX      PortList
    MAX-ACCESS  read-create
    STATUS      current
    DESCRIPTION
        "The set of ports which are prohibited by management
        from being included in the egress list for this VLAN.
        Changes to this object that cause a port to be included
        or excluded affect the per-port per-VLAN Registrar

        control for Registration Forbidden for the relevant GVRP
        state machine on each port.  A port may not be added in
        this set if it is already a member of the set of ports
        in dot1qVlanStaticEgressPorts.  The default value of
        this object is a string of zeros of appropriate length,
        excluding all ports from the forbidden set."
    REFERENCE
        "IEEE 802.1Q/D11 Section 12.7.7.3, 11.2.3.2.3"
    ::= { dot1qVlanStaticEntry 4 }

dot1qVlanStaticUntaggedPorts OBJECT-TYPE
    SYNTAX      PortList
    MAX-ACCESS  read-create
    STATUS      current
    DESCRIPTION
        "The set of ports which should transmit egress packets
        for this VLAN as untagged.  The default value of this
        object for the default VLAN (dot1qVlanIndex = 1) is a string
        of appropriate length including all ports.  There is no
        specified default for other VLANs.  If a device agent cannot
        support the set of ports being set then it will reject the
        set operation with an error. An example might be if a
        manager attempts to set more than one VLAN to be untagged
        on egress where the device does not support this IEEE 802.1Q
        option."
    REFERENCE
        "IEEE 802.1Q/D11 Section 12.10.2.1"
    ::= { dot1qVlanStaticEntry 5 }

dot1qVlanStaticRowStatus OBJECT-TYPE
    SYNTAX      RowStatus
    MAX-ACCESS  read-create
    STATUS      current
    DESCRIPTION
        "This object indicates the status of this entry."
    ::= { dot1qVlanStaticEntry 6 }

-- li dot1qNextFreeLocalVlanIndex OBJECT-TYPE
-- li     SYNTAX      INTEGER (0|4096..2147483647)
-- li     MAX-ACCESS  read-only
-- li     STATUS      current
-- li     DESCRIPTION
-- li         "The next available value for dot1qVlanIndex of a local
-- li         VLAN entry in dot1qVlanStaticTable.  This will report
-- li         values >=4096 if a new Local VLAN may be created or else
-- li         the value 0 if this is not possible.
-- li 
-- li         A row creation operation in this table for an entry with a local
-- li         VlanIndex value may fail if the current value of this object
-- li         is not used as the index. Even if the value read is used,
-- li         there is no guarantee that it will still be the valid index
-- li         when the create operation is attempted - another manager may
-- li         have already got in during the intervening time interval.
-- li         In this case, dot1qNextFreeLocalVlanIndex should be re-read
-- li         and the creation re-tried with the new value.
-- li 
-- li         This value will automatically change when the current value is
-- li         used to create a new row."
-- li     ::= { dot1qVlan 4 }
-- li 
-- -------------------------------------------------------------
-- The VLAN Port Configuration Table
-- -------------------------------------------------------------

dot1qPortVlanTable OBJECT-TYPE
    SYNTAX      SEQUENCE OF Dot1qPortVlanEntry
    MAX-ACCESS  not-accessible
    STATUS      current
    DESCRIPTION
        "A table containing per port control and status
        information for VLAN configuration in the device."
    ::= { dot1qVlan 5 }

dot1qPortVlanEntry OBJECT-TYPE
    SYNTAX      Dot1qPortVlanEntry
    MAX-ACCESS  not-accessible
    STATUS      current
    DESCRIPTION
        "Information controlling VLAN configuration for a port
        on the device.  This is indexed by dot1dBasePort."
-- li del     AUGMENTS { dot1dBasePortEntry }
-- li add the felloing line:
    INDEX  { dot1dBasePort }
    ::= { dot1qPortVlanTable 1 }

Dot1qPortVlanEntry ::=
    SEQUENCE {
        dot1dBasePort
           INTEGER,
        dot1qPvid
            VlanIndex,
        dot1qPortAcceptableFrameTypes
            INTEGER,
        dot1qPortIngressFiltering
            TruthValue
    }

-- li add the felloing object and chg the corrospongding part
dot1dBasePort OBJECT-TYPE
              SYNTAX  INTEGER (1..65535)
              MAX-ACCESS  read-only
              STATUS  current
              DESCRIPTION
                      "The port number of the port for which this entry
                      contains bridge management information."
              ::= { dot1qPortVlanEntry 1 }

dot1qPvid OBJECT-TYPE
    SYNTAX      VlanIndex
    MAX-ACCESS  read-write
    STATUS      current
    DESCRIPTION
        "The PVID, the VLAN ID assigned to untagged frames or
        Priority-Tagged frames received on this port."
    REFERENCE
        "IEEE 802.1Q/D11 Section 12.10.1.1"
    DEFVAL      { 1 }
    ::= { dot1qPortVlanEntry 2 }

dot1qPortAcceptableFrameTypes OBJECT-TYPE
    SYNTAX      INTEGER {
                    admitAll(1),
                    admitOnlyVlanTagged(2)
                }
    MAX-ACCESS  read-write
    STATUS      current
    DESCRIPTION
        "When this is admitOnlyVlanTagged(2) the device will
        discard untagged frames or Priority-Tagged frames
        received on this port.  When admitAll(1), untagged
        frames or Priority-Tagged frames received on this port
        will be accepted and assigned to the PVID for this port.

        This control does not affect VLAN independent BPDU
        frames, such as GVRP and STP.  It does affect VLAN
        dependent BPDU frames, such as GMRP."
    REFERENCE
        "IEEE 802.1Q/D11 Section 12.10.1.3"
    DEFVAL      { admitAll }
    ::= { dot1qPortVlanEntry 3 }

dot1qPortIngressFiltering OBJECT-TYPE
    SYNTAX      TruthValue
    MAX-ACCESS  read-write
    STATUS      current

    DESCRIPTION
        "When this is true(1) the device will discard incoming
        frames for VLANs which do not include this Port in its
        Member set.  When false(2), the port will accept all
        incoming frames.

        This control does not affect VLAN independent BPDU
        frames, such as GVRP and STP.  It does affect VLAN
        dependent BPDU frames, such as GMRP."
    REFERENCE
        "IEEE 802.1Q/D11 Section 12.10.1.4"
    DEFVAL      { false }
    ::= { dot1qPortVlanEntry 4 }

-- dot1qPortGvrpStatus OBJECT-TYPE
--     SYNTAX      EnabledStatus
--     MAX-ACCESS  read-write
--     STATUS      current
--     DESCRIPTION
--         "The state of GVRP operation on this port.  The value
--         enabled(1) indicates that GVRP is enabled on this port,
--         as long as dot1qGvrpStatus is also enabled for this
--         device.  When disabled(2) but dot1qGvrpStatus is still
--         enabled for the device, GVRP is disabled on this port:
--         any GVRP packets received will be silently discarded and
--         no GVRP registrations will be propagated from other
--         ports.  This object affects all GVRP Applicant and
--         Registrar state machines on this port.  A transition
--         from disabled(2) to enabled(1) will cause a reset of all
--         GVRP state machines on this port."
--     DEFVAL      { enabled }
--     ::= { dot1qPortVlanEntry 5 }
-- 
-- dot1qPortGvrpFailedRegistrations OBJECT-TYPE
--     SYNTAX      Counter32
--     MAX-ACCESS  read-only
--     STATUS      current
--     DESCRIPTION
--         "The total number of failed GVRP registrations, for any
--         reason, on this port."
--     ::= { dot1qPortVlanEntry 6 }
-- 
-- dot1qPortGvrpLastPduOrigin OBJECT-TYPE
--     SYNTAX      MacAddress
--     MAX-ACCESS  read-only
--     STATUS      current
-- 
--     DESCRIPTION
--         "The Source MAC Address of the last GVRP message
--         received on this port."
--     ::= { dot1qPortVlanEntry 7 }

-- -------------------------------------------------------------
-- Per port VLAN Statistics Table
-- -------------------------------------------------------------
-- li 
-- li dot1qPortVlanStatisticsTable OBJECT-TYPE
-- li     SYNTAX      SEQUENCE OF Dot1qPortVlanStatisticsEntry
-- li     MAX-ACCESS  not-accessible
-- li     STATUS      current
-- li     DESCRIPTION
-- li         "A table containing per-port, per-VLAN statistics for
-- li         traffic received. Separate objects are provided for both the
-- li         most-significant and least-significant bits of statistics
-- li         counters for ports that are associated with this transparent
-- li         bridge. The most-significant bit objects are only required on
-- li         high capacity interfaces, as defined in the conformance clauses
-- li         for these objects. This mechanism is provided as a way to read
-- li         64-bit counters for agents which support only SNMPv1.
-- li 
-- li         Note that the reporting of most-significant and least-
-- li         significant counter bits separately runs the risk of missing
-- li         an overflow of the lower bits in the interval between sampling.
-- li         The manager must be aware of this possibility, even within the
-- li         same varbindlist, when interpreting the results of a request or
-- li         asynchronous notification."
-- li     ::= { dot1qVlan 6 }
-- li 
-- li dot1qPortVlanStatisticsEntry OBJECT-TYPE
-- li     SYNTAX      Dot1qPortVlanStatisticsEntry
-- li     MAX-ACCESS  not-accessible
-- li     STATUS      current
-- li     DESCRIPTION
-- li         "Traffic statistics for a VLAN on an interface."
-- li     INDEX   { dot1dBasePort, dot1qVlanIndex }
-- li     ::= { dot1qPortVlanStatisticsTable 1 }
-- li 
-- li Dot1qPortVlanStatisticsEntry ::=
-- li     SEQUENCE {
-- li 
-- li         dot1qTpVlanPortInFrames
-- li             Counter32,
-- li         dot1qTpVlanPortOutFrames
-- li             Counter32,
-- li         dot1qTpVlanPortInDiscards
-- li             Counter32,
-- li         dot1qTpVlanPortInOverflowFrames
-- li             Counter32,
-- li         dot1qTpVlanPortOutOverflowFrames
-- li             Counter32,
-- li         dot1qTpVlanPortInOverflowDiscards
-- li             Counter32
-- li     }
-- li 
-- li dot1qTpVlanPortInFrames OBJECT-TYPE
-- li     SYNTAX      Counter32
-- li     MAX-ACCESS  read-only
-- li     STATUS      current
-- li     DESCRIPTION
-- li         "The number of valid frames received by this port from
-- li         its segment which were classified as belonging to this
-- li         VLAN.  Note that a frame received on this port is
-- li         counted by this object if and only if it is for a
-- li         protocol being processed by the local forwarding process
-- li         for this VLAN.  This object includes received bridge
-- li         management frames classified as belonging to this VLAN
-- li         (e.g. GMRP, but not GVRP or STP)."
-- li     REFERENCE
-- li         "IEEE 802.1Q/D11 Section 12.6.1.1.3(a)"
-- li     ::= { dot1qPortVlanStatisticsEntry 1 }
-- li 
-- li dot1qTpVlanPortOutFrames OBJECT-TYPE
-- li     SYNTAX      Counter32
-- li     MAX-ACCESS  read-only
-- li     STATUS      current
-- li     DESCRIPTION
-- li         "The number of valid frames transmitted by this port to
-- li         its segment from the local forwarding process for this
-- li         VLAN.  This includes bridge management frames originated
-- li         by this device which are classified as belonging to this
-- li         VLAN (e.g. GMRP, but not GVRP or STP)."
-- li     REFERENCE
-- li         "IEEE 802.1Q/D11 Section 12.6.1.1.3(d)"
-- li     ::= { dot1qPortVlanStatisticsEntry 2 }
-- li 
-- li dot1qTpVlanPortInDiscards OBJECT-TYPE
-- li     SYNTAX      Counter32
-- li     MAX-ACCESS  read-only
-- li     STATUS      current
-- li     DESCRIPTION
-- li         "The number of valid frames received by this port from
-- li         its segment which were classified as belonging to this
-- li         VLAN which were discarded due to VLAN related reasons.
-- li         Specifically, the IEEE 802.1Q counters for Discard
-- li         Inbound and Discard on Ingress Filtering."
-- li     REFERENCE
-- li         "IEEE 802.1Q/D11 Section 12.6.1.1.3"
-- li     ::= { dot1qPortVlanStatisticsEntry 3 }
-- li 
-- li dot1qTpVlanPortInOverflowFrames OBJECT-TYPE
-- li     SYNTAX      Counter32
-- li     MAX-ACCESS  read-only
-- li     STATUS      current
-- li     DESCRIPTION
-- li         "The number of times the associated
-- li         dot1qTpVlanPortInFrames counter has overflowed."
-- li     REFERENCE
-- li         "ISO/IEC 15802-3 Section 14.6.1.1.3"
-- li     ::= { dot1qPortVlanStatisticsEntry 4 }
-- li 
-- li dot1qTpVlanPortOutOverflowFrames OBJECT-TYPE
-- li     SYNTAX      Counter32
-- li     MAX-ACCESS  read-only
-- li     STATUS      current
-- li     DESCRIPTION
-- li         "The number of times the associated
-- li         dot1qTpVlanPortOutFrames counter has overflowed."
-- li     REFERENCE
-- li         "ISO/IEC 15802-3 Section 14.6.1.1.3"
-- li     ::= { dot1qPortVlanStatisticsEntry 5 }
-- li 
-- li dot1qTpVlanPortInOverflowDiscards OBJECT-TYPE
-- li     SYNTAX      Counter32
-- li     MAX-ACCESS  read-only
-- li     STATUS      current
-- li     DESCRIPTION
-- li         "The number of times the associated
-- li         dot1qTpVlanPortInDiscards counter has overflowed."
-- li     REFERENCE
-- li         "ISO/IEC 15802-3 Section 14.6.1.1.3"
-- li     ::= { dot1qPortVlanStatisticsEntry 6 }
-- li 
-- li dot1qPortVlanHCStatisticsTable OBJECT-TYPE
-- li     SYNTAX      SEQUENCE OF Dot1qPortVlanHCStatisticsEntry
-- li     MAX-ACCESS  not-accessible
-- li     STATUS      current
-- li     DESCRIPTION
-- li         "A table containing per port, per VLAN statistics for
-- li         traffic on high capacity interfaces."
-- li     ::= { dot1qVlan 7 }
-- li 
-- li dot1qPortVlanHCStatisticsEntry OBJECT-TYPE
-- li     SYNTAX      Dot1qPortVlanHCStatisticsEntry
-- li     MAX-ACCESS  not-accessible
-- li     STATUS      current
-- li     DESCRIPTION
-- li         "Traffic statistics for a VLAN on a high capacity
-- li         interface."
-- li     INDEX   { dot1dBasePort, dot1qVlanIndex }
-- li     ::= { dot1qPortVlanHCStatisticsTable 1 }
-- li 
-- li Dot1qPortVlanHCStatisticsEntry ::=
-- li     SEQUENCE {
-- li         dot1qTpVlanPortHCInFrames
-- li             Counter64,
-- li         dot1qTpVlanPortHCOutFrames
-- li             Counter64,
-- li         dot1qTpVlanPortHCInDiscards
-- li             Counter64
-- li     }
-- li 
-- li dot1qTpVlanPortHCInFrames OBJECT-TYPE
-- li     SYNTAX      Counter64
-- li     MAX-ACCESS  read-only
-- li     STATUS      current
-- li     DESCRIPTION
-- li         "The number of valid frames received by this port from
-- li         its segment which were classified as belonging to this
-- li         VLAN.  Note that a frame received on this port is
-- li         counted by this object if and only if it is for a
-- li         protocol being processed by the local forwarding process
-- li         for this VLAN.  This object includes received bridge
-- li         management frames classified as belonging to this VLAN
-- li         (e.g. GMRP, but not GVRP or STP)."
-- li     REFERENCE
-- li         "IEEE 802.1Q/D11 Section 12.6.1.1.3(a)"
-- li     ::= { dot1qPortVlanHCStatisticsEntry 1 }
-- li 
-- li dot1qTpVlanPortHCOutFrames OBJECT-TYPE
-- li     SYNTAX      Counter64
-- li     MAX-ACCESS  read-only
-- li     STATUS      current
-- li     DESCRIPTION
-- li         "The number of valid frames transmitted by this port to
-- li         its segment from the local forwarding process for this
-- li         VLAN.  This includes bridge management frames originated
-- li         by this device which are classified as belonging to this
-- li         VLAN (e.g. GMRP, but not GVRP or STP)."
-- li     REFERENCE
-- li         "IEEE 802.1Q/D11 Section 12.6.1.1.3(d)"
-- li     ::= { dot1qPortVlanHCStatisticsEntry 2 }
-- li 
-- li dot1qTpVlanPortHCInDiscards OBJECT-TYPE
-- li     SYNTAX      Counter64
-- li     MAX-ACCESS  read-only
-- li     STATUS      current
-- li     DESCRIPTION
-- li         "The number of valid frames received by this port from
-- li         its segment which were classified as belonging to this
-- li         VLAN which were discarded due to VLAN related reasons.
-- li         Specifically, the IEEE 802.1Q counters for Discard
-- li         Inbound and Discard on Ingress Filtering."
-- li     REFERENCE
-- li         "IEEE 802.1Q/D11 Section 12.6.1.1.3"
-- li     ::= { dot1qPortVlanHCStatisticsEntry 3 }
-- li 
-- -------------------------------------------------------------
-- The VLAN Learning Constraints Table
-- -------------------------------------------------------------
-- li 
-- li dot1qLearningConstraintsTable OBJECT-TYPE
-- li     SYNTAX      SEQUENCE OF Dot1qLearningConstraintsEntry
-- li     MAX-ACCESS  not-accessible
-- li     STATUS      current
-- li     DESCRIPTION
-- li         "A table containing learning constraints for sets of
-- li         Shared and Independendent VLANs."
-- li     REFERENCE
-- li         "IEEE 802.1Q/D11 Section 12.10.3.1"
-- li     ::= { dot1qVlan 8 }
-- li 
-- li dot1qLearningConstraintsEntry OBJECT-TYPE
-- li     SYNTAX      Dot1qLearningConstraintsEntry
-- li     MAX-ACCESS  not-accessible
-- li     STATUS      current
-- li 
-- li     DESCRIPTION
-- li         "A learning constraint defined for a VLAN."
-- li     INDEX   { dot1qConstraintVlan, dot1qConstraintSet }
-- li     ::= { dot1qLearningConstraintsTable 1 }
-- li 
-- li Dot1qLearningConstraintsEntry ::=
-- li     SEQUENCE {
-- li         dot1qConstraintVlan
-- li             VlanIndex,
-- li         dot1qConstraintSet
-- li             INTEGER,
-- li         dot1qConstraintType
-- li             INTEGER,
-- li         dot1qConstraintStatus
-- li             RowStatus
-- li     }
-- li 
-- li dot1qConstraintVlan OBJECT-TYPE
-- li     SYNTAX      VlanIndex
-- li     MAX-ACCESS  not-accessible
-- li     STATUS      current
-- li     DESCRIPTION
-- li         "The index of the row in dot1qVlanCurrentTable for the
-- li         VLAN constrained by this entry."
-- li     ::= { dot1qLearningConstraintsEntry 1 }
-- li 
-- li dot1qConstraintSet OBJECT-TYPE
-- li     SYNTAX      INTEGER (0..65535)
-- li     MAX-ACCESS  not-accessible
-- li     STATUS      current
-- li     DESCRIPTION
-- li         "The identity of the constraint set to which
-- li         dot1qConstraintVlan belongs.  These values may be chosen
-- li         by the management station."
-- li     ::= { dot1qLearningConstraintsEntry 2 }
-- li 
-- li dot1qConstraintType OBJECT-TYPE
-- li     SYNTAX      INTEGER {
-- li                     independent(1),
-- li                     shared(2)
-- li                 }
-- li     MAX-ACCESS  read-create
-- li     STATUS      current
-- li     DESCRIPTION
-- li         "The type of constraint this entry defines.
-- li             independent(1) - the VLAN, dot1qConstraintVlan,
-- li                 uses an independent filtering database from all
-- li 
-- li                 other VLANs in the same set, defined by
-- li                 dot1qConstraintSet.
-- li             shared(2) - the VLAN, dot1qConstraintVlan, shares
-- li                 the same filtering database as all other VLANs
-- li                 in the same set, defined by dot1qConstraintSet."
-- li     ::= { dot1qLearningConstraintsEntry 3 }
-- li 
-- li dot1qConstraintStatus OBJECT-TYPE
-- li     SYNTAX      RowStatus
-- li     MAX-ACCESS  read-create
-- li     STATUS      current
-- li     DESCRIPTION
-- li         "The status of this entry."
-- li     ::= { dot1qLearningConstraintsEntry 4 }
-- li 
-- li dot1qConstraintSetDefault OBJECT-TYPE
-- li     SYNTAX      INTEGER (0..65535)
-- li     MAX-ACCESS  read-write
-- li     STATUS      current
-- li     DESCRIPTION
-- li         "The identity of the constraint set to which a VLAN
-- li         belongs, if there is not an explicit entry for that VLAN
-- li         in dot1qLearningConstraintsTable."
-- li     ::= { dot1qVlan 9 }
-- li 
-- li dot1qConstraintTypeDefault OBJECT-TYPE
-- li     SYNTAX      INTEGER {
-- li                     independent(1),
-- li                     shared(2)
-- li                 }
-- li     MAX-ACCESS  read-write
-- li     STATUS      current
-- li     DESCRIPTION
-- li         "The type of constraint set to which a VLAN belongs, if
-- li         there is not an explicit entry for that VLAN in
-- li         dot1qLearningConstraintsTable.  The types are as defined
-- li         for dot1qConstraintType."
-- li     ::= { dot1qVlan 10 }
-- li 
-- -------------------------------------------------------------
-- IEEE 802.1Q MIB - Conformance Information
-- -------------------------------------------------------------
 
qBridgeConformance OBJECT IDENTIFIER ::= { zxQvlanMib 2 }

qBridgeGroups OBJECT IDENTIFIER ::= { qBridgeConformance 1 }

qBridgeCompliances OBJECT IDENTIFIER
    ::= { qBridgeConformance 2 }

-- -------------------------------------------------------------
-- units of conformance
-- -------------------------------------------------------------

qBridgeBaseGroup OBJECT-GROUP
    OBJECTS {
        dot1qVlanVersionNumber,
        dot1qMaxVlanId,
        dot1qMaxSupportedVlans,
        dot1qNumVlans
    }
    STATUS      current
    DESCRIPTION
        "A collection of objects providing device level control
        and status information for the Virtual LAN bridge
        services."
    ::= { qBridgeGroups 1 }

-- li qBridgeFdbUnicastGroup OBJECT-GROUP
-- li     OBJECTS {
-- li         dot1qFdbDynamicCount,
-- li         dot1qTpFdbPort,
-- li         dot1qTpFdbStatus
-- li     }
-- li     STATUS      current
-- li     DESCRIPTION
-- li         "A collection of objects providing information about all
-- li         unicast addresses, learnt dynamically or statically
-- li         configured by management, in each Filtering Database."
-- li     ::= { qBridgeGroups 2 }
-- li 
-- li qBridgeFdbMulticastGroup OBJECT-GROUP
-- li     OBJECTS {
-- li         dot1qTpGroupEgressPorts,
-- li         dot1qTpGroupLearnt
-- li     }
-- li 
-- li     STATUS      current
-- li     DESCRIPTION
-- li         "A collection of objects providing information about all
-- li         multicast addresses, learnt dynamically or statically
-- li         configured by management, in each Filtering Database."
-- li     ::= { qBridgeGroups 3 }
-- li 
-- li qBridgeServiceRequirementsGroup OBJECT-GROUP
-- li     OBJECTS {
-- li         dot1qForwardAllPorts,
-- li         dot1qForwardAllStaticPorts,
-- li         dot1qForwardAllForbiddenPorts,
-- li         dot1qForwardUnregisteredPorts,
-- li         dot1qForwardUnregisteredStaticPorts,
-- li         dot1qForwardUnregisteredForbiddenPorts
-- li     }
-- li     STATUS      current
-- li     DESCRIPTION
-- li         "A collection of objects providing information about
-- li         service requirements, learnt dynamically or statically
-- li         configured by management, in each Filtering Database."
-- li     ::= { qBridgeGroups 4 }
-- li 
-- li qBridgeFdbStaticGroup OBJECT-GROUP
-- li     OBJECTS {
-- li         dot1qStaticUnicastAllowedToGoTo,
-- li         dot1qStaticUnicastStatus,
-- li         dot1qStaticMulticastStaticEgressPorts,
-- li         dot1qStaticMulticastForbiddenEgressPorts,
-- li         dot1qStaticMulticastStatus
-- li     }
-- li     STATUS      current
-- li     DESCRIPTION
-- li         "A collection of objects providing information about
-- li         unicast and multicast addresses statically configured by
-- li         management, in each Filtering Database or VLAN."
-- li     ::= { qBridgeGroups 5 }
-- li 
-- li qBridgeVlanGroup OBJECT-GROUP
-- li     OBJECTS {
-- li         dot1qVlanNumDeletes,
-- li         dot1qVlanFdbId,
-- li         dot1qVlanCurrentEgressPorts,
-- li         dot1qVlanCurrentUntaggedPorts,
-- li         dot1qVlanStatus,
-- li         dot1qVlanCreationTime
-- li     }
-- li 
-- li     STATUS      current
-- li     DESCRIPTION
-- li         "A collection of objects providing information about
-- li         all VLANs currently configured on this device."
-- li     ::= { qBridgeGroups 6 }
-- li 
qBridgeVlanStaticGroup OBJECT-GROUP
    OBJECTS {
        dot1qVlanStaticName,
        dot1qVlanStaticEgressPorts,
        dot1qVlanForbiddenEgressPorts,
        dot1qVlanStaticUntaggedPorts,
        dot1qVlanStaticRowStatus
    }
    STATUS      current
    DESCRIPTION
        "A collection of objects providing information about
        VLANs statically configured by management."
    ::= { qBridgeGroups 7 }

qBridgePortGroup OBJECT-GROUP
    OBJECTS {
        dot1qPvid,
        dot1qPortAcceptableFrameTypes,
        dot1qPortIngressFiltering
    }
    STATUS      current
    DESCRIPTION
        "A collection of objects providing port level VLAN
        control and status information for all ports."
    ::= { qBridgeGroups 8 }

-- li qBridgeVlanStatisticsGroup OBJECT-GROUP
-- li     OBJECTS {
-- li         dot1qTpVlanPortInFrames,
-- li         dot1qTpVlanPortOutFrames,
-- li         dot1qTpVlanPortInDiscards
-- li     }
-- li     STATUS      current
-- li     DESCRIPTION
-- li         "A collection of objects providing per-port packet
-- li         statistics for all VLANs currently configured on this
-- li         device."
-- li     ::= { qBridgeGroups 9 }
-- li 
-- li qBridgeVlanStatisticsOverflowGroup OBJECT-GROUP
-- li     OBJECTS {
-- li         dot1qTpVlanPortInOverflowFrames,
-- li         dot1qTpVlanPortOutOverflowFrames,
-- li         dot1qTpVlanPortInOverflowDiscards
-- li     }
-- li     STATUS      current
-- li     DESCRIPTION
-- li         "A collection of objects providing overflow counters for
-- li         per-port packet statistics for all VLANs currently configured
-- li         on this device for high capacity interfaces, defined as those
-- li         that have the value of the corresponding instance of
-- li         ifSpeed greater than 650,000,000 bits/second."
-- li     ::= { qBridgeGroups 10 }
-- li 
-- li qBridgeVlanHCStatisticsGroup OBJECT-GROUP
-- li     OBJECTS {
-- li         dot1qTpVlanPortHCInFrames,
-- li         dot1qTpVlanPortHCOutFrames,
-- li         dot1qTpVlanPortHCInDiscards
-- li     }
-- li     STATUS      current
-- li     DESCRIPTION
-- li         "A collection of objects providing per-port packet
-- li         statistics for all VLANs currently configured on this
-- li         device for high capacity interfaces, defined as those
-- li         that have the value of the corresponding instance of
-- li         ifSpeed greater than 650,000,000 bits/second."
-- li     ::= { qBridgeGroups 11 }
-- li 
-- li qBridgeLearningConstraintsGroup OBJECT-GROUP
-- li     OBJECTS {
-- li         dot1qConstraintType,
-- li         dot1qConstraintStatus
-- li     }
-- li     STATUS      current
-- li     DESCRIPTION
-- li         "A collection of objects defining the Filtering Database
-- li         constraints all VLANs have with each other."
-- li     ::= { qBridgeGroups 12 }
-- li 
-- li qBridgeLearningConstraintDefaultGroup OBJECT-GROUP
-- li     OBJECTS {
-- li         dot1qConstraintSetDefault,
-- li         dot1qConstraintTypeDefault
-- li     }
-- li 
-- li     STATUS      current
-- li     DESCRIPTION
-- li         "A collection of objects defining the default Filtering
-- li         Database constraints for VLANs which have no specific
-- li         constraints defined."
-- li     ::= { qBridgeGroups 13 }
-- li 
-- -------------------------------------------------------------
-- compliance statements
-- -------------------------------------------------------------
-- li 
-- li qBridgeCompliance MODULE-COMPLIANCE
-- li     STATUS  current
-- li     DESCRIPTION
-- li         "The compliance statement for device support of Virtual
-- li         LAN Bridge services."
-- li 
-- li     MODULE
-- li         MANDATORY-GROUPS {
-- li             qBridgeBaseGroup,
-- li             qBridgeVlanGroup,
-- li             qBridgeVlanStaticGroup,
-- li             qBridgePortGroup
-- li         }
-- li 
-- li         GROUP       qBridgeFdbUnicastGroup
-- li         DESCRIPTION
-- li             "This group is mandatory for bridges that implement
-- li             802.1Q transparent bridging."
-- li 
-- li         GROUP       qBridgeFdbMulticastGroup
-- li         DESCRIPTION
-- li             "This group is mandatory for bridges that implement
-- li             802.1Q transparent bridging."
-- li 
-- li         GROUP       qBridgeServiceRequirementsGroup
-- li         DESCRIPTION
-- li             "This group is mandatory for bridges that implement
-- li             extended filtering services.  All objects must be
-- li             read-write if extended-filtering services are
-- li             enabled."
-- li 
-- li         GROUP       qBridgeFdbStaticGroup
-- li         DESCRIPTION
-- li             "This group is optional."
-- li 
-- li         GROUP       qBridgeVlanStatisticsGroup
-- li         DESCRIPTION
-- li             "This group is optional as there may be significant
-- li             implementation cost associated with its support."
-- li 
-- li         GROUP       qBridgeVlanStatisticsOverflowGroup
-- li         DESCRIPTION
-- li             "This group is optional as there may be significant
-- li             implementation cost associated with its support. It is most
-- li             relevant for high capacity interfaces where the SNMP agent
-- li             supports only SNMPv1."
-- li 
-- li         GROUP       qBridgeVlanHCStatisticsGroup
-- li         DESCRIPTION
-- li             "This group is optional as there may be significant
-- li             implementation cost associated with its support. It is most
-- li             relevant for high capacity interfaces."
-- li 
-- li         GROUP       qBridgeLearningConstraintsGroup
-- li         DESCRIPTION
-- li             "This group is mandatory for devices implementing
-- li              both Independent VLAN Learning (IVL) and Shared
-- li              VLAN Learning (SVL) modes of operation of the
-- li              filtering database, as defined by IEEE 802.1Q."
-- li 
-- li         GROUP       qBridgeLearningConstraintDefaultGroup
-- li         DESCRIPTION
-- li             "This group is mandatory for devices implementing
-- li              both Independent VLAN Learning (IVL) and Shared
-- li              VLAN Learning (SVL) modes of operation of the
-- li              filtering database, as defined by IEEE 802.1Q."
-- li 
-- li         OBJECT      dot1qPortAcceptableFrameTypes
-- li         MIN-ACCESS  read-only
-- li         DESCRIPTION
-- li             "Write access is not required as this is an optional
-- li             capability in IEEE 802.1Q."
-- li 
-- li         OBJECT      dot1qPortIngressFiltering
-- li         MIN-ACCESS  read-only
-- li         DESCRIPTION
-- li             "Write access is not required as this is an optional
-- li             capability in IEEE 802.1Q."
-- li 
-- li         OBJECT      dot1qConstraintSetDefault
-- li         MIN-ACCESS  read-only
-- li         DESCRIPTION
-- li             "Write access is not required as this is an optional
-- li             capability in IEEE 802.1Q."
-- li 
-- li         OBJECT      dot1qConstraintTypeDefault
-- li         MIN-ACCESS  read-only
-- li         DESCRIPTION
-- li             "Write access is not required as this is an optional
-- li             capability in IEEE 802.1Q."
-- li 
-- li        ::= { qBridgeCompliances 1 }

END
HDSL2-SHDSL-LINE-MIB DEFINITIONS ::= BEGIN

IMPORTS 
        MODULE-IDENTITY,OBJECT-TYPE,Counter32,Unsigned32,Gauge32,
		NOTIFICATION-TYPE,Integer32,transmission
		      FROM SNMPv2-SMI 
		RowStatus,TEXTUAL-CONVENTION      
		      FROM SNMPv2-TC
		ifIndex                 
		      FROM IF-MIB
		PerfCurrentCount,PerfIntervalCount        
		      FROM PerfHist-TC-MIB
		SnmpAdminString          
		      FROM SNMP-FRAMEWORK-MIB
		MODULE-COMPLIANCE,OBJECT-GROUP,NOTIFICATION-GROUP      
		      FROM SNMPv2-CONF;

hdsl2ShdslMIB MODULE-IDENTITY
    LAST-UPDATED "200205090000Z" -- May 9, 2002
    ORGANIZATION "ADSLMIB Working Group"
    CONTACT-INFO "WG-email:  adslmib@ietf.org
               Info:      https://www1.ietf.org/mailman/listinfo/adslmib
               Chair:     Mike Sneed
               Postal:    P.O. Box 37324
                          Raleigh NC 27627-7324
               Email:     sneedmike@hotmail.com

               Co-editor: Bob Ray
                          PESA Switching Systems, Inc.
               Postal:    330-A Wynn Drive
                          Huntsville, AL 35805 USA
               Email:     rray@pesa.com
               Phone:     +1 256 726 9200 ext. 142

               Co-editor: Rajesh Abbi
                          Alcatel USA
               Postal:    2912 Wake Forest Road
                          Raleigh, NC 27609-7860 USA

               Email:     Rajesh.Abbi@alcatel.com
               Phone:     +1 919 850 6194
              "

DESCRIPTION
     "This MIB module defines a collection of objects for managing
      HDSL2/SHDSL lines.  An agent may reside at either end of the
      line, however the MIB is designed to require no management
      communication between the modems beyond that inherent in the
      low-level EOC line protocol as defined in ANSI T1E1.4/2000-006
      (for HDSL2 lines), or in ITU G.991.2 (for SHDSL lines)."
 REVISION "200205090000Z" -- May 9, 2002
 DESCRIPTION "Initial version, published as RFC 3276."

 ::= { transmission 48 }

hdsl2ShdslMibObjects OBJECT IDENTIFIER ::= { hdsl2ShdslMIB 1 }

-- Textual Conventions used in this MIB
--

Hdsl2ShdslPerfCurrDayCount ::= TEXTUAL-CONVENTION
   STATUS    current
   DESCRIPTION
     "A gauge associated with interface performance measurements in
      a current 1-day (24 hour) measurement interval.

      The value of this gauge starts at zero at the beginning of an
      interval and is increased when associated events occur, until
      the end of the 1-day interval.  At that time the value of the
      gauge is stored in the previous 1-day history interval, as
      defined in a companion object of type
      Hdsl2Shdsl1DayIntevalCount, and the current interval gauge
      is restarted at zero.

      In the case where the agent has no valid data available for
      this interval the corresponding object instance is not
      available and upon a retrieval request a corresponding error
      message shall be returned to indicate that this instance does
      not exist.  Please note that zero is a valid value."
   SYNTAX  Gauge32

Hdsl2Shdsl1DayIntervalCount ::= TEXTUAL-CONVENTION
   STATUS    current
   DESCRIPTION
     "A counter associated with interface performance measurements
      during the most previous 1-day (24 hour) measurement interval.
      The value of this gauge is equal to the value of the current
      day gauge, as defined in a companion object of type
      Hdsl2ShdslPerfCurrDayCount, at the end of its most recent
      interval.

      In the case where the agent has no valid data available for
      this interval the corresponding object instance is not
      available and upon a retrieval request a corresponding error
      message shall be returned to indicate that this instance does
      not exist."
   SYNTAX  Gauge32

Hdsl2ShdslPerfTimeElapsed ::= TEXTUAL-CONVENTION
   STATUS    current
   DESCRIPTION
     "The number of seconds that have elapsed since the beginning of
      the current measurement period.  If, for some reason, such as
      an adjustment in the system's time-of-day clock or the addition
      of a leap second, the current interval exceeds the maximum
      value, the agent will return the maximum value.

      For 15 minute intervals, the range is limited to (0..899).
      For 24 hour intervals, the range is limited to (0..86399)."
   SYNTAX    Unsigned32(0..86399)

Hdsl2ShdslPerfIntervalThreshold ::= TEXTUAL-CONVENTION
   STATUS    current
   DESCRIPTION
     "This convention defines a range of values that may be set in
      a fault threshold alarm control.  As the number of seconds in
      a 15-minute interval numbers at most 900, objects of this type
      may have a range of 0...900, where the value of 0 disables the
      alarm."
   SYNTAX    Unsigned32(0..900)

Hdsl2ShdslUnitId ::= TEXTUAL-CONVENTION
   STATUS    current
   DESCRIPTION
     "This is the unique identification for all units in a
      HDSL2/SHDSL Span.  It is based on the EOC unit addressing
      scheme with reference to the xtuC."
   SYNTAX    INTEGER
           {
           xtuC(1),
           xtuR(2),
           xru1(3),
           xru2(4),
           xru3(5),
           xru4(6),
           xru5(7),
           xru6(8),
           xru7(9),
           xru8(10)
           }

Hdsl2ShdslUnitSide ::= TEXTUAL-CONVENTION
   STATUS    current
   DESCRIPTION
     "This is the referenced side of a HDSL2/SHDSL unit - Network
      or Customer side.  The side facing the Network is the Network
      side, while the side facing the Customer is the Customer side."
   SYNTAX    INTEGER
           {
           networkSide(1),
           customerSide(2)
           }

Hdsl2ShdslWirePair ::= TEXTUAL-CONVENTION
   STATUS    current
   DESCRIPTION
     "This is the referenced pair of wires in a HDSL2/SHDSL Segment.
      HDSL2 only supports a single pair (wirePair1), while SHDSL
      supports an optional second pair (wirePair2)."
   SYNTAX    INTEGER
           {
           wirePair1(1),
           wirePair2(2)
           }

Hdsl2ShdslTransmissionModeType ::= TEXTUAL-CONVENTION
   STATUS    current
   DESCRIPTION
     "Contains the regional setting of the HDSL2/SHDSL span,
     represented as a bit-map of possible settings. The various
     bit positions are:

     Bit   Meaning      Description
     1     region 1     Indicates ITU-T G.991.2 Annex A.
     2     region 2     Indicates ITU-T G.991.2 Annex B."
   SYNTAX      BITS
           {
           region1(0),
           region2(1)
           }

Hdsl2ShdslClockReferenceType ::= TEXTUAL-CONVENTION
   STATUS    current
   DESCRIPTION
     "The various STU-C symbol clock references for the
     HDSL2/SHDSL span, represented as an enumeration."
   SYNTAX    INTEGER
          {
          localClk(1),          -- Mode-1 per G991.2
          networkClk(2),        -- Mode-2 per G991.2
          dataOrNetworkClk(3),  -- Mode-3a per G991.2
          dataClk(4)            -- Mode-3b per G991.2
          }

-- Span Configuration Group
--

hdsl2ShdslSpanConfTable OBJECT-TYPE
   SYNTAX     SEQUENCE OF Hdsl2ShdslSpanConfEntry
   MAX-ACCESS not-accessible
   STATUS     current
   DESCRIPTION
     "This table supports overall configuration of HDSL2/SHDSL
      Spans.  Entries in this table MUST be maintained in a
      persistent manner."
   ::= { hdsl2ShdslMibObjects 1 }

hdsl2ShdslSpanConfEntry OBJECT-TYPE
   SYNTAX      Hdsl2ShdslSpanConfEntry
   MAX-ACCESS  not-accessible
   STATUS      current
   DESCRIPTION
     "An entry in the hdsl2ShdslSpanConfTable.  Each entry
      represents the complete Span in a single HDSL2/SHDSL line.
      It is indexed by the ifIndex of the associated HDSL2/SHDSL
      line."
   INDEX { ifIndex }
   ::= { hdsl2ShdslSpanConfTable 1 }

Hdsl2ShdslSpanConfEntry ::=
   SEQUENCE
   {
   hdsl2ShdslSpanConfNumRepeaters          Unsigned32,
   hdsl2ShdslSpanConfProfile               SnmpAdminString,
   hdsl2ShdslSpanConfAlarmProfile          SnmpAdminString
   }

   hdsl2ShdslSpanConfNumRepeaters OBJECT-TYPE
   SYNTAX      Unsigned32(0..8)
   UNITS       "repeaters"
   MAX-ACCESS  read-write
   STATUS      current
   DESCRIPTION
     "This object provisions the number of repeaters/regenerators
     in this HDSL2/SHDSL Span."
   ::= { hdsl2ShdslSpanConfEntry 1 }

hdsl2ShdslSpanConfProfile OBJECT-TYPE
   SYNTAX      SnmpAdminString (SIZE(1..32))
   MAX-ACCESS  read-write
   STATUS      current
   DESCRIPTION
     "This object is a pointer to a span configuration profile in
     the hdsl2ShdslSpanConfProfileTable, which applies to this span.
     The value of this object is the index of the referenced profile
     in the hdsl2ShdslSpanConfProfileTable.  Note that span
     configuration profiles are only applicable to SHDSL lines.

     HDSL2 lines MUST reference the default profile, 'DEFVAL'.
     By default, this object will have the value 'DEFVAL' (the index
     of the default profile).

     Any attempt to set this object to a value that is not the value
     of the index for an active entry in the profile table,
     hdsl2ShdslSpanConfProfileTable, MUST be rejected."
   ::= { hdsl2ShdslSpanConfEntry 2 }

hdsl2ShdslSpanConfAlarmProfile OBJECT-TYPE
   SYNTAX      SnmpAdminString (SIZE(1..32))
   MAX-ACCESS  read-write
   STATUS      current
   DESCRIPTION
     "This object is a pointer to an Alarm configuration profile in
     the hdsl2ShdslEndpointAlarmConfProfileTable.  The value of this
     object is the index of the referenced profile in the
     hdsl2ShdslEndpointAlarmConfProfileTable.  The alarm threshold
     configuration in the referenced profile will be used by default
     for all segment endpoints in this span.  Individual endpoints
     may override this profile by explicitly specifying some other
     profile in the hdsl2ShdslEndpointConfTable.  By default, this
     object will have the value 'DEFVAL' (the index of the default
     profile).

     Any attempt to set this object to a value that is not the value
     of the index for an active entry in the profile table,
     hdsl2ShdslEndpointAlarmConfProfileTable, MUST be rejected."
   ::= { hdsl2ShdslSpanConfEntry 3 }

-- Span Status Group
--

hdsl2ShdslSpanStatusTable OBJECT-TYPE
   SYNTAX     SEQUENCE OF Hdsl2ShdslSpanStatusEntry
   MAX-ACCESS not-accessible
   STATUS     current
   DESCRIPTION
     "This table provides overall status information of
      HDSL2/SHDSL spans.  This table contains live data from
      equipment.  As such, it is NOT persistent."
   ::= { hdsl2ShdslMibObjects 2 }

hdsl2ShdslSpanStatusEntry OBJECT-TYPE
   SYNTAX      Hdsl2ShdslSpanStatusEntry
   MAX-ACCESS  not-accessible
   STATUS      current
   DESCRIPTION
     "An entry in the hdsl2ShdslSpanStatusTable.  Each entry
      represents the complete span in a single HDSL2/SHDSL line.
      It is indexed by the ifIndex of the associated HDSL2/SHDSL
      line."
   INDEX { ifIndex }
   ::= { hdsl2ShdslSpanStatusTable 1 }

Hdsl2ShdslSpanStatusEntry ::=
   SEQUENCE
   {
   hdsl2ShdslStatusNumAvailRepeaters        Unsigned32,
   hdsl2ShdslStatusMaxAttainableLineRate    Unsigned32,
   hdsl2ShdslStatusActualLineRate           Unsigned32,
   hdsl2ShdslStatusTransmissionModeCurrent
             Hdsl2ShdslTransmissionModeType}

hdsl2ShdslStatusNumAvailRepeaters OBJECT-TYPE
   SYNTAX      Unsigned32(0..8)
   MAX-ACCESS  read-only
   STATUS      current
   DESCRIPTION
     "Contains the actual number of repeaters/regenerators
      discovered in this HDSL2/SHDSL span."
   ::= { hdsl2ShdslSpanStatusEntry 1 }

hdsl2ShdslStatusMaxAttainableLineRate OBJECT-TYPE
   SYNTAX      Unsigned32(0..4112000)
   UNITS       "bps"
   MAX-ACCESS  read-only
   STATUS      current
   DESCRIPTION
     "Contains the maximum attainable line rate in this HDSL2/SHDSL
      span.  This object provides the maximum rate the line is
      capable of achieving.  This is based upon measurements made
      during line probing."
   ::= { hdsl2ShdslSpanStatusEntry 2 }

hdsl2ShdslStatusActualLineRate OBJECT-TYPE
   SYNTAX      Unsigned32(0..4112000)
   UNITS       "bps"
   MAX-ACCESS  read-only
   STATUS      current
   DESCRIPTION
     "Contains the actual line rate in this HDSL2/SHDSL span.  This
     should equal ifSpeed."
   ::= { hdsl2ShdslSpanStatusEntry 3 }

hdsl2ShdslStatusTransmissionModeCurrent OBJECT-TYPE
   SYNTAX      Hdsl2ShdslTransmissionModeType
   MAX-ACCESS  read-only
   STATUS      current
   DESCRIPTION
     "Contains the current Power Spectral Density (PSD) regional
      setting of the HDSL2/SHDSL span."
   ::= { hdsl2ShdslSpanStatusEntry 4 }

-- Unit Inventory Group
--

hdsl2ShdslInventoryTable OBJECT-TYPE
   SYNTAX     SEQUENCE OF Hdsl2ShdslInventoryEntry
   MAX-ACCESS not-accessible
   STATUS     current
   DESCRIPTION
     "This table supports retrieval of unit inventory information
      available via the EOC from units in a HDSL2/SHDSL line.

      Entries in this table are dynamically created during the
      line discovery process.  The life cycle for these entries
      is as follows:

         - xtu discovers a device, either a far-end xtu or an xru
         - an inventory table entry is created for the device
         - the line goes down for whatever reason
         - inventory table entries for unreachable devices are
           destroyed.

      As these entries are created/destroyed dynamically, they
      are NOT persistent."
   ::= { hdsl2ShdslMibObjects 3 }

hdsl2ShdslInventoryEntry OBJECT-TYPE
   SYNTAX      Hdsl2ShdslInventoryEntry
   MAX-ACCESS  not-accessible
   STATUS      current
   DESCRIPTION
     "An entry in the hdsl2ShdslInventoryTable.  Each entry
      represents inventory information for a single unit in a
      HDSL2/SHDSL line.  It is indexed by the ifIndex of the
      HDSL2/SHDSL line and the Hdsl2ShdslUnitId of the
      associated unit."
   INDEX { ifIndex, hdsl2ShdslInvIndex }
   ::= { hdsl2ShdslInventoryTable 1 }

Hdsl2ShdslInventoryEntry ::=
   SEQUENCE
   {
   hdsl2ShdslInvIndex                      Hdsl2ShdslUnitId,
   hdsl2ShdslInvVendorID                   OCTET STRING,
--    hdsl2ShdslInvVendorModelNumber          OCTET STRING,
--    hdsl2ShdslInvVendorSerialNumber         OCTET STRING,
--    hdsl2ShdslInvVendorEOCSoftwareVersion   Integer32,
--    hdsl2ShdslInvStandardVersion            Integer32,
--    hdsl2ShdslInvVendorListNumber           OCTET STRING,
--    hdsl2ShdslInvVendorIssueNumber          OCTET STRING,
--    hdsl2ShdslInvVendorSoftwareVersion      OCTET STRING,
--    hdsl2ShdslInvEquipmentCode              OCTET STRING,
--    hdsl2ShdslInvVendorOther                OCTET STRING,
    hdsl2ShdslInvTransmissionModeCapability
                          Hdsl2ShdslTransmissionModeType
    }
 
hdsl2ShdslInvIndex OBJECT-TYPE
   SYNTAX      Hdsl2ShdslUnitId
   MAX-ACCESS  not-accessible
   STATUS      current
   DESCRIPTION
      "Each entry in this table corresponds to a physical element
      in a HDSL2/SHDSL Span.  It is based on the EOC unit addressing
      scheme with reference to the xtuC."
   ::= { hdsl2ShdslInventoryEntry 1 }

hdsl2ShdslInvVendorID OBJECT-TYPE
   SYNTAX      OCTET STRING(SIZE(8))
   MAX-ACCESS  read-only
   STATUS      current
   DESCRIPTION
     "Vendor ID as reported in an Inventory Response message."
   ::= { hdsl2ShdslInventoryEntry 2 }

-- hdsl2ShdslInvVendorModelNumber OBJECT-TYPE
--    SYNTAX      OCTET STRING(SIZE(12))
--    MAX-ACCESS  read-only
--    STATUS      current
--    DESCRIPTION
--      "Vendor model number as reported in an Inventory Response
--       message."
--    ::= { hdsl2ShdslInventoryEntry 3 }
-- 
-- hdsl2ShdslInvVendorSerialNumber OBJECT-TYPE
--    SYNTAX      OCTET STRING(SIZE(12))
--    MAX-ACCESS  read-only
--    STATUS      current
--    DESCRIPTION
--      "Vendor serial number as reported in an Inventory Response
--       message."
--    ::= { hdsl2ShdslInventoryEntry 4 }
-- 
-- hdsl2ShdslInvVendorEOCSoftwareVersion OBJECT-TYPE
--    SYNTAX      Integer32
--    MAX-ACCESS  read-only
--    STATUS      current
--    DESCRIPTION
--      "Vendor EOC version as reported in a Discovery Response
--       message."
--    ::= { hdsl2ShdslInventoryEntry 5 }
-- 
-- hdsl2ShdslInvStandardVersion OBJECT-TYPE
--    SYNTAX      Integer32
--    MAX-ACCESS  read-only
--    STATUS      current
--    DESCRIPTION
--      "Version of the HDSL2/SHDSL standard implemented, as reported
--       in an Inventory Response message."
--    ::= { hdsl2ShdslInventoryEntry 6 }
-- 
-- hdsl2ShdslInvVendorListNumber OBJECT-TYPE
--    SYNTAX      OCTET STRING(SIZE(3))
--    MAX-ACCESS  read-only
--    STATUS      current
--    DESCRIPTION
--      "Vendor list number as reported in an Inventory Response
--       message."
--    ::= { hdsl2ShdslInventoryEntry 7 }
-- 
-- hdsl2ShdslInvVendorIssueNumber OBJECT-TYPE
--    SYNTAX      OCTET STRING(SIZE(2))
--    MAX-ACCESS  read-only
--    STATUS      current
--    DESCRIPTION
--      "Vendor issue number as reported in an Inventory Response
--       message."
--    ::= { hdsl2ShdslInventoryEntry 8 }
-- 
-- hdsl2ShdslInvVendorSoftwareVersion OBJECT-TYPE
--    SYNTAX      OCTET STRING(SIZE(6))
--    MAX-ACCESS  read-only
--    STATUS      current
--    DESCRIPTION
--      "Vendor software version as reported in an Inventory Response
--       message."
--    ::= { hdsl2ShdslInventoryEntry 9 }
-- 
-- hdsl2ShdslInvEquipmentCode OBJECT-TYPE
--    SYNTAX      OCTET STRING(SIZE(10))
--    MAX-ACCESS  read-only
--    STATUS      current
--    DESCRIPTION
--      "Equipment code conforming to ANSI T1.213, Coded Identification
--       of Equipment Entities."
--    ::= { hdsl2ShdslInventoryEntry 10 }
-- 
-- hdsl2ShdslInvVendorOther OBJECT-TYPE
--    SYNTAX      OCTET STRING(SIZE(12))
--    MAX-ACCESS  read-only
--    STATUS      current
--    DESCRIPTION
--      "Other vendor information as reported in an Inventory Response
--       message."
--    ::= { hdsl2ShdslInventoryEntry 11 }
-- 
hdsl2ShdslInvTransmissionModeCapability OBJECT-TYPE
   SYNTAX      Hdsl2ShdslTransmissionModeType
   MAX-ACCESS  read-only
   STATUS      current
   DESCRIPTION
     "Contains the transmission mode capability of the SHDSL unit."
   ::= { hdsl2ShdslInventoryEntry 12 }

-- Segment Endpoint Configuration Group
--
-- 
hdsl2ShdslEndpointConfTable OBJECT-TYPE
   SYNTAX      SEQUENCE OF Hdsl2ShdslEndpointConfEntry
   MAX-ACCESS  not-accessible
   STATUS      current
   DESCRIPTION
     "This table supports configuration parameters for segment
      endpoints in a HDSL2/SHDSL line.  As this table is indexed
      by ifIndex, it MUST be maintained in a persistent manner."
   ::= { hdsl2ShdslMibObjects 4 }

hdsl2ShdslEndpointConfEntry OBJECT-TYPE
   SYNTAX      Hdsl2ShdslEndpointConfEntry
   MAX-ACCESS  not-accessible
   STATUS      current
   DESCRIPTION
     "An entry in the hdsl2ShdslEndpointConfTable.  Each entry
      represents a single segment endpoint in a HDSL2/SHDSL line.
      It is indexed by the ifIndex of the HDSL2/SHDSL line, the
      UnitId of the associated unit, the side of the unit, and the
      wire-pair of the associated modem."
   INDEX { ifIndex, hdsl2ShdslInvIndex, hdsl2ShdslEndpointSide,
           hdsl2ShdslEndpointWirePair}
   ::= { hdsl2ShdslEndpointConfTable 1 }

Hdsl2ShdslEndpointConfEntry ::=
   SEQUENCE
   {
   hdsl2ShdslEndpointSide                   Hdsl2ShdslUnitSide,
   hdsl2ShdslEndpointWirePair               Hdsl2ShdslWirePair
--    hdsl2ShdslEndpointAlarmConfProfile       SnmpAdminString
   }

hdsl2ShdslEndpointSide OBJECT-TYPE
   SYNTAX      Hdsl2ShdslUnitSide
   MAX-ACCESS  not-accessible
   STATUS      current
   DESCRIPTION
     "The side of the unit associated with this segment endpoint -
      Network/Customer side - as per the Hdsl2ShdslUnitSide textual
      convention."
   ::= { hdsl2ShdslEndpointConfEntry 1 }

hdsl2ShdslEndpointWirePair OBJECT-TYPE
   SYNTAX      Hdsl2ShdslWirePair
   MAX-ACCESS  read-only
   STATUS      current
   DESCRIPTION
     "The wire-pair of the modem associated with this segment
      endpoint as per the Hdsl2ShdslWirePair textual convention."
   ::= { hdsl2ShdslEndpointConfEntry 2 }

-- hdsl2ShdslEndpointAlarmConfProfile OBJECT-TYPE
--    SYNTAX      SnmpAdminString (SIZE(0..32))
--    MAX-ACCESS  read-write
--    STATUS      current
--    DESCRIPTION
--      "This object configures the alarm threshold values to be used
--       for this segment endpoint.  The values are obtained from the
--       alarm configuration profile referenced by this object.  The
--       value of this object is the index of the referenced profile in
--       the hdsl2ShdslEndpointAlarmConfProfileTable, or NULL (a zero-
--       length SnmpAdminString).  If the value is a zero-length
--       SnmpAdminString, the endpoint uses the default Alarm
--       Configuration Profile for the associated span as per the
--       hdsl2ShdslSpanConfAlarmProfile object in the
--       hdsl2ShdslSpanConfTable.  The default value of this object is
--       a zero-length SnmpAdminString.
-- 
--       Any attempt to set this object to a value that is not the value
--       of the index for an active entry in the profile table,
--       hdsl2ShdslEndpointAlarmConfProfileTable, MUST be rejected."
--    ::= { hdsl2ShdslEndpointConfEntry 3 }
-- 
-- Segment Endpoint Current Status/Performance Group
--

hdsl2ShdslEndpointCurrTable OBJECT-TYPE
   SYNTAX      SEQUENCE OF Hdsl2ShdslEndpointCurrEntry
   MAX-ACCESS  not-accessible
   STATUS      current

   DESCRIPTION
     "This table contains current status and performance information
      for segment endpoints in HDSL2/SHDSL Lines.  As with other
      tables in this MIB indexed by ifIndex, entries in this table
      MUST be maintained in a persistent manner."
   ::= { hdsl2ShdslMibObjects 5 }

hdsl2ShdslEndpointCurrEntry OBJECT-TYPE
   SYNTAX      Hdsl2ShdslEndpointCurrEntry
   MAX-ACCESS  not-accessible
   STATUS      current
   DESCRIPTION
     "An entry in the hdsl2ShdslEndpointCurrTable.  Each entry
     contains status and performance information relating to a
     single segment endpoint.  It is indexed by the ifIndex of the
     HDSL2/SHDSL line, the UnitId of the associated unit, the side
     of the unit, and the wire-pair of the associated modem."
   INDEX { ifIndex, hdsl2ShdslInvIndex, hdsl2ShdslEndpointSide,
           hdsl2ShdslEndpointWirePair }
   ::= { hdsl2ShdslEndpointCurrTable 1 }

Hdsl2ShdslEndpointCurrEntry ::=
   SEQUENCE
   {
   hdsl2ShdslEndpointCurrAtn                Integer32,
   hdsl2ShdslEndpointCurrSnrMgn             Integer32,
--   hdsl2ShdslEndpointCurrStatus             BITS,
   hdsl2ShdslEndpointES                     Counter32,
   hdsl2ShdslEndpointSES                    Counter32,
   hdsl2ShdslEndpointCRCanomalies           Counter32,
   hdsl2ShdslEndpointLOSWS                  Counter32,
   hdsl2ShdslEndpointUAS                    Counter32,
   hdsl2ShdslEndpointCurr15MinTimeElapsed
                             Hdsl2ShdslPerfTimeElapsed,
   hdsl2ShdslEndpointCurr15MinES            PerfCurrentCount,
   hdsl2ShdslEndpointCurr15MinSES           PerfCurrentCount,
   hdsl2ShdslEndpointCurr15MinCRCanomalies  PerfCurrentCount,
   hdsl2ShdslEndpointCurr15MinLOSWS         PerfCurrentCount,
   hdsl2ShdslEndpointCurr15MinUAS           PerfCurrentCount,
   hdsl2ShdslEndpointCurr1DayTimeElapsed
                             Hdsl2ShdslPerfTimeElapsed,
   hdsl2ShdslEndpointCurr1DayES
                             Hdsl2ShdslPerfCurrDayCount,
   hdsl2ShdslEndpointCurr1DaySES
                             Hdsl2ShdslPerfCurrDayCount,
   hdsl2ShdslEndpointCurr1DayCRCanomalies
                             Hdsl2ShdslPerfCurrDayCount,
   hdsl2ShdslEndpointCurr1DayLOSWS
                             Hdsl2ShdslPerfCurrDayCount,
   hdsl2ShdslEndpointCurr1DayUAS
                             Hdsl2ShdslPerfCurrDayCount
   }

hdsl2ShdslEndpointCurrAtn OBJECT-TYPE
   SYNTAX      Integer32(-127..128)
   UNITS       "dB"
   MAX-ACCESS  read-only
   STATUS      current
   DESCRIPTION
     "The current loop attenuation for this endpoint as reported in
      a Network or Customer Side Performance Status message."
   REFERENCE   "HDSL2 Section 7.5.3.7; SHDSL Section 9.5.5.7"
   ::= { hdsl2ShdslEndpointCurrEntry 1 }

hdsl2ShdslEndpointCurrSnrMgn OBJECT-TYPE
   SYNTAX      Integer32(-127..128)
   UNITS       "dB"
   MAX-ACCESS  read-only
   STATUS      current
   DESCRIPTION
     "The current SNR margin for this endpoint as reported in a
      Status Response/SNR message."
   REFERENCE   "HDSL2 Section 7.5.3.7; SHDSL Section 9.5.5.7"
   ::= { hdsl2ShdslEndpointCurrEntry 2 }
-- 
-- hdsl2ShdslEndpointCurrStatus OBJECT-TYPE
--    SYNTAX      BITS
--                {
--                noDefect(0),
--                powerBackoff(1),
--                deviceFault(2),
--                dcContinuityFault(3),
--                snrMarginAlarm(4),
--                loopAttenuationAlarm(5),
--                loswFailureAlarm(6),
--                configInitFailure(7),
--                protocolInitFailure(8),
--                noNeighborPresent(9),
--                loopbackActive(10)
--                }
--    MAX-ACCESS  read-only
--    STATUS      current
--    DESCRIPTION
--      "Contains the current state of the endpoint.  This is a
--      bitmap of possible conditions. The various bit positions
--      are:
--      noDefect               There no defects on the line.
-- 
--      powerBackoff           Indicates enhanced Power Backoff.
-- 
--      deviceFault            Indicates a vendor-dependent
--                             diagnostic or self-test fault
--                             has been detected.
-- 
--      dcContinuityFault      Indicates vendor-dependent
--                             conditions that interfere with
--                             span powering such as short and
--                             open circuits.
-- 
--      snrMarginAlarm         Indicates that the SNR margin
--                             has dropped below the alarm threshold.
-- 
--      loopAttenuationAlarm   Indicates that the loop attenuation
--                             exceeds the alarm threshold.
-- 
--      loswFailureAlarm       Indicates a forward LOSW alarm.
-- 
--      configInitFailure      Endpoint failure during initialization
--                             due to paired endpoint not able to
--                             support requested configuration.
-- 
--      protocolInitFailure    Endpoint failure during initialization
--                             due to incompatible protocol used by
--                             the paired endpoint.
-- 
--      noNeighborPresent      Endpoint failure during initialization
--                             due to no activation sequence detected
--                             from paired endpoint.
-- 
--      loopbackActive         A loopback is currently active at this
--                             Segment Endpoint.
-- 
--      This is intended to supplement ifOperStatus.  Note that there
--      is a 1-1 relationship between the status bits defined in this
--      object and the notification thresholds defined elsewhere in
--      this MIB."
--    REFERENCE   "HDSL2 Section 7.5.3.7; SHDSL Section 9.5.5.7"
--    ::= { hdsl2ShdslEndpointCurrEntry 3 }

hdsl2ShdslEndpointES OBJECT-TYPE
   SYNTAX      Counter32
   UNITS       "seconds"
   MAX-ACCESS  read-only
   STATUS      current
   DESCRIPTION
     "Count of Errored Seconds (ES) on this endpoint since the xU
      was last restarted."
   REFERENCE   "HDSL2 Section 7.5.3.7; SHDSL Section 9.5.5.7"
   ::= { hdsl2ShdslEndpointCurrEntry 4 }

hdsl2ShdslEndpointSES OBJECT-TYPE
   SYNTAX       Counter32
   UNITS        "seconds"
   MAX-ACCESS   read-only
   STATUS       current
   DESCRIPTION
     "Count of Severely Errored Seconds (SES) on this endpoint
      since the xU was last restarted."
   REFERENCE   "HDSL2 Section 7.5.3.7; SHDSL Section 9.5.5.7"
   ::= { hdsl2ShdslEndpointCurrEntry 5 }

hdsl2ShdslEndpointCRCanomalies OBJECT-TYPE
   SYNTAX       Counter32
   UNITS        "detected CRC Anomalies"
   MAX-ACCESS   read-only
   STATUS       current
   DESCRIPTION
     "Count of CRC anomalies on this endpoint since the xU was
      last restarted."
   REFERENCE   "HDSL2 Section 7.5.3.7; SHDSL Section 9.5.5.7"
   ::= { hdsl2ShdslEndpointCurrEntry 6 }

hdsl2ShdslEndpointLOSWS OBJECT-TYPE
   SYNTAX       Counter32
   UNITS        "seconds"
   MAX-ACCESS   read-only
   STATUS       current
   DESCRIPTION
     "Count of Loss of Sync Word (LOSW) Seconds on this endpoint
      since the xU was last restarted."
   REFERENCE   "HDSL2 Section 7.5.3.7; SHDSL Section 9.5.5.7"
   ::= { hdsl2ShdslEndpointCurrEntry 7 }

hdsl2ShdslEndpointUAS OBJECT-TYPE
   SYNTAX       Counter32
   UNITS        "seconds"
   MAX-ACCESS   read-only
   STATUS       current
   DESCRIPTION
     "Count of Unavailable Seconds (UAS) on this endpoint since
      the xU was last restarted."
   REFERENCE   "HDSL2 Section 7.5.3.7; SHDSL Section 9.5.5.7"
   ::= { hdsl2ShdslEndpointCurrEntry 8 }

hdsl2ShdslEndpointCurr15MinTimeElapsed OBJECT-TYPE
   SYNTAX       Hdsl2ShdslPerfTimeElapsed
   UNITS        "seconds"
   MAX-ACCESS   read-only
   STATUS       current
   DESCRIPTION
     "Total elapsed seconds in the current 15-minute interval."
   ::= { hdsl2ShdslEndpointCurrEntry 9 }

hdsl2ShdslEndpointCurr15MinES OBJECT-TYPE
   SYNTAX       PerfCurrentCount
   UNITS        "seconds"
   MAX-ACCESS   read-only
   STATUS       current
   DESCRIPTION
     "Count of Errored Seconds (ES) in the current 15-minute
      interval."
   REFERENCE   "HDSL2 Section 7.5.3.7; SHDSL Section 9.5.5.7"
   ::= { hdsl2ShdslEndpointCurrEntry 10 }

hdsl2ShdslEndpointCurr15MinSES OBJECT-TYPE
   SYNTAX       PerfCurrentCount
   UNITS        "seconds"
   MAX-ACCESS   read-only
   STATUS       current
   DESCRIPTION
     "Count of Severely Errored Seconds (SES) in the current
      15-minute interval."
   REFERENCE   "HDSL2 Section 7.5.3.7; SHDSL Section 9.5.5.7"
   ::= { hdsl2ShdslEndpointCurrEntry 11 }

hdsl2ShdslEndpointCurr15MinCRCanomalies OBJECT-TYPE
   SYNTAX       PerfCurrentCount
   UNITS        "detected CRC Anomalies"
   MAX-ACCESS   read-only
   STATUS       current
   DESCRIPTION
     "Count of CRC anomalies in the current 15-minute interval."
   REFERENCE   "HDSL2 Section 7.5.3.7; SHDSL Section 9.5.5.7"
   ::= { hdsl2ShdslEndpointCurrEntry 12 }

hdsl2ShdslEndpointCurr15MinLOSWS OBJECT-TYPE
   SYNTAX       PerfCurrentCount
   UNITS        "seconds"
   MAX-ACCESS   read-only
   STATUS       current
   DESCRIPTION
     "Count of Loss of Sync Word (LOSW) Seconds in the current
      15-minute interval."
   REFERENCE   "HDSL2 Section 7.5.3.7; SHDSL Section 9.5.5.7"
   ::= { hdsl2ShdslEndpointCurrEntry 13 }

hdsl2ShdslEndpointCurr15MinUAS OBJECT-TYPE
   SYNTAX       PerfCurrentCount
   UNITS        "seconds"
   MAX-ACCESS   read-only
   STATUS       current
   DESCRIPTION
     "Count of Unavailable Seconds (UAS) in the current 15-minute
      interval."
   REFERENCE   "HDSL2 Section 7.5.3.7; SHDSL Section 9.5.5.7"
   ::= { hdsl2ShdslEndpointCurrEntry 14 }

hdsl2ShdslEndpointCurr1DayTimeElapsed OBJECT-TYPE
   SYNTAX       Hdsl2ShdslPerfTimeElapsed
   UNITS        "seconds"
   MAX-ACCESS   read-only
   STATUS       current
   DESCRIPTION
     "Number of seconds that have elapsed since the beginning of
      the current 1-day interval."
   ::= { hdsl2ShdslEndpointCurrEntry 15 }

hdsl2ShdslEndpointCurr1DayES OBJECT-TYPE
   SYNTAX       Hdsl2ShdslPerfCurrDayCount
   UNITS        "seconds"
   MAX-ACCESS   read-only
   STATUS       current
   DESCRIPTION
     "Count of Errored Seconds (ES) during the current day as
      measured by hdsl2ShdslEndpointCurr1DayTimeElapsed."
   REFERENCE   "HDSL2 Section 7.5.3.7; SHDSL Section 9.5.5.7"
   ::= { hdsl2ShdslEndpointCurrEntry 16 }

hdsl2ShdslEndpointCurr1DaySES OBJECT-TYPE
   SYNTAX       Hdsl2ShdslPerfCurrDayCount
   UNITS        "seconds"
   MAX-ACCESS   read-only
   STATUS       current
   DESCRIPTION
     "Count of Severely Errored Seconds (SES) during the current
      day as measured by hdsl2ShdslEndpointCurr1DayTimeElapsed."
   REFERENCE   "HDSL2 Section 7.5.3.7; SHDSL Section 9.5.5.7"
   ::= { hdsl2ShdslEndpointCurrEntry 17 }

hdsl2ShdslEndpointCurr1DayCRCanomalies OBJECT-TYPE
   SYNTAX       Hdsl2ShdslPerfCurrDayCount
   UNITS        "detected CRC Anomalies"
   MAX-ACCESS   read-only
   STATUS       current
   DESCRIPTION
     "Count of CRC anomalies during the current day as measured
      by hdsl2ShdslEndpointCurr1DayTimeElapsed."
   REFERENCE   "HDSL2 Section 7.5.3.7; SHDSL Section 9.5.5.7"
   ::= { hdsl2ShdslEndpointCurrEntry 18 }

hdsl2ShdslEndpointCurr1DayLOSWS OBJECT-TYPE
   SYNTAX       Hdsl2ShdslPerfCurrDayCount
   UNITS        "seconds"
   MAX-ACCESS   read-only
   STATUS       current
   DESCRIPTION
     "Count of Loss of Sync Word (LOSW) Seconds during the current
      day as measured by hdsl2ShdslEndpointCurr1DayTimeElapsed."
   REFERENCE   "HDSL2 Section 7.5.3.7; SHDSL Section 9.5.5.7"
   ::= { hdsl2ShdslEndpointCurrEntry 19 }

hdsl2ShdslEndpointCurr1DayUAS OBJECT-TYPE
   SYNTAX       Hdsl2ShdslPerfCurrDayCount
   UNITS        "seconds"
   MAX-ACCESS   read-only
   STATUS       current
   DESCRIPTION
     "Count of Unavailable Seconds (UAS) during the current day as
      measured by hdsl2ShdslEndpointCurr1DayTimeElapsed."
   REFERENCE   "HDSL2 Section 7.5.3.7; SHDSL Section 9.5.5.7"
   ::= { hdsl2ShdslEndpointCurrEntry 20 }

-- Segment Endpoint 15-Minute Interval Status/Performance Group
--

hdsl2Shdsl15MinIntervalTable OBJECT-TYPE
   SYNTAX      SEQUENCE OF Hdsl2Shdsl15MinIntervalEntry
   MAX-ACCESS  not-accessible
   STATUS      current
   DESCRIPTION
     "This table provides one row for each HDSL2/SHDSL endpoint
      performance data collection interval.  This table contains
      live data from equipment.  As such, it is NOT persistent."
   ::= { hdsl2ShdslMibObjects 6 }

hdsl2Shdsl15MinIntervalEntry OBJECT-TYPE
   SYNTAX      Hdsl2Shdsl15MinIntervalEntry
   MAX-ACCESS  not-accessible
   STATUS      current
   DESCRIPTION
     "An entry in the hdsl2Shdsl15MinIntervalTable."
   INDEX { ifIndex, hdsl2ShdslInvIndex, hdsl2ShdslEndpointSide,
           hdsl2ShdslEndpointWirePair, hdsl2Shdsl15MinIntervalNumber}
   ::= { hdsl2Shdsl15MinIntervalTable 1 }

Hdsl2Shdsl15MinIntervalEntry ::=
   SEQUENCE
   {
   hdsl2Shdsl15MinIntervalNumber         Unsigned32,
   hdsl2Shdsl15MinIntervalES             PerfIntervalCount,
   hdsl2Shdsl15MinIntervalSES            PerfIntervalCount,
   hdsl2Shdsl15MinIntervalCRCanomalies   PerfIntervalCount,
   hdsl2Shdsl15MinIntervalLOSWS          PerfIntervalCount,
   hdsl2Shdsl15MinIntervalUAS            PerfIntervalCount
   }

hdsl2Shdsl15MinIntervalNumber OBJECT-TYPE
   SYNTAX      Unsigned32(1..96)
   MAX-ACCESS  not-accessible
   STATUS      current
   DESCRIPTION
     "Performance Data Interval number. 1 is the the most recent
      previous interval; interval 96 is 24 hours ago. Intervals
      2..96 are optional."
   ::= { hdsl2Shdsl15MinIntervalEntry 1 }

hdsl2Shdsl15MinIntervalES OBJECT-TYPE
   SYNTAX      PerfIntervalCount
   UNITS       "seconds"
   MAX-ACCESS  read-only
   STATUS      current
   DESCRIPTION
     "Count of Errored Seconds (ES) during the interval."
   REFERENCE   "HDSL2 Section 7.5.3.7; SHDSL Section 9.5.5.7"
   ::= { hdsl2Shdsl15MinIntervalEntry 2 }

hdsl2Shdsl15MinIntervalSES OBJECT-TYPE
   SYNTAX      PerfIntervalCount
   UNITS       "seconds"
   MAX-ACCESS  read-only
   STATUS      current
   DESCRIPTION
     "Count of Severely Errored Seconds (SES) during the interval."
   REFERENCE   "HDSL2 Section 7.5.3.7; SHDSL Section 9.5.5.7"
   ::= { hdsl2Shdsl15MinIntervalEntry 3 }

hdsl2Shdsl15MinIntervalCRCanomalies OBJECT-TYPE
   SYNTAX      PerfIntervalCount
   UNITS       "detected CRC Anomalies"
   MAX-ACCESS  read-only
   STATUS      current
   DESCRIPTION
     "Count of CRC anomalies during the interval."
   REFERENCE   "HDSL2 Section 7.5.3.7; SHDSL Section 9.5.5.7"
   ::= { hdsl2Shdsl15MinIntervalEntry 4 }

hdsl2Shdsl15MinIntervalLOSWS OBJECT-TYPE
   SYNTAX      PerfIntervalCount
   UNITS       "seconds"
   MAX-ACCESS  read-only
   STATUS      current
   DESCRIPTION
     "Count of Loss of Sync Word (LOSW) Seconds during the
      interval."
   REFERENCE   "HDSL2 Section 7.5.3.7; SHDSL Section 9.5.5.7"
   ::= { hdsl2Shdsl15MinIntervalEntry 5 }

hdsl2Shdsl15MinIntervalUAS OBJECT-TYPE
   SYNTAX      PerfIntervalCount
   UNITS       "seconds"
   MAX-ACCESS  read-only
   STATUS      current
   DESCRIPTION
     "Count of Unavailable Seconds (UAS) during the interval."
   REFERENCE   "HDSL2 Section 7.5.3.7; SHDSL Section 9.5.5.7"
   ::= { hdsl2Shdsl15MinIntervalEntry 6 }

-- Segment Endpoint 1-Day Interval Status/Performance Group
--

hdsl2Shdsl1DayIntervalTable OBJECT-TYPE
   SYNTAX      SEQUENCE OF Hdsl2Shdsl1DayIntervalEntry
   MAX-ACCESS  not-accessible
   STATUS      current
   DESCRIPTION
     "This table provides one row for each HDSL2/SHDSL endpoint
      performance data collection interval.  This table contains
      live data from equipment.  As such, it is NOT persistent."
   ::= { hdsl2ShdslMibObjects 7 }

hdsl2Shdsl1DayIntervalEntry OBJECT-TYPE
   SYNTAX      Hdsl2Shdsl1DayIntervalEntry
   MAX-ACCESS  not-accessible
   STATUS      current

   DESCRIPTION
     "An entry in the hdsl2Shdsl1DayIntervalTable."
   INDEX { ifIndex, hdsl2ShdslInvIndex, hdsl2ShdslEndpointSide,
           hdsl2ShdslEndpointWirePair, hdsl2Shdsl1DayIntervalNumber }
   ::= { hdsl2Shdsl1DayIntervalTable 1 }

Hdsl2Shdsl1DayIntervalEntry ::=
   SEQUENCE
   {
   hdsl2Shdsl1DayIntervalNumber         Unsigned32,
   hdsl2Shdsl1DayIntervalMoniSecs       Hdsl2ShdslPerfTimeElapsed,
   hdsl2Shdsl1DayIntervalES             Hdsl2Shdsl1DayIntervalCount,
   hdsl2Shdsl1DayIntervalSES            Hdsl2Shdsl1DayIntervalCount,
   hdsl2Shdsl1DayIntervalCRCanomalies   Hdsl2Shdsl1DayIntervalCount,
   hdsl2Shdsl1DayIntervalLOSWS          Hdsl2Shdsl1DayIntervalCount,
   hdsl2Shdsl1DayIntervalUAS            Hdsl2Shdsl1DayIntervalCount
   }

hdsl2Shdsl1DayIntervalNumber OBJECT-TYPE
   SYNTAX      Unsigned32(1..30)
   MAX-ACCESS  not-accessible
   STATUS      current
   DESCRIPTION
     "History Data Interval number. Interval 1 is the the most
      recent previous day; interval 30 is 30 days ago. Intervals
      2..30 are optional."
   ::= { hdsl2Shdsl1DayIntervalEntry 1 }

hdsl2Shdsl1DayIntervalMoniSecs OBJECT-TYPE
   SYNTAX       Hdsl2ShdslPerfTimeElapsed
   UNITS        "seconds"
   MAX-ACCESS   read-only
   STATUS       current
   DESCRIPTION
     "The amount of time in the 1-day interval over which the
      performance monitoring information is actually counted.
      This value will be the same as the interval duration except
      in a situation where performance monitoring data could not
      be collected for any reason."
   ::= { hdsl2Shdsl1DayIntervalEntry 2 }

hdsl2Shdsl1DayIntervalES OBJECT-TYPE
   SYNTAX       Hdsl2Shdsl1DayIntervalCount
   UNITS        "seconds"
   MAX-ACCESS   read-only
   STATUS       current
   DESCRIPTION
     "Count of Errored Seconds (ES) during the 1-day interval as
      measured by hdsl2Shdsl1DayIntervalMoniSecs."
   REFERENCE   "HDSL2 Section 7.5.3.7; SHDSL Section 9.5.5.7"
   ::= { hdsl2Shdsl1DayIntervalEntry 3 }

hdsl2Shdsl1DayIntervalSES OBJECT-TYPE
   SYNTAX       Hdsl2Shdsl1DayIntervalCount
   UNITS        "seconds"
   MAX-ACCESS   read-only
   STATUS       current
   DESCRIPTION
     "Count of Severely Errored Seconds (SES) during the 1-day
      interval as measured by hdsl2Shdsl1DayIntervalMoniSecs."
   REFERENCE   "HDSL2 Section 7.5.3.7; SHDSL Section 9.5.5.7"
   ::= { hdsl2Shdsl1DayIntervalEntry 4 }

hdsl2Shdsl1DayIntervalCRCanomalies OBJECT-TYPE
   SYNTAX       Hdsl2Shdsl1DayIntervalCount
   UNITS        "detected CRC Anomalies"
   MAX-ACCESS   read-only
   STATUS       current
   DESCRIPTION
     "Count of CRC anomalies during the 1-day interval as
      measured by hdsl2Shdsl1DayIntervalMoniSecs."
   REFERENCE   "HDSL2 Section 7.5.3.7; SHDSL Section 9.5.5.7"
   ::= { hdsl2Shdsl1DayIntervalEntry 5 }

hdsl2Shdsl1DayIntervalLOSWS OBJECT-TYPE
   SYNTAX       Hdsl2Shdsl1DayIntervalCount
   UNITS        "seconds"
   MAX-ACCESS   read-only
   STATUS       current
   DESCRIPTION
     "Count of Loss of Sync Word (LOSW) Seconds during the 1-day
      interval as measured by hdsl2Shdsl1DayIntervalMoniSecs."
   REFERENCE   "HDSL2 Section 7.5.3.7; SHDSL Section 9.5.5.7"
   ::= { hdsl2Shdsl1DayIntervalEntry 6 }

hdsl2Shdsl1DayIntervalUAS OBJECT-TYPE
   SYNTAX       Hdsl2Shdsl1DayIntervalCount
   UNITS        "seconds"
   MAX-ACCESS   read-only
   STATUS       current
   DESCRIPTION
     "Count of Unavailable Seconds (UAS) during the 1-day interval
      as measured by hdsl2Shdsl1DayIntervalMoniSecs."
   REFERENCE   "HDSL2 Section 7.5.3.7; SHDSL Section 9.5.5.7"
   ::= { hdsl2Shdsl1DayIntervalEntry 7 }


-- Maintenance Group
--
-- 
-- hdsl2ShdslEndpointMaintTable OBJECT-TYPE
--    SYNTAX      SEQUENCE OF Hdsl2ShdslEndpointMaintEntry
--    MAX-ACCESS  not-accessible
--    STATUS      current
--    DESCRIPTION
--      "This table supports maintenance operations (eg. loopbacks)
--       to be performed on HDSL2/SHDSL segment endpoints.  This table
--       contains live data from equipment.  As such, it is NOT
--       persistent."
--    ::= { hdsl2ShdslMibObjects 8 }
-- 
-- hdsl2ShdslEndpointMaintEntry OBJECT-TYPE
--    SYNTAX      Hdsl2ShdslEndpointMaintEntry
--    MAX-ACCESS  not-accessible
--    STATUS      current
--    DESCRIPTION
--      "An entry in the hdsl2ShdslEndpointMaintTable.  Each entry
--       corresponds to a single segment endpoint, and is indexed by the
--       ifIndex of the HDSL2/SHDSL line, the UnitId of the associated
--       unit and the side of the unit."
--    INDEX { ifIndex, hdsl2ShdslInvIndex, hdsl2ShdslEndpointSide }
--    ::= { hdsl2ShdslEndpointMaintTable 1 }
-- 
-- Hdsl2ShdslEndpointMaintEntry ::=
--    SEQUENCE
--    {
--    hdsl2ShdslMaintLoopbackConfig      INTEGER,
--    hdsl2ShdslMaintTipRingReversal     INTEGER,
--    hdsl2ShdslMaintPowerBackOff        INTEGER,
--    hdsl2ShdslMaintSoftRestart         INTEGER
--    }
-- 
-- hdsl2ShdslMaintLoopbackConfig OBJECT-TYPE
--    SYNTAX      INTEGER
--                {
--                noLoopback(1),
--                normalLoopback(2),
--                specialLoopback(3)
--                }
--    MAX-ACCESS  read-write
--    STATUS      current
--    DESCRIPTION
--      "This object controls configuration of loopbacks for the
--       associated segment endpoint.  The status of the loopback
--       is obtained via the hdsl2ShdslEndpointCurrStatus object."
--    ::= { hdsl2ShdslEndpointMaintEntry 1 }
-- 
-- hdsl2ShdslMaintTipRingReversal OBJECT-TYPE
--    SYNTAX      INTEGER
--                {
--                normal(1),
--                reversed(2)
--                }
--    MAX-ACCESS  read-only
--    STATUS      current
--    DESCRIPTION
--      "This object indicates the state of the tip/ring pair at the
--       associated segment endpoint."
--    ::= { hdsl2ShdslEndpointMaintEntry 2 }
-- 
-- hdsl2ShdslMaintPowerBackOff OBJECT-TYPE
--    SYNTAX      INTEGER
--                {
--                default(1),
--                enhanced(2)
--                }
--    MAX-ACCESS  read-write
--    STATUS      current
--    DESCRIPTION
--      "This object configures the receiver at the associated
--       segment endpoint to operate in default or enhanced power
--       backoff mode."
--    ::= { hdsl2ShdslEndpointMaintEntry 3 }
-- 
-- hdsl2ShdslMaintSoftRestart OBJECT-TYPE
--    SYNTAX      INTEGER
--                {
--                ready(1),
--                restart(2)
--                }
--    MAX-ACCESS  read-write
--    STATUS      current
--    DESCRIPTION
--      "This object enables the manager to trigger a soft restart
--       of the modem at the associated segment endpoint.  The manager
--       may only set this object to the 'restart(2)' value, which
--       initiates a restart.  The agent will perform a restart after
--       approximately 5 seconds.  Following the 5 second period, the
--       agent will restore the object to the 'ready(1)' state."
--    ::= { hdsl2ShdslEndpointMaintEntry 4 }
-- 
-- hdsl2ShdslUnitMaintTable OBJECT-TYPE
--    SYNTAX      SEQUENCE OF Hdsl2ShdslUnitMaintEntry
--    MAX-ACCESS  not-accessible
--    STATUS      current
--    DESCRIPTION
--      "This table supports maintenance operations for units in a
--       HDSL2/SHDSL line.  Entries in this table MUST be maintained
--       in a persistent manner."
--    ::= { hdsl2ShdslMibObjects 9 }
-- 
-- hdsl2ShdslUnitMaintEntry OBJECT-TYPE
--    SYNTAX      Hdsl2ShdslUnitMaintEntry
--    MAX-ACCESS  not-accessible
--    STATUS      current
--    DESCRIPTION
--      "An entry in the hdsl2ShdslUnitMaintTable.  Each entry
--       corresponds to a single unit, and is indexed by the ifIndex
--       of the HDSL2/SHDSL line and the UnitId of the associated
--       unit."
--    INDEX { ifIndex, hdsl2ShdslInvIndex  }
--    ::= { hdsl2ShdslUnitMaintTable 1 }
-- 
-- Hdsl2ShdslUnitMaintEntry ::=
--    SEQUENCE
--    {
--    hdsl2ShdslMaintLoopbackTimeout     Integer32,
--    hdsl2ShdslMaintUnitPowerSource     INTEGER
--    }
-- 
-- hdsl2ShdslMaintLoopbackTimeout OBJECT-TYPE
--    SYNTAX      Integer32(0..4095)
--    UNITS       "minutes"
--    MAX-ACCESS  read-write
--    STATUS      current
--    DESCRIPTION
--      "This object configures the timeout value for loopbacks
--       initiated at segments endpoints contained in the associated
--       unit.  A value of 0 disables the timeout."
--    ::= { hdsl2ShdslUnitMaintEntry 1 }
-- 
-- hdsl2ShdslMaintUnitPowerSource OBJECT-TYPE
--    SYNTAX      INTEGER
--                {
--                local(1),
--                span(2)
--                }
--    MAX-ACCESS  read-only
--    STATUS      current
--    DESCRIPTION
--      "This object indicates the DC power source being used by the
--       associated unit."
--    ::= { hdsl2ShdslUnitMaintEntry 2 }
-- 
-- Span Configuration Profile Group
--

hdsl2ShdslSpanConfProfileTable OBJECT-TYPE
   SYNTAX      SEQUENCE OF Hdsl2ShdslSpanConfProfileEntry
   MAX-ACCESS  not-accessible
   STATUS      current
   DESCRIPTION
     "This table supports definitions of span configuration
      profiles for SHDSL lines.  HDSL2 does not support these
      configuration options.  This table MUST be maintained
      in a persistent manner."
   ::= { hdsl2ShdslMibObjects 10 }

hdsl2ShdslSpanConfProfileEntry OBJECT-TYPE
   SYNTAX      Hdsl2ShdslSpanConfProfileEntry
   MAX-ACCESS  not-accessible
   STATUS      current
   DESCRIPTION
     "Each entry corresponds to a single span configuration
      profile.  Each profile contains a set of span configuration
      parameters.  The configuration parameters in a profile are
      applied to those lines referencing that profile (see the
      hdsl2ShdslSpanConfProfile object).  Profiles may be
      created/deleted using the row creation/deletion mechanism
      via hdsl2ShdslSpanConfProfileRowStatus.  If an active
      entry is referenced in hdsl2ShdslSpanConfProfile, the
      entry MUST remain active until all references are removed."
   INDEX { IMPLIED hdsl2ShdslSpanConfProfileName }
   ::= { hdsl2ShdslSpanConfProfileTable 1 }

Hdsl2ShdslSpanConfProfileEntry ::=
   SEQUENCE
   {
   hdsl2ShdslSpanConfProfileName               SnmpAdminString,
   hdsl2ShdslSpanConfWireInterface             INTEGER,
   hdsl2ShdslSpanConfMinLineRate               Unsigned32,
   hdsl2ShdslSpanConfMaxLineRate               Unsigned32,
   hdsl2ShdslSpanConfPSD                       INTEGER,
   hdsl2ShdslSpanConfTransmissionMode
                                   Hdsl2ShdslTransmissionModeType,
   hdsl2ShdslSpanConfRemoteEnabled             INTEGER,
   hdsl2ShdslSpanConfPowerFeeding              INTEGER,
   hdsl2ShdslSpanConfCurrCondTargetMarginDown  Integer32,
   hdsl2ShdslSpanConfWorstCaseTargetMarginDown Integer32,
   hdsl2ShdslSpanConfCurrCondTargetMarginUp    Integer32,
   hdsl2ShdslSpanConfWorstCaseTargetMarginUp   Integer32,
   hdsl2ShdslSpanConfUsedTargetMargins         BITS,
   hdsl2ShdslSpanConfReferenceClock
                                   Hdsl2ShdslClockReferenceType,
   hdsl2ShdslSpanConfLineProbeEnable           INTEGER,
   hdsl2ShdslSpanConfProfileRowStatus          RowStatus
   }

hdsl2ShdslSpanConfProfileName OBJECT-TYPE
   SYNTAX      SnmpAdminString (SIZE(1..32))
   MAX-ACCESS  not-accessible
   STATUS      current
   DESCRIPTION
     "This object is the unique index associated with this profile.
      Entries in this table are referenced via the object
      hdsl2ShdslSpanConfProfile in Hdsl2ShdslSpanConfEntry."
   ::= { hdsl2ShdslSpanConfProfileEntry 1 }

hdsl2ShdslSpanConfWireInterface OBJECT-TYPE
   SYNTAX      INTEGER
               {
               twoWire(1),
               fourWire(2)
               }
   MAX-ACCESS  read-create
   STATUS      current
   DESCRIPTION
     "This object configures the two-wire or optional four-wire
      operation for SHDSL Lines."
   DEFVAL      { twoWire }
   ::= { hdsl2ShdslSpanConfProfileEntry 2 }

hdsl2ShdslSpanConfMinLineRate OBJECT-TYPE
   SYNTAX      Unsigned32(0..4112000)
   UNITS       "bps"
   MAX-ACCESS  read-create
   STATUS      current
   DESCRIPTION
     "This object configures the minimum transmission rate for
      the associated SHDSL Line in bits-per-second (bps).  If
      the minimum line rate equals the maximum line rate
      (hdsl2ShdslSpanMaxLineRate), the line rate is considered
      'fixed'.  If the minimum line rate is less than the maximum
      line rate, the line rate is considered 'rate-adaptive'."
   DEFVAL      { 1552000 }
   ::= { hdsl2ShdslSpanConfProfileEntry 3 }

hdsl2ShdslSpanConfMaxLineRate OBJECT-TYPE
   SYNTAX      Unsigned32(0..4112000)
   UNITS       "bps"
   MAX-ACCESS  read-create
   STATUS      current
   DESCRIPTION
     "This object configures the maximum transmission rate for
      the associated SHDSL Line in bits-per-second (bps).  If
      the minimum line rate equals the maximum line rate
      (hdsl2ShdslSpanMaxLineRate), the line rate is considered
      'fixed'.  If the minimum line rate is less than the maximum
      line rate, the line rate is considered 'rate-adaptive'."
   DEFVAL      { 1552000 }
   ::= { hdsl2ShdslSpanConfProfileEntry 4 }

hdsl2ShdslSpanConfPSD OBJECT-TYPE
   SYNTAX      INTEGER
               {
               symmetric(1),
               asymmetric(2)
               }
   MAX-ACCESS  read-create
   STATUS      current
   DESCRIPTION
     "This object configures use of symmetric/asymmetric PSD (Power
      Spectral Density) Mask for the associated SHDSL Line.  Support
      for symmetric PSD is mandatory for all supported data rates.
      Support for asymmetric PSD is optional."
   DEFVAL      { symmetric }
   ::= { hdsl2ShdslSpanConfProfileEntry 5 }

hdsl2ShdslSpanConfTransmissionMode OBJECT-TYPE
   SYNTAX      Hdsl2ShdslTransmissionModeType
   MAX-ACCESS  read-create
   STATUS      current
   DESCRIPTION
     "This object specifies the regional setting for the SHDSL
      line."
   DEFVAL      { { region1 } }
   ::= { hdsl2ShdslSpanConfProfileEntry 6 }

hdsl2ShdslSpanConfRemoteEnabled OBJECT-TYPE
   SYNTAX      INTEGER
               {
               enabled(1),
               disabled(2)
               }
   MAX-ACCESS  read-create
   STATUS      current
   DESCRIPTION
     "This object enables/disables support for remote management
      of the units in a SHDSL line from the STU-R via the EOC."
   DEFVAL      { enabled }
   ::= { hdsl2ShdslSpanConfProfileEntry 7 }

hdsl2ShdslSpanConfPowerFeeding OBJECT-TYPE
   SYNTAX      INTEGER
               {
               noPower(1),
               powerFeed(2),
               wettingCurrent(3)
               }
   MAX-ACCESS  read-create
   STATUS      current
   DESCRIPTION
     "This object enables/disables support for optional power
      feeding in a SHDSL line."
   DEFVAL      { noPower }
   ::= { hdsl2ShdslSpanConfProfileEntry 8 }

hdsl2ShdslSpanConfCurrCondTargetMarginDown OBJECT-TYPE
   SYNTAX      Integer32(-10..21)
   UNITS       "dB"
   MAX-ACCESS  read-create
   STATUS      current
   DESCRIPTION
     "This object specifies the downstream current condition target
      SNR margin for a SHDSL line.  The SNR margin is the difference
      between the desired SNR and the actual SNR.  Target SNR margin
      is the desired SNR margin for a unit."
   DEFVAL      { 0 }
   ::= { hdsl2ShdslSpanConfProfileEntry 9 }

hdsl2ShdslSpanConfWorstCaseTargetMarginDown OBJECT-TYPE
   SYNTAX      Integer32(-10..21)
   UNITS       "dB"
   MAX-ACCESS  read-create
   STATUS      current
   DESCRIPTION
     "This object specifies the downstream worst case target SNR
      margin for a SHDSL line.  The SNR margin is the difference
      between the desired SNR and the actual SNR.  Target SNR
      margin is the desired SNR margin for a unit."
   DEFVAL      { 0 }
   ::= { hdsl2ShdslSpanConfProfileEntry 10 }

hdsl2ShdslSpanConfCurrCondTargetMarginUp OBJECT-TYPE
   SYNTAX      Integer32(-10..21)
   UNITS       "dB"
   MAX-ACCESS  read-create
   STATUS      current
   DESCRIPTION
     "This object specifies the upstream current condition target
      SNR margin for a SHDSL line.  The SNR margin is the difference
      between the desired SNR and the actual SNR.  Target SNR margin
      is the desired SNR margin for a unit."
   DEFVAL      { 0 }
   ::= { hdsl2ShdslSpanConfProfileEntry 11 }

hdsl2ShdslSpanConfWorstCaseTargetMarginUp OBJECT-TYPE
   SYNTAX      Integer32(-10..21)
   UNITS       "dB"
   MAX-ACCESS  read-create
   STATUS      current
   DESCRIPTION
     "This object specifies the upstream worst case target SNR
      margin for a SHDSL line.  The SNR margin is the difference
      between the desired SNR and the actual SNR.  Target SNR margin
      is the desired SNR margin for a unit."
   DEFVAL      { 0 }
   ::= { hdsl2ShdslSpanConfProfileEntry 12 }

hdsl2ShdslSpanConfUsedTargetMargins OBJECT-TYPE
   SYNTAX      BITS
               {
               currCondDown(0),
               worstCaseDown(1),
               currCondUp(2),
               worstCaseUp(3)
               }
   MAX-ACCESS  read-create
   STATUS      current
   DESCRIPTION
     "Contains indicates whether a target SNR margin is enabled or
      disabled.  This is a bit-map of possible settings.  The
      various bit positions are:

      currCondDown     current condition downstream target SNR
                       margin enabled

      worstCaseDown    worst case downstream target SNR margin
                       enabled

      currCondUp       current condition upstream target SNR
                       margin enabled

      worstCaseUp      worst case upstream target SNR margin
                       enabled."
   DEFVAL      { { currCondDown } }
   ::= { hdsl2ShdslSpanConfProfileEntry 13 }

hdsl2ShdslSpanConfReferenceClock OBJECT-TYPE
   SYNTAX      Hdsl2ShdslClockReferenceType
   MAX-ACCESS  read-create
   STATUS      current
   DESCRIPTION
     "This object configures the clock reference for the STU-C
     in a SHDSL Line."
   DEFVAL      { localClk }
   ::= { hdsl2ShdslSpanConfProfileEntry 14 }

hdsl2ShdslSpanConfLineProbeEnable OBJECT-TYPE
   SYNTAX      INTEGER
               {
               disable(1),
               enable(2)
               }
   MAX-ACCESS  read-create
   STATUS      current
   DESCRIPTION
     "This object enables/disables support for Line Probe of
     the units in a SHDSL line.  When Line Probe is enabled, the
     system performs Line Probing to find the best possible
     rate.  If Line probe is disabled, the rate adaptation phase
     is skipped to shorten set up time."
   DEFVAL      { disable }
   ::= { hdsl2ShdslSpanConfProfileEntry 15 }

hdsl2ShdslSpanConfProfileRowStatus OBJECT-TYPE
   SYNTAX      RowStatus
   MAX-ACCESS  read-create
   STATUS      current
   DESCRIPTION
     "This object controls creation/deletion of the associated
      entry in this table per the semantics of RowStatus.  If an
      active entry is referenced in hdsl2ShdslSpanConfProfile, the
      entry MUST remain active until all references are removed."
   ::= { hdsl2ShdslSpanConfProfileEntry 16 }

-- Segment Endpoint Alarm Configuration Profile group
--

hdsl2ShdslEndpointAlarmConfProfileTable OBJECT-TYPE
   SYNTAX      SEQUENCE OF Hdsl2ShdslEndpointAlarmConfProfileEntry
   MAX-ACCESS  not-accessible
   STATUS      current
   DESCRIPTION
     "This table supports definitions of alarm configuration
      profiles for HDSL2/SHDSL segment endpoints.  This table
      MUST be maintained in a persistent manner."
   ::= { hdsl2ShdslMibObjects 11 }

hdsl2ShdslEndpointAlarmConfProfileEntry OBJECT-TYPE
   SYNTAX      Hdsl2ShdslEndpointAlarmConfProfileEntry
   MAX-ACCESS  not-accessible
   STATUS      current
   DESCRIPTION
     "Each entry corresponds to a single alarm configuration profile.
      Each profile contains a set of parameters for setting alarm
      thresholds for various performance attributes monitored at
      HDSL2/SHDSL segment endpoints.  Profiles may be created/deleted
      using the row creation/deletion mechanism via
      hdsl2ShdslEndpointAlarmConfProfileRowStatus.  If an active
      entry is referenced in either hdsl2ShdslSpanConfAlarmProfile
      or hdsl2ShdslEndpointAlarmConfProfile, the entry MUST remain
      active until all references are removed."
   INDEX { IMPLIED hdsl2ShdslEndpointAlarmConfProfileName }
   ::= { hdsl2ShdslEndpointAlarmConfProfileTable 1 }

Hdsl2ShdslEndpointAlarmConfProfileEntry ::=
   SEQUENCE
   {
   hdsl2ShdslEndpointAlarmConfProfileName       SnmpAdminString,
   hdsl2ShdslEndpointThreshLoopAttenuation      Integer32,
   hdsl2ShdslEndpointThreshSNRMargin            Integer32,
   hdsl2ShdslEndpointThreshES
               Hdsl2ShdslPerfIntervalThreshold,
   hdsl2ShdslEndpointThreshSES
               Hdsl2ShdslPerfIntervalThreshold,
   hdsl2ShdslEndpointThreshCRCanomalies         Integer32,
   hdsl2ShdslEndpointThreshLOSWS
               Hdsl2ShdslPerfIntervalThreshold,
   hdsl2ShdslEndpointThreshUAS
               Hdsl2ShdslPerfIntervalThreshold,
   hdsl2ShdslEndpointAlarmConfProfileRowStatus  RowStatus
   }

hdsl2ShdslEndpointAlarmConfProfileName OBJECT-TYPE
   SYNTAX      SnmpAdminString (SIZE(1..32))
   MAX-ACCESS  not-accessible
   STATUS      current
   DESCRIPTION
     "This object is the unique index associated with this profile."
   ::= { hdsl2ShdslEndpointAlarmConfProfileEntry 1 }

hdsl2ShdslEndpointThreshLoopAttenuation OBJECT-TYPE
   SYNTAX      Integer32(-127..128)
   UNITS       "dB"
   MAX-ACCESS  read-create
   STATUS      current
   DESCRIPTION
     "This object configures the loop attenuation alarm threshold.
      When the current value of hdsl2ShdslEndpointCurrAtn reaches
      or exceeds this threshold, a hdsl2ShdslLoopAttenCrossing
      MAY be generated."
   DEFVAL      { 0 }
   ::= { hdsl2ShdslEndpointAlarmConfProfileEntry 2 }

hdsl2ShdslEndpointThreshSNRMargin OBJECT-TYPE
   SYNTAX      Integer32(-127..128)
   UNITS       "dB"
   MAX-ACCESS  read-create
   STATUS      current
   DESCRIPTION
     "This object configures the SNR margin alarm threshold.
      When the current value of hdsl2ShdslEndpointCurrSnrMgn
      reaches or drops below this threshold, a
      hdsl2ShdslSNRMarginCrossing MAY be generated."
   DEFVAL      { 0 }
   ::= { hdsl2ShdslEndpointAlarmConfProfileEntry 3 }

hdsl2ShdslEndpointThreshES OBJECT-TYPE
   SYNTAX      Hdsl2ShdslPerfIntervalThreshold
   UNITS       "seconds"
   MAX-ACCESS  read-create
   STATUS      current
   DESCRIPTION
     "This object configures the threshold for the number of
      errored seconds (ES) within any given 15-minute performance
      data collection interval.  If the value of errored seconds
      in a particular 15-minute collection interval reaches/
      exceeds this value, a hdsl2ShdslPerfESThresh MAY be
      generated.  At most one notification will be sent per
      interval per endpoint."
   DEFVAL      { 0 }
   ::= { hdsl2ShdslEndpointAlarmConfProfileEntry 4 }

hdsl2ShdslEndpointThreshSES OBJECT-TYPE
   SYNTAX      Hdsl2ShdslPerfIntervalThreshold
   UNITS       "seconds"
   MAX-ACCESS  read-create
   STATUS      current
   DESCRIPTION
     "This object configures the threshold for the number of
      severely errored seconds (SES) within any given 15-minute
      performance data collection interval.  If the value of
      severely errored seconds in a particular 15-minute collection
      interval reaches/exceeds this value, a hdsl2ShdslPerfSESThresh
      MAY be generated.  At most one notification will be sent per
      interval per endpoint."
   DEFVAL      { 0 }
   ::= { hdsl2ShdslEndpointAlarmConfProfileEntry 5 }

hdsl2ShdslEndpointThreshCRCanomalies OBJECT-TYPE
   SYNTAX      Integer32
   UNITS       "detected CRC Anomalies"
   MAX-ACCESS  read-create
   STATUS      current
   DESCRIPTION
     "This object configures the threshold for the number of
      CRC anomalies within any given 15-minute performance data
      collection interval.  If the value of CRC anomalies in a
      particular 15-minute collection interval reaches/exceeds
      this value, a hdsl2ShdslPerfCRCanomaliesThresh MAY be
      generated.  At most one notification will be sent per
      interval per endpoint."
   DEFVAL      { 0 }
   ::= { hdsl2ShdslEndpointAlarmConfProfileEntry 6 }

hdsl2ShdslEndpointThreshLOSWS OBJECT-TYPE
   SYNTAX      Hdsl2ShdslPerfIntervalThreshold
   UNITS       "seconds"
   MAX-ACCESS  read-create
   STATUS      current
   DESCRIPTION
     "This object configures the threshold for the number of
      Loss of Sync Word (LOSW) Seconds within any given 15-minute
      performance data collection interval.  If the value of LOSW
      in a particular 15-minute collection interval reaches/exceeds
      this value, a hdsl2ShdslPerfLOSWSThresh MAY be generated.
      At most one notification will be sent per interval per
      endpoint."
   DEFVAL      { 0 }
   ::= { hdsl2ShdslEndpointAlarmConfProfileEntry 7 }

hdsl2ShdslEndpointThreshUAS OBJECT-TYPE
   SYNTAX      Hdsl2ShdslPerfIntervalThreshold
   UNITS       "seconds"
   MAX-ACCESS  read-create
   STATUS      current
   DESCRIPTION
     "This object configures the threshold for the number of
      unavailable seconds (UAS) within any given 15-minute
      performance data collection interval.  If the value of UAS
      in a particular 15-minute collection interval reaches/exceeds
      this value, a hdsl2ShdslPerfUASThresh MAY be generated.
      At most one notification will be sent per interval per
      endpoint."
   DEFVAL      { 0 }
   ::= { hdsl2ShdslEndpointAlarmConfProfileEntry 8 }

hdsl2ShdslEndpointAlarmConfProfileRowStatus OBJECT-TYPE
   SYNTAX      RowStatus
   MAX-ACCESS  read-create
   STATUS      current
   DESCRIPTION
     "This object controls creation/deletion of the associated
      entry in this table as per the semantics of RowStatus.
      If an active entry is referenced in either
      hdsl2ShdslSpanConfAlarmProfile or
      hdsl2ShdslEndpointAlarmConfProfile, the entry MUST remain
      active until all references are removed."
   ::= { hdsl2ShdslEndpointAlarmConfProfileEntry 9 }

-- Notifications Group
--

hdsl2ShdslNotifications OBJECT IDENTIFIER ::= { hdsl2ShdslMIB 0 }

hdsl2ShdslLoopAttenCrossing NOTIFICATION-TYPE
   OBJECTS
   {
   hdsl2ShdslEndpointCurrAtn,
   hdsl2ShdslEndpointThreshLoopAttenuation
   }
   STATUS     current
   DESCRIPTION
     "This notification indicates that the loop attenuation
      threshold (as per the hdsl2ShdslEndpointThreshLoopAttenuation
      value) has been reached/exceeded for the HDSL2/SHDSL segment
      endpoint."
   ::= { hdsl2ShdslNotifications 1 }

hdsl2ShdslSNRMarginCrossing NOTIFICATION-TYPE
   OBJECTS
   {

   hdsl2ShdslEndpointCurrSnrMgn,
   hdsl2ShdslEndpointThreshSNRMargin
   }
   STATUS     current
   DESCRIPTION
     "This notification indicates that the SNR margin threshold (as
      per the hdsl2ShdslEndpointThreshSNRMargin value) has been
      reached/exceeded for the HDSL2/SHDSL segment endpoint."
   ::= { hdsl2ShdslNotifications 2 }

hdsl2ShdslPerfESThresh NOTIFICATION-TYPE
   OBJECTS
   {
   hdsl2ShdslEndpointCurr15MinES,
   hdsl2ShdslEndpointThreshES
   }
   STATUS     current
   DESCRIPTION
     "This notification indicates that the errored seconds threshold
      (as per the hdsl2ShdslEndpointThreshES value) has been reached/
      exceeded for the HDSL2/SHDSL segment endpoint."
   ::= { hdsl2ShdslNotifications 3 }

hdsl2ShdslPerfSESThresh NOTIFICATION-TYPE
   OBJECTS
   {
   hdsl2ShdslEndpointCurr15MinSES,
   hdsl2ShdslEndpointThreshSES
   }
   STATUS     current
   DESCRIPTION
     "This notification indicates that the severely errored seconds
      threshold (as per the hdsl2ShdslEndpointThreshSES value) has
      been reached/exceeded for the HDSL2/SHDSL Segment Endpoint."
   ::= { hdsl2ShdslNotifications 4 }

hdsl2ShdslPerfCRCanomaliesThresh NOTIFICATION-TYPE
   OBJECTS
   {
   hdsl2ShdslEndpointCurr15MinCRCanomalies,
   hdsl2ShdslEndpointThreshCRCanomalies
   }
   STATUS    current
   DESCRIPTION
     "This notification indicates that the CRC anomalies threshold
      (as per the hdsl2ShdslEndpointThreshCRCanomalies value) has
      been reached/exceeded for the HDSL2/SHDSL Segment Endpoint."
   ::= { hdsl2ShdslNotifications 5 }

hdsl2ShdslPerfLOSWSThresh NOTIFICATION-TYPE
   OBJECTS
   {

   hdsl2ShdslEndpointCurr15MinLOSWS,
   hdsl2ShdslEndpointThreshLOSWS
   }
   STATUS     current
   DESCRIPTION
     "This notification indicates that the LOSW seconds threshold
      (as per the hdsl2ShdslEndpointThreshLOSWS value) has been
      reached/exceeded for the HDSL2/SHDSL segment endpoint."
   ::= { hdsl2ShdslNotifications 6 }

hdsl2ShdslPerfUASThresh NOTIFICATION-TYPE
   OBJECTS
   {
   hdsl2ShdslEndpointCurr15MinUAS,
   hdsl2ShdslEndpointThreshUAS
   }
   STATUS     current
   DESCRIPTION
     "This notification indicates that the unavailable seconds
      threshold (as per the hdsl2ShdslEndpointThreshUAS value) has
      been reached/exceeded for the HDSL2/SHDSL segment endpoint."
   ::= { hdsl2ShdslNotifications 7 }

-- hdsl2ShdslSpanInvalidNumRepeaters NOTIFICATION-TYPE
--    OBJECTS
--    {
--    hdsl2ShdslSpanConfNumRepeaters
--    }
--    STATUS     current
--    DESCRIPTION
--      "This notification indicates that a mismatch has been detected
--       between the number of repeater/regenerator units configured
--       for a HDSL2/SHDSL line via the hdsl2ShdslSpanConfNumRepeaters
--       object and the actual number of repeater/regenerator units
--       discovered via the EOC."
--    ::= { hdsl2ShdslNotifications 8 }
-- 
-- hdsl2ShdslLoopbackFailure NOTIFICATION-TYPE
--    OBJECTS
--    {
--    hdsl2ShdslMaintLoopbackConfig
--    }
--    STATUS     current
--    DESCRIPTION
--      "This notification indicates that an endpoint maintenance
--       loopback command failed for an HDSL2/SHDSL segment."
--    ::= { hdsl2ShdslNotifications 9 }
-- 
-- hdsl2ShdslpowerBackoff NOTIFICATION-TYPE
--    OBJECTS
--    {
--    hdsl2ShdslEndpointCurrStatus
--    }
--    STATUS    current
--    DESCRIPTION
--      "This notification indicates that the bit setting for
--       powerBackoff in the hdsl2ShdslEndpointCurrStatus object for
--       this endpoint has changed."
--    ::= { hdsl2ShdslNotifications 10 }
-- 
-- hdsl2ShdsldeviceFault NOTIFICATION-TYPE
--    OBJECTS
--    {
--    hdsl2ShdslEndpointCurrStatus
--    }
--    STATUS    current
--    DESCRIPTION
--      "This notification indicates that the bit setting for
--       deviceFault in the hdsl2ShdslEndpointCurrStatus object for
--       this endpoint has changed."
--    ::= { hdsl2ShdslNotifications 11 }
-- 
-- hdsl2ShdsldcContinuityFault NOTIFICATION-TYPE
--    OBJECTS
--    {
--    hdsl2ShdslEndpointCurrStatus
--    }
--    STATUS    current
--    DESCRIPTION
--      "This notification indicates that the bit setting for
--       dcContinuityFault in the hdsl2ShdslEndpointCurrStatus object
--       for this endpoint has changed."
--    ::= { hdsl2ShdslNotifications 12 }
-- 
-- hdsl2ShdslconfigInitFailure NOTIFICATION-TYPE
--    OBJECTS
--    {
--    hdsl2ShdslEndpointCurrStatus
--    }
--    STATUS    current
--    DESCRIPTION
--      "This notification indicates that the bit setting for
--       configInitFailure in the hdsl2ShdslEndpointCurrStatus object
--       for this endpoint has changed."
--    ::= { hdsl2ShdslNotifications 13 }
-- 
-- hdsl2ShdslprotocolInitFailure NOTIFICATION-TYPE
--    OBJECTS
--    {
--    hdsl2ShdslEndpointCurrStatus
--    }
--    STATUS    current
--    DESCRIPTION
--      "This notification indicates that the bit setting for
--       protocolInitFailure in the hdsl2ShdslEndpointCurrStatus
--       object for this endpoint has changed."
--    ::= { hdsl2ShdslNotifications 14 }
-- 
-- hdsl2ShdslnoNeighborPresent NOTIFICATION-TYPE
--    OBJECTS
--    {
--    hdsl2ShdslEndpointCurrStatus
--    }
--    STATUS    current
--    DESCRIPTION
--      "This notification indicates that the bit setting for
--       noNeighborPresent in the hdsl2ShdslEndpointCurrStatus object
--       for this endpoint has changed."
--    ::= { hdsl2ShdslNotifications 15 }
-- 
hdsl2ShdslLocalPowerLoss NOTIFICATION-TYPE
   OBJECTS
   {
   hdsl2ShdslInvVendorID
   }
   STATUS    current
   DESCRIPTION
     "This notification indicates impending unit failure due to
      loss of local power (last gasp)."
   ::= { hdsl2ShdslNotifications 16 }

-- conformance information
--

hdsl2ShdslConformance OBJECT IDENTIFIER ::= { hdsl2ShdslMIB 3 }
hdsl2ShdslGroups      OBJECT IDENTIFIER ::=
             { hdsl2ShdslConformance 1 }
hdsl2ShdslCompliances OBJECT IDENTIFIER ::=
             { hdsl2ShdslConformance 2 }

-- agent compliance statements

hdsl2ShdslLineMibCompliance MODULE-COMPLIANCE
   STATUS  current
   DESCRIPTION
     "The section outlines compliance requirements for this MIB."
   MODULE
   MANDATORY-GROUPS
   {
   hdsl2ShdslSpanConfGroup,
   hdsl2ShdslSpanStatusGroup,
--    hdsl2ShdslInventoryGroup,
   hdsl2ShdslEndpointConfGroup,
   hdsl2ShdslEndpointCurrGroup,
   hdsl2Shdsl15MinIntervalGroup,
   hdsl2Shdsl1DayIntervalGroup,
--    hdsl2ShdslMaintenanceGroup,
   hdsl2ShdslEndpointAlarmConfGroup,
   hdsl2ShdslNotificationGroup
   }

GROUP  hdsl2ShdslInventoryShdslGroup
   DESCRIPTION
     "Support for this group is only required for implementations
     supporting SHDSL lines."

GROUP  hdsl2ShdslSpanShdslStatusGroup
   DESCRIPTION
     "Support for this group is only required for implementations
     supporting SHDSL lines."

GROUP  hdsl2ShdslSpanConfProfileGroup
   DESCRIPTION
     "Support for this group is only required for implementations
     supporting SHDSL lines."

   ::= { hdsl2ShdslCompliances 1 }

-- units of conformance
--

hdsl2ShdslSpanConfGroup OBJECT-GROUP
   OBJECTS
   {
   hdsl2ShdslSpanConfNumRepeaters,
   hdsl2ShdslSpanConfProfile,
   hdsl2ShdslSpanConfAlarmProfile
   }
   STATUS      current
   DESCRIPTION
     "This group supports objects for configuring span related
      parameters for HDSL2/SHDSL lines."
   ::= { hdsl2ShdslGroups 1 }

hdsl2ShdslSpanStatusGroup OBJECT-GROUP
   OBJECTS
   {
   hdsl2ShdslStatusNumAvailRepeaters
   }
   STATUS      current
   DESCRIPTION
     "This group supports objects for retrieving span related
      status for HDSL2/SHDSL lines."
   ::= { hdsl2ShdslGroups 2 }

hdsl2ShdslInventoryShdslGroup OBJECT-GROUP
   OBJECTS
   {
   hdsl2ShdslInvTransmissionModeCapability
   }
   STATUS      current
   DESCRIPTION
     "This group supports objects for retrieving SHDSL-specific
      inventory information."
   ::= { hdsl2ShdslGroups 3 }

hdsl2ShdslSpanShdslStatusGroup OBJECT-GROUP
   OBJECTS
   {
   hdsl2ShdslStatusMaxAttainableLineRate,
   hdsl2ShdslStatusActualLineRate,
   hdsl2ShdslStatusTransmissionModeCurrent
   }
   STATUS      current
   DESCRIPTION
     "This group supports objects for retrieving SHDSL-specific
      span related status."
   ::= { hdsl2ShdslGroups 4 }

-- hdsl2ShdslInventoryGroup OBJECT-GROUP
--    OBJECTS
--    {
--    hdsl2ShdslInvVendorID,
--    hdsl2ShdslInvVendorModelNumber,
--    hdsl2ShdslInvVendorSerialNumber,
--    hdsl2ShdslInvVendorEOCSoftwareVersion,
--    hdsl2ShdslInvStandardVersion,
--    hdsl2ShdslInvVendorListNumber,
--    hdsl2ShdslInvVendorIssueNumber,
--    hdsl2ShdslInvVendorSoftwareVersion,
--    hdsl2ShdslInvEquipmentCode,
--    hdsl2ShdslInvVendorOther
--    }
--    STATUS      current
--    DESCRIPTION
--      "This group supports objects that provide unit inventory
--       information about the units in HDSL2/SHDSL lines."
--    ::= { hdsl2ShdslGroups 5 }

hdsl2ShdslEndpointConfGroup OBJECT-GROUP
   OBJECTS
   {
   hdsl2ShdslEndpointCurrAtn
   }
   STATUS      current
   DESCRIPTION
     "This group supports objects for configuring parameters for
      segment endpoints in HDSL2/SHDSL lines."
   ::= { hdsl2ShdslGroups 6 }

hdsl2ShdslEndpointCurrGroup OBJECT-GROUP
   OBJECTS
   {
   hdsl2ShdslEndpointCurrAtn,
   hdsl2ShdslEndpointCurrSnrMgn,
--   hdsl2ShdslEndpointCurrStatus,
   hdsl2ShdslEndpointES,
   hdsl2ShdslEndpointSES,
   hdsl2ShdslEndpointCRCanomalies,
   hdsl2ShdslEndpointLOSWS,
   hdsl2ShdslEndpointUAS,
   hdsl2ShdslEndpointCurr15MinTimeElapsed,
   hdsl2ShdslEndpointCurr15MinES,
   hdsl2ShdslEndpointCurr15MinSES,
   hdsl2ShdslEndpointCurr15MinCRCanomalies,
   hdsl2ShdslEndpointCurr15MinLOSWS,
   hdsl2ShdslEndpointCurr15MinUAS,
   hdsl2ShdslEndpointCurr1DayTimeElapsed,
   hdsl2ShdslEndpointCurr1DayES,
   hdsl2ShdslEndpointCurr1DaySES,
   hdsl2ShdslEndpointCurr1DayCRCanomalies,
   hdsl2ShdslEndpointCurr1DayLOSWS,
   hdsl2ShdslEndpointCurr1DayUAS
   }
   STATUS      current
   DESCRIPTION
     "This group supports objects which provide current status and
      performance measurements relating to segment endpoints in
      HDSL2/SHDSL lines."
   ::= { hdsl2ShdslGroups 7 }

hdsl2Shdsl15MinIntervalGroup OBJECT-GROUP
   OBJECTS
   {
   hdsl2Shdsl15MinIntervalES,
   hdsl2Shdsl15MinIntervalSES,
   hdsl2Shdsl15MinIntervalCRCanomalies,
   hdsl2Shdsl15MinIntervalLOSWS,
   hdsl2Shdsl15MinIntervalUAS
   }
   STATUS      current
   DESCRIPTION
     "This group supports objects which maintain historic
      performance measurements relating to segment endpoints in
      HDSL2/SHDSL lines in 15-minute intervals."
   ::= { hdsl2ShdslGroups 8 }

hdsl2Shdsl1DayIntervalGroup OBJECT-GROUP
   OBJECTS
   {
   hdsl2Shdsl1DayIntervalMoniSecs,
   hdsl2Shdsl1DayIntervalES,
   hdsl2Shdsl1DayIntervalSES,
   hdsl2Shdsl1DayIntervalCRCanomalies,
   hdsl2Shdsl1DayIntervalLOSWS,
   hdsl2Shdsl1DayIntervalUAS
   }
   STATUS      current
   DESCRIPTION
     "This group supports objects which maintain historic
      performance measurements relating to segment endpoints in
      HDSL2/SHDSL lines in 1-day intervals."
   ::= { hdsl2ShdslGroups 9 }

-- hdsl2ShdslMaintenanceGroup OBJECT-GROUP
--    OBJECTS
--    {
--    hdsl2ShdslMaintLoopbackConfig,
--    hdsl2ShdslMaintTipRingReversal,
--    hdsl2ShdslMaintPowerBackOff,
--    hdsl2ShdslMaintSoftRestart,
--    hdsl2ShdslMaintLoopbackTimeout,
--    hdsl2ShdslMaintUnitPowerSource
--    }
--    STATUS      current
--    DESCRIPTION
--      "This group supports objects that provide support for
--       maintenance actions for HDSL2/SHDSL lines."
--    ::= { hdsl2ShdslGroups 10 }
-- 
hdsl2ShdslEndpointAlarmConfGroup OBJECT-GROUP
   OBJECTS
   {
--   hdsl2ShdslEndpointAlarmConfProfile,
   hdsl2ShdslEndpointThreshLoopAttenuation,
   hdsl2ShdslEndpointThreshSNRMargin,
   hdsl2ShdslEndpointThreshES,
   hdsl2ShdslEndpointThreshSES,
   hdsl2ShdslEndpointThreshCRCanomalies,
   hdsl2ShdslEndpointThreshLOSWS,
   hdsl2ShdslEndpointThreshUAS,
   hdsl2ShdslEndpointAlarmConfProfileRowStatus
   }
   STATUS      current
   DESCRIPTION
     "This group supports objects that allow configuration of alarm
      thresholds for various performance parameters for HDSL2/SHDSL
      lines."
   ::= { hdsl2ShdslGroups 11 }

hdsl2ShdslNotificationGroup NOTIFICATION-GROUP
   NOTIFICATIONS
   {
   hdsl2ShdslLoopAttenCrossing,
   hdsl2ShdslSNRMarginCrossing,
   hdsl2ShdslPerfESThresh,
   hdsl2ShdslPerfSESThresh,
   hdsl2ShdslPerfCRCanomaliesThresh,
   hdsl2ShdslPerfLOSWSThresh,
   hdsl2ShdslPerfUASThresh,
--   hdsl2ShdslSpanInvalidNumRepeaters,
--   hdsl2ShdslLoopbackFailure,
--   hdsl2ShdslpowerBackoff,
--   hdsl2ShdsldeviceFault,
--   hdsl2ShdsldcContinuityFault,
--   hdsl2ShdslconfigInitFailure,
--   hdsl2ShdslprotocolInitFailure,
--   hdsl2ShdslnoNeighborPresent,
   hdsl2ShdslLocalPowerLoss
   }
   STATUS      current
   DESCRIPTION
     "This group supports notifications of significant conditions
     associated with HDSL2/SHDSL lines."
   ::= { hdsl2ShdslGroups 12 }

hdsl2ShdslSpanConfProfileGroup OBJECT-GROUP
   OBJECTS
   {
   hdsl2ShdslSpanConfWireInterface,
   hdsl2ShdslSpanConfMinLineRate,
   hdsl2ShdslSpanConfMaxLineRate,
   hdsl2ShdslSpanConfPSD,
   hdsl2ShdslSpanConfTransmissionMode,
   hdsl2ShdslSpanConfRemoteEnabled,
   hdsl2ShdslSpanConfPowerFeeding,
   hdsl2ShdslSpanConfCurrCondTargetMarginDown,
   hdsl2ShdslSpanConfWorstCaseTargetMarginDown,
   hdsl2ShdslSpanConfCurrCondTargetMarginUp,
   hdsl2ShdslSpanConfWorstCaseTargetMarginUp,
   hdsl2ShdslSpanConfUsedTargetMargins,
   hdsl2ShdslSpanConfReferenceClock,
   hdsl2ShdslSpanConfLineProbeEnable,
   hdsl2ShdslSpanConfProfileRowStatus
   }
   STATUS      current
   DESCRIPTION
     "This group supports objects that constitute configuration
      profiles for configuring span related parameters in SHDSL
      lines."
   ::= { hdsl2ShdslGroups 13 }
END
