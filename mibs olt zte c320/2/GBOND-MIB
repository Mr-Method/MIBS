GBOND-MIB DEFINITIONS ::= BEGIN

     IMPORTS
       MODULE-IDENTITY, OBJECT-TYPE, NOTIFICATION-TYPE,
       Unsigned32, Gauge32, mib-2
         FROM SNMPv2-SMI         -- [RFC2578]
       TEXTUAL-CONVENTION, TruthValue, PhysAddress
         FROM SNMPv2-TC          -- [RFC2579]
       MODULE-COMPLIANCE, OBJECT-GROUP, NOTIFICATION-GROUP
         FROM SNMPv2-CONF        -- [RFC2580]
       ifIndex
         FROM IF-MIB             -- [RFC2863]
       ;

     gBondMIB MODULE-IDENTITY
       LAST-UPDATED "200809010000Z"  -- Sep 01, 2008
       ORGANIZATION "IETF ADSL MIB Working Group"
       CONTACT-INFO
         "WG charter:
           http://www.ietf.org/html.charters/adslmib-charter.html

         Mailing Lists:
           General Discussion: adslmib@ietf.org
           To Subscribe: adslmib-request@ietf.org
           In Body: subscribe your_email_address

          Chair: Menachem Dodge
         Postal: ECI Telecom, Ltd.
                 30 Hasivim St.,
                 Petach-Tikva 49517
                 Israel
          Phone: +972-3-926-8421
          EMail: menachem.dodge@ecitele.com

         Editor: Edward Beili
         Postal: Actelis Networks, Inc.
                 25 Bazel St., P.O.B. 10173
                 Petach-Tikva 10173
                 Israel
          Phone: +972-3-924-3491
          EMail: edward.beili@actelis.com

         Editor: Moti Morgenstern
         Postal: ECI Telecom
                 30 Hasivim St.
                 Petach-Tikva 49517
                 Israel
          Phone: +972-3-926-6258
          EMail: moti.morgenstern@ecitele.com

         Editor: Narendranath Nair
         Posatl: Wipro Technologies
                 Keonics Electronics City
                 Bangalore 560 100
                 India
          Phone: +91-80-2852-0408 x85338
          EMail: narendranath.nair@wipro.com"

       DESCRIPTION
         "The objects in this MIB module are used to manage the
         multi-pair bonded xDSL Interfaces, defined in ITU-T
         recommendations G.998.1, G.998.2 and G.998.3.

         This MIB module MUST be used in conjunction with a bonding
         scheme specific MIB module, that is, GBOND-ATM-MIB,
         GBOND-ETH-MIB or GBOND-TDIM-MIB.

         The following references are used throughout this MIB module:

         [G.998.1] refers to:
           ITU-T Recommendation G.998.1: 'ATM-based multi-pair bonding',
           January 2005.

         [G.998.2] refers to:
           ITU-T Recommendation G.998.2: 'Ethernet-based multi-pair
           bonding', January 2005.

         [G.998.3] refers to:
           ITU-T Recommendation G.998.3: 'Multi-pair bonding using
           time-division inverse multiplexing', January 2005.

         [WT-159] refers to:
           DSL Forum Technical Report: 'Management Framework for xDSL
           Bonding', September 2008.

         Naming Conventions:
           BCE   - Bonding Channel Entity
           CO    - Central Office
           CPE   - Customer Premises Equipment
           GBS   - Generic Bonding Sublayer
           SNR   - Signal to Noise Ratio

         Copyright (C) The IETF Trust (2008).
         This version of this MIB module is part of RFC XXXX;
         see the RFC itself for full legal notices."

       REVISION    "200809010000Z"  -- Sep 01, 2008
       DESCRIPTION "Initial version, published as RFC XXXX."

         -- EdNote: Replace XXXX with the actual RFC number &
         -- remove this note

       ::= { mib-2 2001 }

         -- EdNote: Replace ZZZ with a real OID once it is
         -- allocated & remove this note.

      -- Sections of the module
      -- Structured as recommended by [RFC4181], Appendix D

      gBondObjects     OBJECT IDENTIFIER ::= { gBondMIB 1 }

      gBondConformance OBJECT IDENTIFIER ::= { gBondMIB 2 }

      -- Groups in the module

      gBondPort        OBJECT IDENTIFIER ::= { gBondObjects 1 }

      gBondBce         OBJECT IDENTIFIER ::= { gBondObjects 2 }

      -- Textual Conventions

      GBondSchemeList ::= TEXTUAL-CONVENTION
        STATUS       current
        DESCRIPTION
          "This textual convention defines a bitmap of possible ITU-T
          G.998 (G.Bond) bonding schemes. Currently there are 3 bonding
          schemes defined: G.998.1, G.998.2 and G.998.3, identified by
          bit values g9981(1), g9982(2) and g9983(3), respectively.
          An additional value of unknown(0), can be returned as a result
          of GET operation, when an value of the object cannot be
          determined, for example a peer GBS cannot be reached or it
          does not support any kind of bonding."
        SYNTAX       BITS {
          unknown(0),
          g9981(1),
          g9982(2),
          g9983(3)
        }

      GBondScheme ::= TEXTUAL-CONVENTION
        STATUS       current
        DESCRIPTION
          "This textual convention defines ITU-T G.998 bonding scheme
          values. Possible values are:
            unknown(0) - undefined or unknown
            g9981(1)   - G.998.1 (G.Bond/ATM)
            g9982(2)   - G.998.2 (G.Bond/Ethernt)
            g9983(3)   - G.998.3 (G.Bond/TDIM)."
        SYNTAX       INTEGER {
          unknown(0),
          g9981(1),
          g9982(2),
          g9983(3)
        }


     -- Port Notifications Group

      gBondPortNotifications OBJECT IDENTIFIER ::= { gBondPort 0 }

      gBondLowUpRateCrossing NOTIFICATION-TYPE
        OBJECTS {
          -- ifIndex is not needed here since we are under specific GBS
          gBondUpDataRate,
          gBondThreshLowUpRate
        }
        STATUS      current
        DESCRIPTION
          "This notification indicates that the G.Bond port' upstream
          data rate has reached/dropped below or exceeded the low
          upstream rate threshold, specified by gBondThreshLowUpRate.

          This notification MAY be sent for the -O subtype ports
          while the port is up, on the crossing event in both
          directions: from normal (rate is above the threshold) to low
          (rate equals the threshold or below it) and from low to
          normal. This notification is not applicable to the -R
          subtypes.

          It is RECOMMENDED that a small debouncing period of 2.5 sec,
          between the detection of the condition and notification,
          is implemented to prevent simultaneous LinkUp/LinkDown and
          gBondLowUpRateCrossing notifications to be sent.

          The adaptive nature of the G.Bond technology allows the port
          to adapt itself to the changes in the copper environment,
          e.g., an impulse noise, alien crosstalk, or a
          micro-interruption may temporarily drop one or more BCEs in
          the aggregation group, causing a rate degradation of the
          aggregated G.Bond link. The dropped BCEs would then try to
          re-initialize, possibly at a lower rate than before, adjusting
          the rate to provide required target SNR margin.

          Generation of this notification is controlled by the
          gBondLowRateCrossingEnable object.

          This object maps to the WT-159 notification
          nGroupLowUpRateCrossing."
        REFERENCE
          "[WT-159] 5.5.1.24"
        ::= { gBondPortNotifications 1 }

      gBondLowDownRateCrossing NOTIFICATION-TYPE
        OBJECTS {
          -- ifIndex is not needed here since we are under specific GBS
          gBondDownDataRate,
          gBondThreshLowDownRate
        }
        STATUS      current
        DESCRIPTION
          "This notification indicates that the G.Bond port' downstream
          data rate has reached/dropped below or exceeded the low
          downstream rate threshold, specified by
          gBondThreshLowDownRate.

          This notification MAY be sent for the -O subtype ports
          while the port is up, on the crossing event in both
          directions: from normal (rate is above the threshold) to low
          (rate equals the threshold or below it) and from low to
          normal. This notification is not applicable to the -R
          subtypes.

          It is RECOMMENDED that a small debouncing period of 2.5 sec,
          between the detection of the condition and notification,
          is implemented to prevent simultaneous LinkUp/LinkDown and
          gBondLowDownRateCrossing notifications to be sent.

          The adaptive nature of the G.Bond technology allows the port
          to adapt itself to the changes in the copper environment,
          e.g., an impulse noise, alien crosstalk, or a
          micro-interruption may temporarily drop one or more BCEs in
          the aggregation group, causing a rate degradation of the
          aggregated G.Bond link. The dropped BCEs would then try to
          re-initialize, possibly at a lower rate than before,
          adjusting the rate to provide required target SNR margin.
          
          Generation of this notification is controlled by the
          gBondLowRateCrossingEnable object.

          This object maps to the WT-159 notification
          nGroupLowDownRateCrossing."
        REFERENCE
          "[WT-159] 5.5.1.25"
        ::= { gBondPortNotifications 2}

      -- G.Bond Port (GBS) group

      gBondPortConfTable OBJECT-TYPE
        SYNTAX      SEQUENCE OF GBondPortConfEntry
        MAX-ACCESS  not-accessible
        STATUS      current
        DESCRIPTION
          "Table for Configuration of G.Bond GBS ports. Entries in this
          table MUST be maintained in a persistent manner"
        ::= { gBondPort 1 }

      gBondPortConfEntry OBJECT-TYPE
        SYNTAX      GBondPortConfEntry
        MAX-ACCESS  not-accessible
        STATUS      current
        DESCRIPTION
          "An entry in the G.Bond Port Configuration table.
          Each entry represents an G.Bond port indexed by the ifIndex.
          Note that an G.Bond GBS port runs on top of a single
          or multiple BCE port(s), which are also indexed by ifIndex."
        INDEX  { ifIndex }
        ::= { gBondPortConfTable 1 }

      GBondPortConfEntry ::=
        SEQUENCE {
          gBondAdminScheme              GBondScheme,
          gBondPeerAdminScheme          GBondScheme,
          gBondDiscoveryCode            PhysAddress,
          gBondTargetUpDataRate         Unsigned32,
          gBondTargetDownDataRate       Unsigned32,
          gBondThreshLowUpRate          Unsigned32,
          gBondThreshLowDownRate        Unsigned32,
          gBondLowRateCrossingEnable    TruthValue
        }

      gBondAdminScheme  OBJECT-TYPE
        SYNTAX      GBondScheme
        MAX-ACCESS  read-write
        STATUS      current
        DESCRIPTION
          "A desired bonding scheme for a G.Bond GBS port.
          The following values instruct the port to use corresponding
          bonding scheme if supported:
            g9981(1)      - instructs the port to use G.998.1 bonding
            g9982(2)      - instructs the port to use G.998.2 bonding
            g9983(3)      - instructs the port to use G.998.3 bonding

          Changing of the gBondAdminScheme MUST be performed when the
          link is Down. Attempts to change this object MUST be rejected
          (in case of SNMP with the error inconsistentValue), if the
          link is Up or Initializing. Attempts to change this object to
          an unsupported bonding scheme (see gBondSchemesSupported)
          SHALL be rejected (in case of SNMP with the error wrongValue).

          This object MUST be maintained in a persistent manner.

          This object maps to the WT-159 attribute
          aGroupAdminBondScheme."
        REFERENCE
          "[WT-159] 5.5.1.6"
        ::= { gBondPortConfEntry 1 }

      gBondPeerAdminScheme  OBJECT-TYPE
        SYNTAX      GBondScheme
        MAX-ACCESS  read-write
        STATUS      current
        DESCRIPTION
          "A desired bonding scheme for a peer (link partner) G.Bond
          port (GBS).
          The following values instruct the peer port to use
          corresponding bonding scheme if supported:
            g9981(1)      - instructs the port to use G.998.1 bonding
            g9982(2)      - instructs the port to use G.998.2 bonding
            g9983(3)      - instructs the port to use G.998.3 bonding

          Changing of the gBondAdminScheme MUST be performed when the
          link is Down. Attempts to change this object MUST be rejected
          (in case of SNMP with the error inconsistentValue), if the
          link is Up or Initializing. Attempts to change this object to
          an unsupported bonding scheme (see gBondPeerSchemesSupported)
          SHALL be rejected (in case of SNMP with the error wrongValue).

          This object MUST be maintained in a persistent manner.

          This object maps to the WT-159 attribute
          aGroupPeerAdminBondScheme."
        REFERENCE
          "[WT-159] 5.5.1.7"
        ::= { gBondPortConfEntry 2 }

      gBondDiscoveryCode  OBJECT-TYPE
        SYNTAX      PhysAddress (SIZE(6))
        MAX-ACCESS  read-write
        STATUS      current
        DESCRIPTION
          "A Discovery Code of the G.Bond port (GBS).
          A unique 6 octet long code used by the Discovery function.
          This object MUST be instantiated for the -O subtype GBS before
          writing operations on the gBondBceRemoteDiscoveryCode
          (Set_if_Clear and Clear_if_Same) are performed by BCEs
          associated with the GBS.
          The initial value of this object for -R subtype ports after
          reset is all zeroes. For -R subtype ports, the value of this
          object cannot be changed directly. This value may be changed
          as a result of writing operation on the
          gBondBceRemoteDiscoveryCode object of remote BCE of -O
          subtype, connected to one of the local BCEs associated with
          the GBS.

          Discovery MUST be performed when the link is Down.
          Attempts to change this object MUST be rejected (in case of
          SNMP with the error inconsistentValue), if the link is Up or
          Initializing.

          This object maps to the WT-159 attribute
          aGroupDiscoveryCode."
        REFERENCE
          "[WT-159] 5.5.1.20; [802.3] 61.2.2.8.3, 61.2.2.8.4,
          45.2.6.6.1, 45.2.6.8, 61A.2"
        ::= { gBondPortConfEntry 3 }

      gBondTargetUpDataRate  OBJECT-TYPE
        SYNTAX      Unsigned32(1..1000000|9999999)
        UNITS       "Kbps"
        MAX-ACCESS  read-write
        STATUS      current
        DESCRIPTION
          "A desired G.Bond port Data Rate in the upstream direction,
          in Kbps, to be achieved during initialization, under
          restrictions placed upon the member BCEs by their respective
          configuration settings.
          This object represents a sum of individual BCE upstream data
          rates, modified to compensate for fragmentation and
          encapsulation overhead (e.g., for an Ethernet service, the
          target data rate of 10Mbps SHALL allow lossless transmission
          of full-duplex 10Mbps Ethernet frame stream with minimal
          inter-frame gap).
          Note that the target upstream data rate may not be achieved
          during initialization (e.g., due to unavailability of required
          BCEs) or the initial bandwidth could deteriorate, so that the
          actual upstream data rate (gBondUpDataRate) could be less
          than gBondTargetUpDataRate.

          The value between 1 and 1000000 indicates that the total
          upstream data rate of the G.Bond port after initialization
          SHALL be equal to the target data rate or less, if the target
          upstream data rate cannot be achieved under the restrictions
          configured for BCEs. In case the copper environment allows to
          achieve higher upstream data rate than that specified by this
          object, the excess capability SHALL be either converted to
          additional SNR margin or reclaimed by minimizing transmit
          power.

          The value of 9999999 means that the target data rate is not
          fixed and SHALL be set to the maximum attainable rate during
          initialization (Best Effort), under specified spectral
          restrictions and with desired SNR Margin per BCE.

          This object is read-write for the -O subtype G.Bond ports
          and irrelevant for the -R subtypes.

          Changing of the Target Upstream Data Rate MUST be performed
          when the link is Down. Attempts to change this object MUST be
          rejected (In case of SNMP with the error inconsistentValue),
          if the link is Up or Initializing.

          This object MUST be maintained in a persistent manner.

          This object maps to the WT-159 attribute
          aGroupTargetUpRate."
        REFERENCE
          "[WT-159] 5.5.1.17"
        ::= { gBondPortConfEntry 4 }

      gBondTargetDownDataRate  OBJECT-TYPE
        SYNTAX      Unsigned32(1..1000000|9999999)
        UNITS       "Kbps"
        MAX-ACCESS  read-write
        STATUS      current
        DESCRIPTION
          "A desired G.Bond port Data Rate in the downstream direction,
          in Kbps, to be achieved during initialization, under
          restrictions placed upon the member BCEs by their respective
          configuration settings.
          This object represents a sum of individual BCE downstream data
          rates, modified to compensate for fragmentation and
          encapsulation overhead (e.g., for an Ethernet service, the
          target data rate of 10Mbps SHALL allow lossless transmission
          of full-duplex 10Mbps Ethernet frame stream with minimal
          inter-frame gap).
          Note that the target downstream data rate may not be achieved
          during initialization (e.g., due to unavailability of required
          BCEs) or the initial bandwidth could deteriorate, so that the
          actual downstream data rate (gBondDownDataRate) could be less
          than gBondTargetDownDataRate.

          The value between 1 and 1000000 indicates that the total
          downstream data rate of the G.Bond port after initialization
          SHALL be equal to the target data rate or less, if the target
          downstream data rate cannot be achieved under the restrictions
          configured for BCEs. In case the copper environment allows to
          achieve higher downstream data rate than that specified by
          this object, the excess capability SHALL be either converted
          to additional SNR margin or reclaimed by minimizing transmit
          power.

          The value of 9999999 means that the target data rate is not
          fixed and SHALL be set to the maximum attainable rate during
          initialization (Best Effort), under specified spectral
          restrictions and with desired SNR Margin per BCE.

          This object is read-write for the -O subtype G.Bond ports
          and irrelevant for the -R subtypes.

          Changing of the Target Downstream Data Rate MUST be performed
          when the link is Down. Attempts to change this object MUST be
          rejected (In case of SNMP with the error inconsistentValue),
          if the link is Up or Initializing.

          This object MUST be maintained in a persistent manner.

          This object maps to the WT-159 attribute
          aGroupTargetDownRate."
        REFERENCE
          "[WT-159] 5.5.1.18"
        ::= { gBondPortConfEntry 5 }

      gBondThreshLowUpRate  OBJECT-TYPE
        SYNTAX      Unsigned32(1..1000000)
        UNITS       "Kbps"
        MAX-ACCESS  read-write
        STATUS      current
        DESCRIPTION
          "This object configures the G.Bond port low upstream rate
          crossing alarm threshold. When the current value of
          gBondUpDataRate for this port reaches/drops below or exceeds
          this threshold, an gBondLowUpRateCrossing notification MAY be
          generated if enabled by gBondLowRateCrossingEnable.

          This object is read-write for the -O subtype G.Bond ports
          and irrelevant for the -R subtypes.

          This object MUST be maintained in a persistent manner.

          This object maps to the WT-159 attribute
          aGroupthreshLowUpRate."
        REFERENCE
          "[WT-159] 5.5.1.21"
        ::= { gBondPortConfEntry 6 }

      gBondThreshLowDownRate  OBJECT-TYPE
        SYNTAX      Unsigned32(1..1000000)
        UNITS       "Kbps"
        MAX-ACCESS  read-write
        STATUS      current
        DESCRIPTION
          "This object configures the G.Bond port low downstream rate
          crossing alarm threshold. When the current value of
          gBondDownDataRate for this port reaches/drops below or exceeds
          this threshold, an gBondLowDownRateCrossing notification MAY
          be generated if enabled by gBondLowRateCrossingEnable.

          This object is read-write for the -O subtype G.Bond ports
          and irrelevant for the -R subtypes.

          This object MUST be maintained in a persistent manner.

          This object maps to the WT-159 attribute
          aGroupThreshDownUpRate."
        REFERENCE
          "[WT-159] 5.5.1.22"
        ::= { gBondPortConfEntry 7 }

      gBondLowRateCrossingEnable  OBJECT-TYPE
        SYNTAX      TruthValue
        MAX-ACCESS  read-write
        STATUS      current
        DESCRIPTION
          "Indicates whether gBondLowUpRateCrossing and
          gBondLowDownRateCrossing notifications should be generated
          for this interface.

          Value of true(1) indicates that the notifications are enabled.
          Value of false(2) indicates that the notifications are
          disabled.

          This object is read-write for the -O subtype G.Bond ports
          and irrelevant for the -R subtypes.

          This object MUST be maintained in a persistent manner.

          This object maps to the WT-159 attribute
          aGroupLowRateCrossingEnable."
        REFERENCE
          "[WT-159] 5.5.1.23"
        ::= { gBondPortConfEntry 8 }


      gBondPortCapabilityTable OBJECT-TYPE
        SYNTAX      SEQUENCE OF GBondPortCapabilityEntry
        MAX-ACCESS  not-accessible
        STATUS      current
        DESCRIPTION
          "Table for Capabilities of G.Bond Ports. Entries in this table
          MUST be maintained in a persistent manner"
        ::= { gBondPort 2 }

      gBondPortCapabilityEntry OBJECT-TYPE
        SYNTAX      GBondPortCapabilityEntry
        MAX-ACCESS  not-accessible
        STATUS      current
        DESCRIPTION
          "An entry in the G.Bond Port Capability table.
          Each entry represents an G.Bond port indexed by the ifIndex.
          Note that a G.Bond GBS port runs on top of a single
          or multiple BCE port(s), which are also indexed by ifIndex."
        INDEX  { ifIndex }
        ::= { gBondPortCapabilityTable 1 }

      GBondPortCapabilityEntry ::=
        SEQUENCE {
          gBondSchemesSupported            GBondSchemeList,
          gBondPeerSchemesSupported        GBondSchemeList,
          gBondCapacity                    Unsigned32,
          gBondPeerCapacity                Unsigned32
        }

      gBondSchemesSupported  OBJECT-TYPE
        SYNTAX      GBondSchemeList
        MAX-ACCESS  read-only
        STATUS      current
        DESCRIPTION
          "Bonding Capability of the G.Bond port (GBS). This is a
          read-only bitmap of the possible bonding schemes supported by
          the GBS. The various bit-positions are:
            g9981(1)      - GBS is capable of G.998.1 bonding
            g9982(2)      - GBS is capable of G.998.2 bonding
            g9983(3)      - GBS is capable of G.998.3 bonding

          Note that for ports supporting multiple bonding schemes the
          actual administrative scheme is set via gBondAdminScheme
          object. The current operating bonding scheme is reflected in
          the gBondOperScheme.

          This object maps to the WT-159 attribute
          aGroupBondSchemesSupported."
        REFERENCE
          "[WT-159] 5.5.1.2"
        ::= { gBondPortCapabilityEntry 1 }

      gBondPeerSchemesSupported  OBJECT-TYPE
        SYNTAX      GBondSchemeList
        MAX-ACCESS  read-only
        STATUS      current
        DESCRIPTION
          "Bonding Capability of the peer G.Bond port (GBS). This is a
          read-only bitmap of the possible bonding schemes supported by
          the link partner GBS. The various bit-positions are:
            unknown(0)    - GBS does not support bonding or
                            the peer unit could not be reached.
            g9981(1)      - GBS is capable of G.998.1 bonding
            g9982(2)      - GBS is capable of G.998.2 bonding
            g9983(3)      - GBS is capable of G.998.3 bonding

          Note that for ports supporting multiple bonding schemes the
          actual administrative scheme is set via gBondPeerAdminScheme
          object. The current operating bonding scheme is reflected in
          the gBondPeerOperScheme.

          This object maps to the WT-159 attribute
          aGroupBondPeerSchemesSupported."
        REFERENCE
          "[WT-159] 5.5.1.3"
        ::= { gBondPortCapabilityEntry 2 }

      gBondCapacity  OBJECT-TYPE
        SYNTAX      Unsigned32 (1..32)
        MAX-ACCESS  read-only
        STATUS      current
        DESCRIPTION
          "Number of BCEs that can be aggregated by the local GBS.
          The number of BCEs currently assigned to a particular G.Bond
          port (gBondNumBCEs) is never greater than gBondCapacity.

          This object maps to the WT-159 attribute aGroupCapacity."
        REFERENCE
          "[WT-159] 5.5.1.12"
        ::= { gBondPortCapabilityEntry 3 }

      gBondPeerCapacity  OBJECT-TYPE
        SYNTAX      Unsigned32 (0|1..32)
        MAX-ACCESS  read-only
        STATUS      current
        DESCRIPTION
          "Number of BCEs that can be aggregated by the peer GBS port.
          Value of 0 is returned when peer Bonding Capacity is unknown
          (peer cannot be reached).

          This object maps to the WT-159 attribute aGroupPeerCapacity."
        REFERENCE
          "[WT-159] 5.5.1.13"
        ::= { gBondPortCapabilityEntry 4 }


      gBondPortStatusTable OBJECT-TYPE
        SYNTAX      SEQUENCE OF GBondPortStatusEntry
        MAX-ACCESS  not-accessible
        STATUS      current
        DESCRIPTION
          "This table provides overall status information of G.Bond
          ports, complementing the generic status information from the
          ifTable of IF-MIB. Additional status information about
          connected BCEs is available from the relevant line MIBs

          This table contains live data from the equipment. As such,
          it is NOT persistent."
        ::= { gBondPort 3 }

      gBondPortStatusEntry OBJECT-TYPE
        SYNTAX      GBondPortStatusEntry
        MAX-ACCESS  not-accessible
        STATUS      current
        DESCRIPTION
          "An entry in the G.Bond Port Status table.
          Each entry represents an G.Bond port indexed by the ifIndex.
          Note that an G.Bond GBS port runs on top of a single
          or multiple BCE port(s), which are also indexed by ifIndex."
        INDEX  { ifIndex }
        ::= { gBondPortStatusTable 1 }

      GBondPortStatusEntry ::=
        SEQUENCE {
          gBondOperScheme                  GBondScheme,
          gBondPeerOperScheme              GBondScheme,
          gBondUpDataRate                  Gauge32,
          gBondDownDataRate                Gauge32,
          gBondFltStatus                   BITS,
          gBondPortSide                    INTEGER,
          gBondNumBCEs                     Unsigned32
        }

      gBondOperScheme  OBJECT-TYPE
        SYNTAX      GBondScheme
        MAX-ACCESS  read-only
        STATUS      current
        DESCRIPTION
          "Current operating bonding scheme of a G.Bond port.
          The possible values are:
            g9981(1)      - G.998.1 bonding
            g9982(2)      - G.998.2 bonding
            g9983(3)      - G.998.3 bonding

          This object maps to the WT-159 attribute
          aGroupOperBondScheme."
        REFERENCE
          "[WT-159] 5.5.1.4"
        ::= { gBondPortStatusEntry 1 }

      gBondPeerOperScheme  OBJECT-TYPE
        SYNTAX      GBondScheme
        MAX-ACCESS  read-only
        STATUS      current
        DESCRIPTION
          "Curent operating bonding scheme of a G.Bond port link
          partner.
          The possible values are:
            unknown(0)     - peer cannot be reached due to the link
                             state
            g9981(1)      - G.998.1 bonding
            g9982(2)      - G.998.2 bonding
            g9983(3)      - G.998.3 bonding

          This object maps to the WT-159 attribute
          aGroupPeerOperBondScheme."
        REFERENCE
          "[WT-159] 5.5.1.5"
        ::= { gBondPortStatusEntry 2 }

      gBondUpDataRate  OBJECT-TYPE
        SYNTAX      Gauge32
        UNITS       "bps"
        MAX-ACCESS  read-only
        STATUS      current
        DESCRIPTION
          "A current G.Bond port operational Data Rate in the upstream
          direction, in bps.
          This object represents an estimation of the sum of individual
          BCE upstream data rates, modified to compensate for
          fragmentation and encapsulation overhead (e.g., for an
          Ethernet service, the target data rate of 10Mbps SHALL allow
          lossless transmission of full-duplex 10Mbps Ethernet frame
          stream with minimal inter-frame gap).

          Note that for symmetrical interfaces gBondUpDataRate ==
          gBondDownDataRate == ifSpeed.

          This object maps to the WT-159 attribute aGroupUpRate."
        REFERENCE
          "[WT-159] 5.5.1.15"
        ::= { gBondPortStatusEntry 3 }

      gBondDownDataRate  OBJECT-TYPE
        SYNTAX      Gauge32
        UNITS       "bps"
        MAX-ACCESS  read-only
        STATUS      current
        DESCRIPTION
          "A current G.Bond port operational Data Rate in the downstream
          direction, in bps.
          This object represents an estimation of the sum of individual
          BCE downstream data rates, modified to compensate for
          fragmentation and encapsulation overhead (e.g., for an
          Ethernet service, the target data rate of 10Mbps SHALL allow
          lossless transmission of full-duplex 10Mbps Ethernet frame
          stream with minimal inter-frame gap).

          Note that for symmetrical interfaces gBondUpDataRate ==
          gBondDownDataRate == ifSpeed.

          This object maps to the WT-159 attribute aGroupDownRate."
        REFERENCE
          "[WT-159] 5.5.1.16"
        ::= { gBondPortStatusEntry 4 }


      gBondFltStatus  OBJECT-TYPE
        SYNTAX      BITS {
          noPeer(0),
          peerPowerLoss(1),
          peerBondSchemeMismatch(2),
          bceSubTypeMismatch(3),
          lowRate(4)
        }
        MAX-ACCESS  read-only
        STATUS      current
        DESCRIPTION
          "G.Bond (GBS) port Fault Status. This is a bitmap of possible
          conditions. The various bit positions are:
            noPeer              - peer GBS cannot be reached (e.g.,
                                  no BCEs attached, all BCEs are Down
                                  etc.).
            peerPowerLoss       - peer GBS has indicated impending unit
                                  failure due to loss of local power
                                  ('Dying Gasp').
            peerBondSchemeMismatch - operating bonding scheme of a peer
                                  GBS is different from the local one.
            bceSubTypeMismatch  - local BCEs in the aggregation group
                                  are not of the same sub-type, e.g.,
                                  some BCEs in the local device are -O
                                  while others are -R subtype.
            lowRate             - gBondUpRate/gBondDownRate of the port
                                  has reached or dropped below
                                  gBondThreshLowUpRate/
                                  gBondThreshLowUpRate.

          This object is intended to supplement ifOperStatus object
          in IF-MIB and ifMauMediaAvailable in MAU-MIB.

          This object maps to the WT-159 attribute aGroupStatus."
        REFERENCE
          "[WT-159] 5.5.1.9; IF-MIB, ifOperStatus; MAU-MIB,
          ifMauMediaAvailable"
        ::= { gBondPortStatusEntry 5 }

      gBondPortSide  OBJECT-TYPE
        SYNTAX      INTEGER {
          subscriber(1),
          office(2),
          unknown(3)
        }
        MAX-ACCESS  read-only
        STATUS      current
        DESCRIPTION
          "G.Bond port mode of operation (subtype).
          The value of 'subscriber' indicates the port is designated as
          '-R' subtype (all BCEs assigned to this port are of subtype
          '-R').
          The value of the 'office' indicates that the port is
          designated as '-O' subtype (all BCEs assigned to this port are
          of subtype '-O').
          The value of 'unknown' indicates that the port has no assigned
          BCEs yet or that the assigned BCEs are not of the same side
          (subTypeBCEMismatch).

          This object maps to the WT-159 attribute aGroupEnd."
        REFERENCE
           "[WT-159] 5.5.1.11"
        ::= { gBondPortStatusEntry 6 }

      gBondNumBCEs  OBJECT-TYPE
        SYNTAX      Unsigned32 (0..32)
        MAX-ACCESS  read-only
        STATUS      current
        DESCRIPTION
          "Number of BCEs that is currently aggregated by the local GBS
          (assigned to the G.Bond port using ifStackTable).
          This number is never greater than gBondCapacity.

          This object SHALL be automatically incremented or decremented
          when a BCE is added or deleted to/from the G.Bond port using
          ifStackTable.

          This object maps to the WT-159 attribute aGroupNumChannels"
        REFERENCE
          "[WT-159] 5.5.1.14"
        ::= { gBondPortStatusEntry 7 }

      -- The BCE group

      gBondBceConfTable OBJECT-TYPE
        SYNTAX      SEQUENCE OF GBondBceConfEntry
        MAX-ACCESS  not-accessible
        STATUS      current
        DESCRIPTION
          "Table for Configuration of G.Bond common aspects for the
          Bonding Channel Entity (BCE) ports (modems/channels).
          Entries in this table MUST be maintained in a persistent
          manner."
        ::= { gBondBce 1 }

      gBondBceConfEntry OBJECT-TYPE
        SYNTAX      GBondBceConfEntry
        MAX-ACCESS  not-accessible
        STATUS      current
        DESCRIPTION
          "An entry in the G.Bond BCE Configuration table.
          Each entry represents common aspects of a G.Bond BCE port
          indexed by the ifIndex. Note that an G.Bond BCE port can be
          stacked below a single GBS port, also indexed by ifIndex,
          possibly together with other BCE ports if GAF is enabled."
        INDEX  { ifIndex }
        ::= { gBondBceConfTable 1 }

      GBondBceConfEntry ::=
        SEQUENCE {
          gBondBceRemoteDiscoveryCode    PhysAddress
        }

      gBondBceRemoteDiscoveryCode  OBJECT-TYPE
        SYNTAX      PhysAddress (SIZE(0|6))
        MAX-ACCESS  read-write
        STATUS      current
        DESCRIPTION
          "A Remote Discovery Code of the BCE port at CO.
          A 6 octet long Discovery Code of the peer GBS connected via
          the BCE.
          Reading this object results in a Discovery Get operation.
          Setting this object to all zeroes results in a Discovery
          Clear_if_Same operation (the value of gBondDiscoveryCode
          at the peer GBS SHALL be the same as gBondDiscoveryCode of
          the local GBS associated with the BCE for the operation to
          succeed).
          Writing a non-zero value to this object results in a
          Discovery Set_if_Clear operation.
          A zero-length octet string SHALL be returned on an attempt to
          read this object when GAF aggregation is not enabled.

          This object is irrelevant in BCE-R port subtypes (CPE side):
          in this case a zero length octet string SHALL be returned on
          an attempt to read this object, writing to this object SHALL
          be rejected.

          Discovery MUST be performed when the link is Down.
          Attempts to change this object MUST be rejected (in case of
          SNMP with the error inconsistentValue), if the link is Up or
          Initializing.

          This object maps to the WT-159 attribute
          aLineRemoteDiscoveryCode."
        REFERENCE
          "[WT-159] 5.5.6.7"
        ::= { gBondBceConfEntry 1 }

     --
     -- Conformance Statements
     --

      gBondGroups      OBJECT IDENTIFIER ::= { gBondConformance 1 }

      gBondCompliances OBJECT IDENTIFIER ::= { gBondConformance 2 }

      -- Object Groups

      gBondBasicGroup OBJECT-GROUP
        OBJECTS {
          gBondOperScheme,
          gBondUpDataRate,
          gBondDownDataRate,
          gBondTargetUpDataRate,
          gBondTargetDownDataRate,
          gBondOperScheme,
          gBondCapacity,
          gBondNumBCEs,
          gBondPortSide,
          gBondFltStatus
        }
        STATUS      current
        DESCRIPTION
          "A collection of objects representing management information
          common to all types of G.Bond ports."
        ::= { gBondGroups 1 }

      gBondDiscoveryGroup OBJECT-GROUP
        OBJECTS {
          gBondPeerOperScheme,
          gBondPeerCapacity,
          gBondDiscoveryCode,
          gBondBceRemoteDiscoveryCode
        }
        STATUS      current
        DESCRIPTION
          "A collection of objects supporting OPTIONAL G.Bond discovery
          in G.Bond ports."
        ::= { gBondGroups 2 }

      gBondMultiSchemeGroup OBJECT-GROUP
        OBJECTS {
          gBondSchemeSupported,
          gBondPeerSchemeSupported,
          gBondAdminScheme,
          gBondPeerAdminScheme
        }
        STATUS      current
        DESCRIPTION
          "A collection of objects providing OPTIONAL management
          information for G.Bond ports supporting multiple bonding
          schemes."
        ::= { gBondGroups 3 }

      gBondAlarmConfGroup OBJECT-GROUP
        OBJECTS {
          gBondThreshLowUpRate,
          gBondThreshLowDownRate,
          gBondLowRateCrossingEnable
        }
        STATUS      current
        DESCRIPTION
          "A collection of objects required for configuration of alarm
          thresholds and notifications in G.Bond ports."
        ::= { gBondGroups 4 }

      gBondNotificationGroup NOTIFICATION-GROUP
        NOTIFICATIONS {
          gBondLowUpRateCrossing,
          gBondLowDownRateCrossing
        }
        STATUS      current
        DESCRIPTION
          "This group supports notifications of significant conditions
          associated with G.Bond ports."
        ::= { gBondGroups 5 }

     -- Compliance Statements

      gBondCompliance MODULE-COMPLIANCE
        STATUS      current
        DESCRIPTION
          "The compliance statement for G.Bond interfaces.
          Compliance with the following external compliance statements
          is REQUIRED:
          
          MIB Module             Compliance Statement
          ----------             --------------------
          IF-MIB                 ifCompliance3

          Compliance with the following external compliance statements
          is OPTIONAL for implementations supporting bonding with
          flexible cross-connect between the GBS and BCE ports:

          MIB Module             Compliance Statement
          ----------             --------------------
          IF-INVERTED-STACK-MIB  ifInvCompliance
          IF-CAP-STACK-MIB       ifCapStackCompliance"

        MODULE  -- this module
          MANDATORY-GROUPS {
            gBondBasicGroup,
            gBondAlarmConfGroup,
            gBondNotificationGroup
          }

          GROUP       gBondDiscoveryGroup
          DESCRIPTION
            "Support for this group is only required for implementations
            supporting G.Bond Discovery function."

          GROUP       gBondMultiSchemeGroup
          DESCRIPTION
            "Support for this group is only required for implementations
            supporting multiple bonding schemes."

        ::= { gBondCompliances 1 }
   END
