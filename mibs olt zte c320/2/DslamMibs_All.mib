-- All the MIBs needed for ZTE DSLAM in correct sequence
-- By Shenjie, 2001/03/21
-- Include the following MIBs:
--      SNMPv2-SMI
--      Rfc1907, SNMPv2-MIB
--      Rfc2233, IF-MIB
--      Rfc1573a, IANAifType-MIB, all the ifTypes defined here
--      Rfc2261, SNMP-FRAMEWORK-MIB, needed by Atm Mibs
--      Rfc2493, PerfHist-TC-MIB, needed by Adsl Mibs
--      Rfc2514, ATM-TC-MIB, needed by Rfc2515
--      Rfc2515, ATM-MIB
--      Rfc2662, ADSL-TC-MIB
--      zxdslam.mib, ZXDSLAM-MIB
--      Rfc1493
--      Rfc2674q
--      wrsMasterMib.mi2 imasys imagroup imalink
--      Rfc2674p
--      lanBridgeMib.mib
--      lanMib.mib
--      OEM-galnet-MIB
--------------------------------------------------------------------------
-- SNMPv2-SMI
--------------------------------------------------------------------------
SNMPv2-SMI DEFINITIONS ::= BEGIN

org OBJECT IDENTIFIER ::= { iso  3 }

dod OBJECT IDENTIFIER ::= { org  6 }

internet OBJECT IDENTIFIER ::= { dod  1 }

directory OBJECT IDENTIFIER  ::= { internet  1 }

mgmt  OBJECT IDENTIFIER  ::= { internet  2 }

mib-2  OBJECT IDENTIFIER  ::= { mgmt  1 }

transmission  OBJECT IDENTIFIER  ::= { mib-2  10 }

experimental  OBJECT IDENTIFIER  ::= { internet  3 }

private  OBJECT IDENTIFIER  ::= { internet  4 }

enterprises  OBJECT IDENTIFIER  ::= { private  1 }

security  OBJECT IDENTIFIER  ::= { internet  5 }

snmpV2  OBJECT IDENTIFIER  ::= { internet  6 }

snmpDomains  OBJECT IDENTIFIER  ::= { snmpV2  1 }

snmpProxys  OBJECT IDENTIFIER  ::= { snmpV2  2 }

snmpModules  OBJECT IDENTIFIER  ::= { snmpV2  3 }

--ObjectName    ::=
--    OBJECT IDENTIFIER

--NotificationName ::=
--    OBJECT IDENTIFIER

--ObjectSyntax ::=
--    CHOICE {
--        simple
--            SimpleSyntax,
--
--        application-wide
--            ApplicationSyntax
--}

--SimpleSyntax ::=
--    CHOICE {
--        integer-value
--            INTEGER,
--
--        string-value
--            OCTET STRING,
--
--        objectID-value
--            OBJECT IDENTIFIER
--}

--Integer32 ::=
--    [UNIVERSAL 2]
--    IMPLICIT INTEGER

--ApplicationSyntax ::=
--    CHOICE {
--        ipAddress-value
--            IpAddress,
--
--        counter-value
--            Counter32,
--
--        timeticks-value
--            TimeTicks,
--
--        arbitrary-value
--            Opaque,
--
--        big-counter-value
--            Counter64,
--
--        unsigned-integer-value
--            Unsigned32
--}

--IpAddress ::=
--    [APPLICATION 0]
--    IMPLICIT OCTET STRING

--Counter32 ::=
--    [APPLICATION 1]
--    IMPLICIT INTEGER

--Gauge32 ::=
--    [APPLICATION 2]
--    IMPLICIT INTEGER

--Unsigned32 ::=
--    [APPLICATION 2]
--    IMPLICIT INTEGER

--TimeTicks ::=
--    [APPLICATION 3]
--    IMPLICIT INTEGER

--Opaque ::=
--    [APPLICATION 4]
--    IMPLICIT OCTET STRING

--Counter64 ::=
--    [APPLICATION 6]
--    IMPLICIT INTEGER

--zeroDotZero OBJECT-IDENTITY
--    STATUS       current
--    DESCRIPTION
--        "A value used for null identifiers."
--    ::= { 0  0 }

END


--------------------------------------------------------------------------
-- Rfc1907, SNMPv2-MIB
--------------------------------------------------------------------------
SNMPv2-MIB DEFINITIONS ::= BEGIN

IMPORTS
    MODULE-IDENTITY, OBJECT-TYPE,
    TimeTicks, snmpModules, mib-2
        FROM SNMPv2-SMI
    DisplayString
	    FROM SNMPv2-TC;

snmpMIB MODULE-IDENTITY
    LAST-UPDATED "9511090000Z"
    ORGANIZATION "IETF SNMPv2 Working Group"
    CONTACT-INFO
            "        Marshall T. Rose

             Postal: Dover Beach Consulting, Inc.
                     420 Whisman Court
                     Mountain View, CA  94043-2186
                     US

                Tel: +1 415 968 1052

             E-mail: mrose@dbc.mtview.ca.us"
    DESCRIPTION
            "The MIB module for SNMPv2 entities."
    REVISION      "9304010000Z"
    DESCRIPTION
            "The initial revision of this MIB module was published as
            RFC 1450."
    ::= { snmpModules 1 }


snmpMIBObjects OBJECT IDENTIFIER ::= { snmpMIB 1 }

--  ::= { snmpMIBObjects 1 }        this OID is obsolete
--  ::= { snmpMIBObjects 2 }        this OID is obsolete
--  ::= { snmpMIBObjects 3 }        this OID is obsolete


-- the System group
--
-- a collection of objects common to all managed systems.

system   OBJECT IDENTIFIER ::= { mib-2 1 }

sysDescr OBJECT-TYPE
    SYNTAX      DisplayString (SIZE (0..255))
    MAX-ACCESS  read-only
    STATUS      current
    DESCRIPTION
            "A textual description of the entity.  This value should
            include the full name and version identification of the
            system's hardware type, software operating-system, and
            networking software."
    ::= { system 1 }

sysObjectID OBJECT-TYPE
    SYNTAX      OBJECT IDENTIFIER
    MAX-ACCESS  read-only
    STATUS      current
    DESCRIPTION
            "The vendor's authoritative identification of the network
            management subsystem contained in the entity.  This value is
            allocated within the SMI enterprises subtree (1.3.6.1.4.1)
            and provides an easy and unambiguous means for determining
            `what kind of box' is being managed.  For example, if vendor
            `Flintstones, Inc.' was assigned the subtree
            1.3.6.1.4.1.4242, it could assign the identifier
            1.3.6.1.4.1.4242.1.1 to its `Fred Router'."
    ::= { system 2 }

sysUpTime OBJECT-TYPE
    SYNTAX      TimeTicks
    MAX-ACCESS  read-only
    STATUS      current
    DESCRIPTION
            "The time (in hundredths of a second) since the network
            management portion of the system was last re-initialized."
    ::= { system 3 }

sysContact OBJECT-TYPE
    SYNTAX      DisplayString (SIZE (0..100))
    MAX-ACCESS  read-write
    STATUS      current
    DESCRIPTION
            "The textual identification of the contact person for this
            managed node, together with information on how to contact
            this person.  If no contact information is known, the value
            is the zero-length string."
    ::= { system 4 }

sysName OBJECT-TYPE
    SYNTAX      DisplayString (SIZE (0..100))
    MAX-ACCESS  read-write
    STATUS      current
    DESCRIPTION
            "An administratively-assigned name for this managed node.
            By convention, this is the node's fully-qualified domain
            name.  If the name is unknown, the value is the zero-length
            string."
    ::= { system 5 }

sysLocation OBJECT-TYPE
    SYNTAX      DisplayString (SIZE (0..100))
    MAX-ACCESS  read-write
    STATUS      current
    DESCRIPTION
            "The physical location of this node (e.g., `telephone
            closet, 3rd floor').  If the location is unknown, the value
            is the zero-length string."
    ::= { system 6 }

sysServices OBJECT-TYPE
    SYNTAX      INTEGER (0..127)
    MAX-ACCESS  read-only
    STATUS      current
    DESCRIPTION
            "A value which indicates the set of services that this
            entity may potentially offers.  The value is a sum.  This
            sum initially takes the value zero, Then, for each layer, L,
            in the range 1 through 7, that this node performs
            transactions for, 2 raised to (L - 1) is added to the sum.
            For example, a node which performs only routing functions
            would have a value of 4 (2^(3-1)).  In contrast, a node
            which is a host offering application services would have a
            value of 72 (2^(4-1) + 2^(7-1)).  Note that in the context
            of the Internet suite of protocols, values should be
            calculated accordingly:

                 layer      functionality
                   1        physical (e.g., repeaters)
                   2        datalink/subnetwork (e.g., bridges)
                   3        internet (e.g., supports the IP)
                   4        end-to-end  (e.g., supports the TCP)
                   7        applications (e.g., supports the SMTP)

            For systems including OSI protocols, layers 5 and 6 may also
            be counted."
    ::= { system 7 }

MacAddress ::= OCTET STRING(SIZE (6))

sysOutBandMacAddr OBJECT-TYPE
    SYNTAX      MacAddress
    MAX-ACCESS  read-only
    STATUS      current
    DESCRIPTION
            "system outBand hardware address."
    ::= { system 8 }


sysInBandMacAddr OBJECT-TYPE
    SYNTAX  MacAddress
    MAX-ACCESS  read-only
    STATUS      current
    DESCRIPTION
            "system inBand hardware address."
    ::= { system 9 }

sysUpLinks OBJECT-TYPE
    SYNTAX      INTEGER (0..4096)
    MAX-ACCESS  read-only
    STATUS      current
    DESCRIPTION
            "system current up links."
    ::= { system 10 }

-- well-known traps


snmpTrap       OBJECT IDENTIFIER ::= { snmpMIBObjects 4 }
snmpTrapOID OBJECT-TYPE
    SYNTAX     OBJECT IDENTIFIER
    MAX-ACCESS accessible-for-notify
    STATUS     current
    DESCRIPTION
            "The authoritative identification of the notification
            currently being sent.  This variable occurs as the second
            varbind in every SNMPv2-Trap-PDU and InformRequest-PDU."
    ::= { snmpTrap 1 }

snmpTrapEnterprise OBJECT-TYPE
    SYNTAX     OBJECT IDENTIFIER
    MAX-ACCESS accessible-for-notify
    STATUS     current
    DESCRIPTION
            "The authoritative identification of the enterprise
            associated with the trap currently being sent.  When a
            SNMPv2 proxy agent is mapping an RFC1157 Trap-PDU into a
            SNMPv2-Trap-PDU, this variable occurs as the last varbind."
    ::= { snmpTrap 3 }

snmpTraps      OBJECT IDENTIFIER ::= { snmpMIBObjects 5 }

coldStart NOTIFICATION-TYPE
    STATUS  current
    DESCRIPTION
            "A coldStart trap signifies that the SNMPv2 entity, acting
            in an agent role, is reinitializing itself and that its
            configuration may have been altered."
    ::= { snmpTraps 1 }

warmStart NOTIFICATION-TYPE
    STATUS  current
    DESCRIPTION
            "A warmStart trap signifies that the SNMPv2 entity, acting
            in an agent role, is reinitializing itself such that its
            configuration is unaltered."
    ::= { snmpTraps 2 }

authenticationFailure NOTIFICATION-TYPE
    STATUS  current
    DESCRIPTION
            "An authenticationFailure trap signifies that the SNMPv2
            entity, acting in an agent role, has received a protocol
            message that is not properly authenticated.  While all
            implementations of the SNMPv2 must be capable of generating
            this trap, the snmpEnableAuthenTraps object indicates
            whether this trap will be generated."
    ::= { snmpTraps 5 }

END

--------------------------------------------------------------------------
-- Rfc2233, IF-MIB
--------------------------------------------------------------------------
   IF-MIB DEFINITIONS ::= BEGIN

   IMPORTS
       MODULE-IDENTITY, OBJECT-TYPE,
	   NOTIFICATION-TYPE,
	   Counter32,
	   Gauge32,
       Integer32, TimeTicks, mib-2					FROM SNMPv2-SMI
       TEXTUAL-CONVENTION, DisplayString, TruthValue,
       PhysAddress, RowStatus						FROM SNMPv2-TC
       IANAifType									FROM IANAifType-MIB
	   snmpTraps									FROM SNMPv2-MIB;

   ifMIB MODULE-IDENTITY
       LAST-UPDATED "9611031355Z"
       ORGANIZATION "IETF Interfaces MIB Working Group"
       CONTACT-INFO
               "   Keith McCloghrie
                   Cisco Systems, Inc.
                   170 West Tasman Drive
                   San Jose, CA  95134-1706
                   US

                   408-526-5260
                   kzm@cisco.com"
       DESCRIPTION
               "The MIB module to describe generic objects for
               network interface sub-layers.  This MIB is an updated
               version of MIB-II's ifTable, and incorporates the
               extensions defined in RFC 1229."
       REVISION      "9602282155Z"
       DESCRIPTION
               "Revisions made by the Interfaces MIB WG."
       REVISION      "9311082155Z"
       DESCRIPTION
               "Initial revision, published as part of RFC 1573."
       ::= { mib-2 31 }


   ifMIBObjects OBJECT IDENTIFIER ::= { ifMIB 1 }

   interfaces   OBJECT IDENTIFIER ::= { mib-2 2 }


--   OwnerString ::= TEXTUAL-CONVENTION
--       DISPLAY-HINT "255a"
--       STATUS       current
--       DESCRIPTION
--               "This data type is used to model an administratively
--               assigned name of the owner of a resource.  This
--               information is taken from the NVT ASCII character set.
--               It is suggested that this name contain one or more of
--               the following: ASCII form of the manager station's
--               transport address, management station name (e.g.,
--               domain name), network management personnel's name,
--               location, or phone number.  In some cases the agent
--               itself will be the owner of an entry.  In these cases,
--               this string shall be set to a string starting with
--               'agent'."
--       SYNTAX       OCTET STRING (SIZE(0..255))

   -- InterfaceIndex contains the semantics of ifIndex and
   -- should be used for any objects defined on other mib
   -- modules that need these semantics.

   InterfaceIndex ::= TEXTUAL-CONVENTION
       DISPLAY-HINT "d"
       STATUS       current
       DESCRIPTION
               "A unique value, greater than zero, for each interface
               or interface sub-layer in the managed system.  It is
               recommended that values are assigned contiguously
               starting from 1.  The value for each interface sub-
               layer must remain constant at least from one re-
               initialization of the entity's network management
               system to the next re-initialization."
       SYNTAX       Integer32 (1..2147483647)


   InterfaceIndexOrZero ::= TEXTUAL-CONVENTION
       DISPLAY-HINT "d"
       STATUS       current
       DESCRIPTION
               "This textual convention is an extension of the
               InterfaceIndex convention.  The latter defines a
               greater than zero value used to identify an interface
               or interface sub-layer in the managed system.  This
               extension permits the additional value of zero.  the
               value zero is object-specific and must therefore be
               defined as part of the description of any object which
               uses this syntax.  Examples of the usage of zero might
               include situations where interface was unknown, or
               when none or all interfaces need to be referenced."
       SYNTAX       Integer32 (0..2147483647)


   ifNumber  OBJECT-TYPE
       SYNTAX      Integer32
       MAX-ACCESS  read-only
       STATUS      current
       DESCRIPTION
               "The number of network interfaces (regardless of their
               current state) present on this system."
       ::= { interfaces 1 }

   ifTableLastChange  OBJECT-TYPE
       SYNTAX      TimeTicks
       MAX-ACCESS  read-only
       STATUS      current
       DESCRIPTION
               "The value of sysUpTime at the time of the last
               creation or deletion of an entry in the ifTable.  If
               the number of entries has been unchanged since the
               last re-initialization of the local network management
               subsystem, then this object contains a zero value."
       ::= { ifMIBObjects 5 }


   -- the Interfaces table

   -- The Interfaces table contains information on the entity's
   -- interfaces.  Each sub-layer below the internetwork-layer
   -- of a network interface is considered to be an interface.

   ifTable OBJECT-TYPE
       SYNTAX      SEQUENCE OF IfEntry
       MAX-ACCESS  not-accessible
       STATUS      current
       DESCRIPTION
               "A list of interface entries.  The number of entries
               is given by the value of ifNumber."
       ::= { interfaces 2 }

   ifEntry OBJECT-TYPE
       SYNTAX      IfEntry
       MAX-ACCESS  not-accessible
       STATUS      current
       DESCRIPTION
               "An entry containing management information applicable
               to a particular interface."
       INDEX   { ifIndex }
       ::= { ifTable 1 }

   IfEntry ::=
       SEQUENCE {
           ifIndex                 InterfaceIndex,
           ifDescr                 DisplayString,
           ifType                  IANAifType,
--           ifMtu                   Integer32,
           ifSpeed                 Gauge32,
           ifPhysAddress           PhysAddress,
           ifAdminStatus           INTEGER,
           ifOperStatus            INTEGER,
           ifLastChange            TimeTicks,
           ifInOctets              Counter32,
--           ifInUcastPkts           Counter32,
--           ifInNUcastPkts          Counter32,
												-- deprecated
--           ifInDiscards            Counter32,
           ifInErrors              Counter32,
           ifInUnknownProtos       Counter32,
           ifOutOctets             Counter32,
--           ifOutUcastPkts          Counter32,
--           ifOutNUcastPkts         Counter32,
												-- deprecated
--           ifOutDiscards           Counter32,
           ifOutErrors             Counter32
--           ifOutQLen               Gauge32,
												-- deprecated
--           ifSpecific              OBJECT IDENTIFIER
												-- deprecated
       }


   ifIndex OBJECT-TYPE
       SYNTAX      InterfaceIndex
       MAX-ACCESS  read-only
       STATUS      current
       DESCRIPTION
               "A unique value, greater than zero, for each
               interface.  It is recommended that values are assigned
               contiguously starting from 1.  The value for each
               interface sub-layer must remain constant at least from
               one re-initialization of the entity's network
               management system to the next re-initialization."
       ::= { ifEntry 1 }

   ifDescr OBJECT-TYPE
       SYNTAX      DisplayString (SIZE (0..255))
       MAX-ACCESS  read-only
       STATUS      current
       DESCRIPTION
               "A textual string containing information about the
               interface.  This string should include the name of the
               manufacturer, the product name and the version of the
               interface hardware/software."
       ::= { ifEntry 2 }

   ifType OBJECT-TYPE
       SYNTAX      IANAifType
       MAX-ACCESS  read-only
       STATUS      current
       DESCRIPTION
               "The type of interface.  Additional values for ifType
               are assigned by the Internet Assigned Numbers
               Authority (IANA), through updating the syntax of the
               IANAifType textual convention."
       ::= { ifEntry 3 }

--   ifMtu OBJECT-TYPE
--       SYNTAX      Integer32
--       MAX-ACCESS  read-only
--       STATUS      current
--       DESCRIPTION
--               "The size of the largest packet which can be
--               sent/received on the interface, specified in octets.
--               For interfaces that are used for transmitting network
--               datagrams, this is the size of the largest network
--               datagram that can be sent on the interface."
--       ::= { ifEntry 4 }

   ifSpeed OBJECT-TYPE
       SYNTAX      Gauge32
       MAX-ACCESS  read-only
       STATUS      current
       DESCRIPTION
               "An estimate of the interface's current bandwidth in
               bits per second.  For interfaces which do not vary in
               bandwidth or for those where no accurate estimation
               can be made, this object should contain the nominal
               bandwidth.  If the bandwidth of the interface is
               greater than the maximum value reportable by this
               object then this object should report its maximum
               value (4,294,967,295) and ifHighSpeed must be used to
               report the interace's speed.  For a sub-layer which
               has no concept of bandwidth, this object should be
               zero."
       ::= { ifEntry 5 }

   ifPhysAddress OBJECT-TYPE
       SYNTAX      PhysAddress
       MAX-ACCESS  read-only
       STATUS      current
       DESCRIPTION
               "The interface's address at its protocol sub-layer.
               For example, for an 802.x interface, this object
               normally contains a MAC address.  The interface's
               media-specific MIB must define the bit and byte
               ordering and the format of the value of this object.
               For interfaces which do not have such an address
               (e.g., a serial line), this object should contain an
               octet string of zero length."
       ::= { ifEntry 6 }

   ifAdminStatus OBJECT-TYPE
       SYNTAX  INTEGER {
                   up(1),       -- ready to pass packets
                   down(2),
                   testing(3)   -- in some test mode
               }
       MAX-ACCESS  read-write
       STATUS      current
       DESCRIPTION
               "The desired state of the interface.  The testing(3)
               state indicates that no operational packets can be
               passed.  When a managed system initializes, all
               interfaces start with ifAdminStatus in the down(2)
               state.  As a result of either explicit management
               action or per configuration information retained by
               the managed system, ifAdminStatus is then changed to
               either the up(1) or testing(3) states (or remains in
               the down(2) state)."
       ::= { ifEntry 7 }

   ifOperStatus OBJECT-TYPE
       SYNTAX  INTEGER {
                   up(1),        -- ready to pass packets
                   down(2),
                   testing(3),   -- in some test mode
                   unknown(4),   -- status can not be determined
                                 -- for some reason.
                   dormant(5),
                   notPresent(6),    -- some component is missing
                   lowerLayerDown(7) -- down due to state of
                                     -- lower-layer interface(s)
               }
       MAX-ACCESS  read-only
       STATUS      current
       DESCRIPTION
               "The current operational state of the interface.  The
               testing(3) state indicates that no operational packets
               can be passed.  If ifAdminStatus is down(2) then
               ifOperStatus should be down(2).  If ifAdminStatus is
               changed to up(1) then ifOperStatus should change to
               up(1) if the interface is ready to transmit and
               receive network traffic; it should change to
               dormant(5) if the interface is waiting for external
               actions (such as a serial line waiting for an incoming
               connection); it should remain in the down(2) state if
               and only if there is a fault that prevents it from
               going to the up(1) state; it should remain in the
               notPresent(6) state if the interface has missing
               (typically, hardware) components."
       ::= { ifEntry 8 }

   ifLastChange OBJECT-TYPE
       SYNTAX      TimeTicks
       MAX-ACCESS  read-only
       STATUS      current
       DESCRIPTION
               "The value of sysUpTime at the time the interface
               entered its current operational state.  If the current
               state was entered prior to the last re-initialization
               of the local network management subsystem, then this
               object contains a zero value."
       ::= { ifEntry 9 }

   ifInOctets OBJECT-TYPE
       SYNTAX      Counter32
       MAX-ACCESS  read-only
       STATUS      current
       DESCRIPTION
               "The total number of octets received on the interface,
               including framing characters.

               Discontinuities in the value of this counter can occur
               at re-initialization of the management system, and at
               other times as indicated by the value of
               ifCounterDiscontinuityTime."
       ::= { ifEntry 10 }

--   ifInUcastPkts OBJECT-TYPE
--       SYNTAX      Counter32
--       MAX-ACCESS  read-only
--       STATUS      current
--       DESCRIPTION
--               "The number of packets, delivered by this sub-layer to
--               a higher (sub-)layer, which were not addressed to a
--               multicast or broadcast address at this sub-layer.
--
--               Discontinuities in the value of this counter can occur
--               at re-initialization of the management system, and at
--               other times as indicated by the value of
--               ifCounterDiscontinuityTime."
--       ::= { ifEntry 11 }

--   ifInNUcastPkts OBJECT-TYPE
--       SYNTAX  Counter32
--       MAX-ACCESS  read-only
--       STATUS      deprecated
--       DESCRIPTION
--               "The number of packets, delivered by this sub-layer to
--               a higher (sub-)layer, which were addressed to a
--               multicast or broadcast address at this sub-layer.
--
--               Discontinuities in the value of this counter can occur
--               at re-initialization of the management system, and at
--               other times as indicated by the value of
--               ifCounterDiscontinuityTime.
--
--               This object is deprecated in favour of
--               ifInMulticastPkts and ifInBroadcastPkts."
--       ::= { ifEntry 12 }

--   ifInDiscards OBJECT-TYPE
--       SYNTAX      Counter32
--       MAX-ACCESS  read-only
--       STATUS      current
--       DESCRIPTION
--               "The number of inbound packets which were chosen to be
--               discarded even though no errors had been detected to
--               prevent their being deliverable to a higher-layer
--               protocol.  One possible reason for discarding such a
--               packet could be to free up buffer space.
--
--               Discontinuities in the value of this counter can occur
--               at re-initialization of the management system, and at
--               other times as indicated by the value of
--               ifCounterDiscontinuityTime."
--       ::= { ifEntry 13 }

   ifInErrors OBJECT-TYPE
       SYNTAX      Counter32
       MAX-ACCESS  read-only
       STATUS      current
       DESCRIPTION
               "For packet-oriented interfaces, the number of inbound
               packets that contained errors preventing them from
               being deliverable to a higher-layer protocol.  For
               character-oriented or fixed-length interfaces, the
               number of inbound transmission units that contained
               errors preventing them from being deliverable to a
               higher-layer protocol.

               Discontinuities in the value of this counter can occur
               at re-initialization of the management system, and at
               other times as indicated by the value of
               ifCounterDiscontinuityTime."
       ::= { ifEntry 14 }

   ifInUnknownProtos OBJECT-TYPE
       SYNTAX      Counter32
       MAX-ACCESS  read-only
       STATUS      current
       DESCRIPTION
               "For packet-oriented interfaces, the number of packets
               received via the interface which were discarded
               because of an unknown or unsupported protocol.  For
               character-oriented or fixed-length interfaces that
               support protocol multiplexing the number of
               transmission units received via the interface which
               were discarded because of an unknown or unsupported
               protocol.  For any interface that does not support
               protocol multiplexing, this counter will always be 0.

               Discontinuities in the value of this counter can occur
               at re-initialization of the management system, and at
               other times as indicated by the value of
               ifCounterDiscontinuityTime."
       ::= { ifEntry 15 }

   ifOutOctets OBJECT-TYPE
       SYNTAX      Counter32
       MAX-ACCESS  read-only
       STATUS      current
       DESCRIPTION
               "The total number of octets transmitted out of the
               interface, including framing characters.

              Discontinuities in the value of this counter can occur
               at re-initialization of the management system, and at
               other times as indicated by the value of
               ifCounterDiscontinuityTime."
       ::= { ifEntry 16 }

--   ifOutUcastPkts OBJECT-TYPE
--       SYNTAX      Counter32
--       MAX-ACCESS  read-only
--       STATUS      current
--       DESCRIPTION
--               "The total number of packets that higher-level
--               protocols requested be transmitted, and which were not
--               addressed to a multicast or broadcast address at this
--               sub-layer, including those that were discarded or not
--               sent.
--
--               Discontinuities in the value of this counter can occur
--               at re-initialization of the management system, and at
--               other times as indicated by the value of
--               ifCounterDiscontinuityTime."
--       ::= { ifEntry 17 }

--   ifOutNUcastPkts OBJECT-TYPE
--       SYNTAX      Counter32
--       MAX-ACCESS  read-only
--       STATUS      deprecated
--       DESCRIPTION
--               "The total number of packets that higher-level
--               protocols requested be transmitted, and which were
--               addressed to a multicast or broadcast address at this
--               sub-layer, including those that were discarded or not
--               sent.
--
--               Discontinuities in the value of this counter can occur
--               at re-initialization of the management system, and at
--               other times as indicated by the value of
--               ifCounterDiscontinuityTime.
--               This object is deprecated in favour of
--               ifOutMulticastPkts and ifOutBroadcastPkts."
--       ::= { ifEntry 18 }

--   ifOutDiscards OBJECT-TYPE
--       SYNTAX      Counter32
--       MAX-ACCESS  read-only
--       STATUS      current
--       DESCRIPTION
--               "The number of outbound packets which were chosen to
--               be discarded even though no errors had been detected
--               to prevent their being transmitted.  One possible
--               reason for discarding such a packet could be to free
--               up buffer space.
--
--               Discontinuities in the value of this counter can occur
--               at re-initialization of the management system, and at
--               other times as indicated by the value of
--               ifCounterDiscontinuityTime."
--       ::= { ifEntry 19 }

   ifOutErrors OBJECT-TYPE
       SYNTAX      Counter32
       MAX-ACCESS  read-only
       STATUS      current
       DESCRIPTION
               "For packet-oriented interfaces, the number of
               outbound packets that could not be transmitted because
               of errors.  For character-oriented or fixed-length
               interfaces, the number of outbound transmission units
               that could not be transmitted because of errors.

               Discontinuities in the value of this counter can occur
               at re-initialization of the management system, and at
               other times as indicated by the value of
               ifCounterDiscontinuityTime."
       ::= { ifEntry 20 }


--   ifOutQLen OBJECT-TYPE
--       SYNTAX      Gauge32
--       MAX-ACCESS  read-only
--       STATUS      deprecated
--       DESCRIPTION
--               "The length of the output packet queue (in packets)."
--       ::= { ifEntry 21 }

--   ifSpecific OBJECT-TYPE
--       SYNTAX      OBJECT IDENTIFIER
--       MAX-ACCESS  read-only
--       STATUS      deprecated
--       DESCRIPTION
--               "A reference to MIB definitions specific to the
--               particular media being used to realize the interface.
--               It is recommended that this value point to an instance
--               of a MIB object in the media-specific MIB, i.e., that
--               this object have the semantics associated with the
--               InstancePointer textual convention defined in RFC
--               1903.  In fact, it is recommended that the media-
--               specific MIB specify what value ifSpecific should/can
--               take for values of ifType.  If no MIB definitions
--               specific to the particular media are available, the
--               value should be set to the OBJECT IDENTIFIER { 0 0 }."
--       ::= { ifEntry 22 }



   --
   --   Extension to the interface table
   --
   -- This table replaces the ifExtnsTable table.
   --

   ifXTable        OBJECT-TYPE
       SYNTAX      SEQUENCE OF IfXEntry
       MAX-ACCESS  not-accessible
       STATUS      current
       DESCRIPTION
               "A list of interface entries.  The number of entries
               is given by the value of ifNumber.  This table
               contains additional objects for the interface table."
       ::= { ifMIBObjects 1 }

   ifXEntry        OBJECT-TYPE
       SYNTAX      IfXEntry
       MAX-ACCESS  not-accessible
       STATUS      current
       DESCRIPTION
               "An entry containing additional management information
               applicable to a particular interface."
       AUGMENTS    { ifEntry }
       ::= { ifXTable 1 }

   IfXEntry ::=
       SEQUENCE {
           ifName                  DisplayString,
--           ifInMulticastPkts       Counter32,
--           ifInBroadcastPkts       Counter32,
--           ifOutMulticastPkts      Counter32,
--           ifOutBroadcastPkts      Counter32,
--           ifHCInOctets            Counter64,
--           ifHCInUcastPkts         Counter64,
--           ifHCInMulticastPkts     Counter64,
--           ifHCInBroadcastPkts     Counter64,
--           ifHCOutOctets           Counter64,
--           ifHCOutUcastPkts        Counter64,
--           ifHCOutMulticastPkts    Counter64,
--           ifHCOutBroadcastPkts    Counter64,
           ifLinkUpDownTrapEnable  INTEGER,
           ifHighSpeed             Gauge32,
--           ifPromiscuousMode       TruthValue,
           ifConnectorPresent      TruthValue,
           ifAlias                 DisplayString
--           ifCounterDiscontinuityTime TimeStamp
       }


   ifName OBJECT-TYPE
       SYNTAX      DisplayString
       MAX-ACCESS  read-only
       STATUS      current
       DESCRIPTION
               "The textual name of the interface.  The value of this
               object should be the name of the interface as assigned
               by the local device and should be suitable for use in
               commands entered at the device's `console'.  This
               might be a text name, such as `le0' or a simple port
               number, such as `1', depending on the interface naming
               syntax of the device.  If several entries in the
               ifTable together represent a single interface as named
               by the device, then each will have the same value of
               ifName.  Note that for an agent which responds to SNMP
               queries concerning an interface on some other
               (proxied) device, then the value of ifName for such an
               interface is the proxied device's local name for it.

               If there is no local name, or this object is otherwise
               not applicable, then this object contains a zero-
               length string."
       ::= { ifXEntry 1 }

--   ifInMulticastPkts OBJECT-TYPE
--       SYNTAX      Counter32
--       MAX-ACCESS  read-only
--       STATUS      current
--       DESCRIPTION
--               "The number of packets, delivered by this sub-layer to
--               a higher (sub-)layer, which were addressed to a
--               multicast address at this sub-layer.  For a MAC layer
--               protocol, this includes both Group and Functional
--               addresses.
--
--               Discontinuities in the value of this counter can occur
--               at re-initialization of the management system, and at
--               other times as indicated by the value of
--               ifCounterDiscontinuityTime."
--       ::= { ifXEntry 2 }

--   ifInBroadcastPkts OBJECT-TYPE
--       SYNTAX      Counter32
--       MAX-ACCESS  read-only
--       STATUS      current
--       DESCRIPTION
--               "The number of packets, delivered by this sub-layer to
--               a higher (sub-)layer, which were addressed to a
--               broadcast address at this sub-layer.
--
--               Discontinuities in the value of this counter can occur
--               at re-initialization of the management system, and at
--               other times as indicated by the value of
--               ifCounterDiscontinuityTime."
--       ::= { ifXEntry 3 }

--   ifOutMulticastPkts OBJECT-TYPE
--       SYNTAX      Counter32
--       MAX-ACCESS  read-only
--       STATUS      current
--       DESCRIPTION
--               "The total number of packets that higher-level
--               protocols requested be transmitted, and which were
--               addressed to a multicast address at this sub-layer,
--               including those that were discarded or not sent.  For
--               a MAC layer protocol, this includes both Group and
--               Functional addresses.
--
--               Discontinuities in the value of this counter can occur
--               at re-initialization of the management system, and at
--               other times as indicated by the value of
--               ifCounterDiscontinuityTime."
--       ::= { ifXEntry 4 }

--   ifOutBroadcastPkts OBJECT-TYPE
--       SYNTAX      Counter32
--       MAX-ACCESS  read-only
--       STATUS      current
--       DESCRIPTION
--               "The total number of packets that higher-level
--               protocols requested be transmitted, and which were
--               addressed to a broadcast address at this sub-layer,
--               including those that were discarded or not sent.
--
--               Discontinuities in the value of this counter can occur
--               at re-initialization of the management system, and at
--               other times as indicated by the value of
--               ifCounterDiscontinuityTime."
--       ::= { ifXEntry 5 }

   --
   -- High Capacity Counter objects.  These objects are all
   -- 64 bit versions of the "basic" ifTable counters.  These
   -- objects all have the same basic semantics as their 32-bit
   -- counterparts, however, their syntax has been extended
   -- to 64 bits.
   --

--   ifHCInOctets OBJECT-TYPE
--       SYNTAX      Counter64
--       MAX-ACCESS  read-only
--       STATUS      current
--
--       DESCRIPTION
--               "The total number of octets received on the interface,
--               including framing characters.  This object is a 64-bit
--               version of ifInOctets.
--
--               Discontinuities in the value of this counter can occur
--               at re-initialization of the management system, and at
--               other times as indicated by the value of
--               ifCounterDiscontinuityTime."
--       ::= { ifXEntry 6 }

--   ifHCInUcastPkts OBJECT-TYPE
--       SYNTAX      Counter64
--       MAX-ACCESS  read-only
--       STATUS      current
--       DESCRIPTION
--               "The number of packets, delivered by this sub-layer to
--               a higher (sub-)layer, which were not addressed to a
--               multicast or broadcast address at this sub-layer.
--               This object is a 64-bit version of ifInUcastPkts.
--
--               Discontinuities in the value of this counter can occur
--               at re-initialization of the management system, and at
--               other times as indicated by the value of
--               ifCounterDiscontinuityTime."
--       ::= { ifXEntry 7 }

--   ifHCInMulticastPkts OBJECT-TYPE
--       SYNTAX      Counter64
--       MAX-ACCESS  read-only
--       STATUS      current
--       DESCRIPTION
--               "The number of packets, delivered by this sub-layer to
--               a higher (sub-)layer, which were addressed to a
--               multicast address at this sub-layer.  For a MAC layer
--               protocol, this includes both Group and Functional
--               addresses.  This object is a 64-bit version of
--               ifInMulticastPkts.
--
--               Discontinuities in the value of this counter can occur
--               at re-initialization of the management system, and at
--               other times as indicated by the value of
--               ifCounterDiscontinuityTime."
--       ::= { ifXEntry 8 }


--   ifHCInBroadcastPkts OBJECT-TYPE
--       SYNTAX      Counter64
--       MAX-ACCESS  read-only
--       STATUS      current
--       DESCRIPTION
--               "The number of packets, delivered by this sub-layer to
--               a higher (sub-)layer, which were addressed to a
--               broadcast address at this sub-layer.  This object is a
--               64-bit version of ifInBroadcastPkts.
--
--               Discontinuities in the value of this counter can occur
--               at re-initialization of the management system, and at
--               other times as indicated by the value of
--               ifCounterDiscontinuityTime."
--       ::= { ifXEntry 9 }

--   ifHCOutOctets OBJECT-TYPE
--       SYNTAX      Counter64
--       MAX-ACCESS  read-only
--       STATUS      current
--       DESCRIPTION
--               "The total number of octets transmitted out of the
--               interface, including framing characters.  This object
--               is a 64-bit version of ifOutOctets.
--
--               Discontinuities in the value of this counter can occur
--               at re-initialization of the management system, and at
--               other times as indicated by the value of
--               ifCounterDiscontinuityTime."
--       ::= { ifXEntry 10 }

--   ifHCOutUcastPkts OBJECT-TYPE
--       SYNTAX      Counter64
--       MAX-ACCESS  read-only
--       STATUS      current
--       DESCRIPTION
--               "The total number of packets that higher-level
--               protocols requested be transmitted, and which were not
--               addressed to a multicast or broadcast address at this
--               sub-layer, including those that were discarded or not
--               sent.  This object is a 64-bit version of
--               ifOutUcastPkts.
--
--               Discontinuities in the value of this counter can occur
--               at re-initialization of the management system, and at
--               other times as indicated by the value of
--               ifCounterDiscontinuityTime."
--       ::= { ifXEntry 11 }

--   ifHCOutMulticastPkts OBJECT-TYPE
--       SYNTAX      Counter64
--       MAX-ACCESS  read-only
--       STATUS      current
--       DESCRIPTION
--               "The total number of packets that higher-level
--               protocols requested be transmitted, and which were
--               addressed to a multicast address at this sub-layer,
--               including those that were discarded or not sent.  For
--               a MAC layer protocol, this includes both Group and
--               Functional addresses.  This object is a 64-bit version
--               of ifOutMulticastPkts.
--               Discontinuities in the value of this counter can occur
--               at re-initialization of the management system, and at
--               other times as indicated by the value of
--               ifCounterDiscontinuityTime."
--       ::= { ifXEntry 12 }

--   ifHCOutBroadcastPkts OBJECT-TYPE
--       SYNTAX      Counter64
--       MAX-ACCESS  read-only
--       STATUS      current
--       DESCRIPTION
--               "The total number of packets that higher-level
--               protocols requested be transmitted, and which were
--               addressed to a broadcast address at this sub-layer,
--               including those that were discarded or not sent.  This
--               object is a 64-bit version of ifOutBroadcastPkts.
--
--               Discontinuities in the value of this counter can occur
--               at re-initialization of the management system, and at
--               other times as indicated by the value of
--               ifCounterDiscontinuityTime."
--       ::= { ifXEntry 13 }

  ifLinkUpDownTrapEnable  OBJECT-TYPE
       SYNTAX      INTEGER { enabled(1), disabled(2) }
       MAX-ACCESS  read-write
       STATUS      current
       DESCRIPTION
               "Indicates whether linkUp/linkDown traps should be
               generated for this interface.

               By default, this object should have the value
               enabled(1) for interfaces which do not operate on
               'top' of any other interface (as defined in the
               ifStackTable), and disabled(2) otherwise."
       ::= { ifXEntry 14 }

   ifHighSpeed OBJECT-TYPE
       SYNTAX      Gauge32
       MAX-ACCESS  read-only
       STATUS      current
       DESCRIPTION
               "An estimate of the interface's current bandwidth in
               units of 1,000,000 bits per second.  If this object
               reports a value of `n' then the speed of the interface
               is somewhere in the range of `n-500,000' to
               `n+499,999'.  For interfaces which do not vary in
               bandwidth or for those where no accurate estimation
               can be made, this object should contain the nominal
               bandwidth.  For a sub-layer which has no concept of
               bandwidth, this object should be zero."
       ::= { ifXEntry 15 }

--   ifPromiscuousMode  OBJECT-TYPE
--       SYNTAX      TruthValue
--       MAX-ACCESS  read-write
--       STATUS      current
--       DESCRIPTION
--               "This object has a value of false(2) if this interface
--               only accepts packets/frames that are addressed to this
--               station.  This object has a value of true(1) when the
--               station accepts all packets/frames transmitted on the
--               media.  The value true(1) is only legal on certain
--               types of media.  If legal, setting this object to a
--               value of true(1) may require the interface to be reset
--               before becoming effective.
--
--               The value of ifPromiscuousMode does not affect the
--               reception of broadcast and multicast packets/frames by
--               the interface."
--       ::= { ifXEntry 16 }

   ifConnectorPresent   OBJECT-TYPE
       SYNTAX      TruthValue
       MAX-ACCESS  read-only
       STATUS      current
       DESCRIPTION
               "This object has the value 'true(1)' if the interface
               sublayer has a physical connector and the value
               'false(2)' otherwise."
       ::= { ifXEntry 17 }

   ifAlias   OBJECT-TYPE
       SYNTAX      DisplayString (SIZE(0..64))
       MAX-ACCESS  read-write
       STATUS      current
       DESCRIPTION
               "This object is an 'alias' name for the interface as
               specified by a network manager, and provides a non-
               volatile 'handle' for the interface.

               On the first instantiation of an interface, the value
               of ifAlias associated with that interface is the
               zero-length string.  As and when a value is written
               into an instance of ifAlias through a network
               management set operation, then the agent must retain
               the supplied value in the ifAlias instance associated
               with the same interface for as long as that interface
               remains instantiated, including across all re-
               initializations/reboots of the network management
               system, including those which result in a change of
               the interface's ifIndex value.

               An example of the value which a network manager might
               store in this object for a WAN interface is the
               (Telco's) circuit number/identifier of the interface.

               Some agents may support write-access only for
               interfaces having particular values of ifType.  An
               agent which supports write access to this object is
               required to keep the value in non-volatile storage,
               but it may limit the length of new values depending on
               how much storage is already occupied by the current
               values for other interfaces."
       ::= { ifXEntry 18 }

--   ifCounterDiscontinuityTime OBJECT-TYPE
--       SYNTAX      TimeStamp
--       MAX-ACCESS  read-only
--       STATUS      current
--       DESCRIPTION
--               "The value of sysUpTime on the most recent occasion at
--               which any one or more of this interface's counters
--               suffered a discontinuity.  The relevant counters are
--               the specific instances associated with this interface
--               of any Counter32 or Counter64 object contained in the
--               ifTable or ifXTable.  If no such discontinuities have
--               occurred since the last re-initialization of the local
--               management subsystem, then this object contains a zero
--               value."
--       ::= { ifXEntry 19 }


   --           The Interface Stack Group
   --
   -- Implementation of this group is mandatory for all systems
   --

   ifStackTable  OBJECT-TYPE
        SYNTAX        SEQUENCE OF IfStackEntry
        MAX-ACCESS    not-accessible
        STATUS        current
        DESCRIPTION
               "The table containing information on the relationships
               between the multiple sub-layers of network interfaces.
               In particular, it contains information on which sub-
               layers run 'on top of' which other sub-layers, where
               each sub-layer corresponds to a conceptual row in the
               ifTable.  For example, when the sub-layer with ifIndex
               value x runs over the sub-layer with ifIndex value y,
               then this table contains:

                 ifStackStatus.x.y=active

               For each ifIndex value, I, which identifies an active
               interface, there are always at least two instantiated
               rows in this table associated with I.  For one of
               these rows, I is the value of ifStackHigherLayer; for
               the other, I is the value of ifStackLowerLayer.  (If I
               is not involved in multiplexing, then these are the
               only two rows associated with I.)

               For example, two rows exist even for an interface
               which has no others stacked on top or below it:

                 ifStackStatus.0.x=active
                 ifStackStatus.x.0=active "
        ::= { ifMIBObjects 2 }


   ifStackEntry  OBJECT-TYPE
        SYNTAX        IfStackEntry
        MAX-ACCESS    not-accessible
        STATUS        current
        DESCRIPTION
               "Information on a particular relationship between two
               sub-layers, specifying that one sub-layer runs on
               'top' of the other sub-layer.  Each sub-layer
               corresponds to a conceptual row in the ifTable."
        INDEX { ifStackHigherLayer, ifStackLowerLayer }
        ::= { ifStackTable 1 }


   IfStackEntry ::=
       SEQUENCE {
           ifStackHigherLayer  Integer32,
           ifStackLowerLayer   Integer32,
           ifStackStatus       RowStatus
        }

   ifStackHigherLayer  OBJECT-TYPE
        SYNTAX        Integer32
        MAX-ACCESS    not-accessible
        STATUS        current
        DESCRIPTION
               "The value of ifIndex corresponding to the higher
               sub-layer of the relationship, i.e., the sub-layer
               which runs on 'top' of the sub-layer identified by the
               corresponding instance of ifStackLowerLayer.  If there
               is no higher sub-layer (below the internetwork layer),
               then this object has the value 0."
        ::= { ifStackEntry 1 }


   ifStackLowerLayer  OBJECT-TYPE
        SYNTAX        Integer32
        MAX-ACCESS    not-accessible
        STATUS        current
        DESCRIPTION
               "The value of ifIndex corresponding to the lower sub-
               layer of the relationship, i.e., the sub-layer which
               runs 'below' the sub-layer identified by the
               corresponding instance of ifStackHigherLayer.  If
               there is no lower sub-layer, then this object has the
               value 0."
        ::= { ifStackEntry 2 }


   ifStackStatus  OBJECT-TYPE
       SYNTAX         RowStatus
       MAX-ACCESS     read-create
       STATUS         current
       DESCRIPTION
               "The status of the relationship between two sub-
               layers.

               Changing the value of this object from 'active' to
               'notInService' or 'destroy' will likely have
               consequences up and down the interface stack.  Thus,
               write access to this object is likely to be
               inappropriate for some types of interfaces, and many
               implementations will choose not to support write-
               access for any type of interface."
       ::= { ifStackEntry 3 }

--   ifStackLastChange OBJECT-TYPE
--       SYNTAX         TimeTicks
--       MAX-ACCESS     read-only
--       STATUS         current
--       DESCRIPTION
--               "The value of sysUpTime at the time of the last change
--               of the (whole) interface stack.  A change of the
--               interface stack is defined to be any creation,
--               deletion, or change in value of any instance of
--               ifStackStatus.  If the interface stack has been
--               unchanged since the last re-initialization of the
--               local network management subsystem, then this object
--               contains a zero value."
--       ::= { ifMIBObjects 6 }

   --   Generic Receive Address Table
   --
   -- This group of objects is mandatory for all types of
   -- interfaces which can receive packets/frames addressed to
   -- more than one address.
   --
   -- This table replaces the ifExtnsRcvAddr table.  The main
   -- difference is that this table makes use of the RowStatus
   -- textual convention, while ifExtnsRcvAddr did not.

--   ifRcvAddressTable  OBJECT-TYPE
--       SYNTAX      SEQUENCE OF IfRcvAddressEntry
--       MAX-ACCESS  not-accessible
--       STATUS      current
--       DESCRIPTION
--               "This table contains an entry for each address
--               (broadcast, multicast, or uni-cast) for which the
--               system will receive packets/frames on a particular
--               interface, except as follows:
--
--               - for an interface operating in promiscuous mode,
--               entries are only required for those addresses for
--               which the system would receive frames were it not
--               operating in promiscuous mode.
--
--               - for 802.5 functional addresses, only one entry is
--               required, for the address which has the functional
--               address bit ANDed with the bit mask of all functional
--               addresses for which the interface will accept frames.
--
--               A system is normally able to use any unicast address
--               which corresponds to an entry in this table as a
--               source address."
--       ::= { ifMIBObjects 4 }

--
--   ifRcvAddressEntry  OBJECT-TYPE
--       SYNTAX      IfRcvAddressEntry
--       MAX-ACCESS  not-accessible
--       STATUS      current
--       DESCRIPTION
--               "A list of objects identifying an address for which
--               the system will accept packets/frames on the
--               particular interface identified by the index value
--               ifIndex."
--       INDEX  { ifIndex, ifRcvAddressAddress }
--       ::= { ifRcvAddressTable 1 }
--
--   IfRcvAddressEntry ::=
--       SEQUENCE {
--           ifRcvAddressAddress   PhysAddress,
--           ifRcvAddressStatus    RowStatus,
--           ifRcvAddressType      INTEGER
--       }
--
--   ifRcvAddressAddress OBJECT-TYPE
--       SYNTAX      PhysAddress
--       MAX-ACCESS  not-accessible
--       STATUS      current
--       DESCRIPTION
--               "An address for which the system will accept
--               packets/frames on this entry's interface."
--
--       ::= { ifRcvAddressEntry 1 }
--
--   ifRcvAddressStatus OBJECT-TYPE
--       SYNTAX      RowStatus
--       MAX-ACCESS  read-create
--       STATUS      current
--       DESCRIPTION
--               "This object is used to create and delete rows in the
--               ifRcvAddressTable."
--
--       ::= { ifRcvAddressEntry 2 }
--
--   ifRcvAddressType OBJECT-TYPE
--       SYNTAX      INTEGER {
--                       other(1),
--                       volatile(2),
--                       nonVolatile(3)
--                   }
--
--       MAX-ACCESS  read-create
--       STATUS      current
--       DESCRIPTION
--               "This object has the value nonVolatile(3) for those
--               entries in the table which are valid and will not be
--               deleted by the next restart of the managed system.
--               Entries having the value volatile(2) are valid and
--               exist, but have not been saved, so that will not exist
--               after the next restart of the managed system.  Entries
--               having the value other(1) are valid and exist but are
--               not classified as to whether they will continue to
--               exist after the next restart."
--
--       DEFVAL  { volatile }
--       ::= { ifRcvAddressEntry 3 }
--

   -- definition of interface-related traps.

   linkDown NOTIFICATION-TYPE
           OBJECTS { ifIndex, ifAdminStatus, ifOperStatus }
           STATUS  current
           DESCRIPTION
               "A linkDown trap signifies that the SNMPv2 entity,
               acting in an agent role, has detected that the
               ifOperStatus object for one of its communication links
               is about to enter the down state from some other state
               (but not from the notPresent state).  This other state
               is indicated by the included value of ifOperStatus."
       ::= { snmpTraps 3 }

   linkUp NOTIFICATION-TYPE
           OBJECTS { ifIndex, ifAdminStatus, ifOperStatus }
           STATUS  current
           DESCRIPTION
               "A linkDown trap signifies that the SNMPv2 entity,
               acting in an agent role, has detected that the
               ifOperStatus object for one of its communication links
               left the down state and transitioned into some other
               state (but not into the notPresent state).  This other
               state is indicated by the included value of
               ifOperStatus."
       ::= { snmpTraps 4 }

   -- conformance information

--   ifConformance OBJECT IDENTIFIER ::= { ifMIB 2 }

--   ifGroups      OBJECT IDENTIFIER ::= { ifConformance 1 }
--   ifCompliances OBJECT IDENTIFIER ::= { ifConformance 2 }

   -- compliance statements

--   ifCompliance2 MODULE-COMPLIANCE
--       STATUS  current
--       DESCRIPTION
--               "The compliance statement for SNMPv2 entities which
--               have network interfaces."
--
--       MODULE
				-- this module
--           MANDATORY-GROUPS { ifGeneralInformationGroup, ifStackGroup2,
--                              ifCounterDiscontinuityGroup }
--
--           GROUP       ifFixedLengthGroup
--           DESCRIPTION
--               "This group is mandatory for all network interfaces
--               which are character-oriented or transmit data in
--               fixed-length transmission units."
--
--           GROUP       ifHCFixedLengthGroup
--           DESCRIPTION
--               "This group is mandatory only for those network
--               interfaces which are character-oriented or transmit
--               data in fixed-length transmission units, and for which
--               the value of the corresponding instance of ifSpeed is
--               greater than 20,000,000 bits/second."
--
--           GROUP       ifPacketGroup
--           DESCRIPTION
--               "This group is mandatory for all network interfaces
--               which are packet-oriented."
--
--           GROUP       ifHCPacketGroup
--           DESCRIPTION
--               "This group is mandatory only for those network
--               interfaces which are packet-oriented and for which the
--               value of the corresponding instance of ifSpeed is
--               greater than 650,000,000 bits/second."
--
--           GROUP       ifRcvAddressGroup
--           DESCRIPTION
--               "The applicability of this group MUST be defined by
--               the media-specific MIBs.  Media-specific MIBs must
--               define the exact meaning, use, and semantics of the
--               addresses in this group."
--
--           OBJECT      ifLinkUpDownTrapEnable
--           MIN-ACCESS  read-only
--           DESCRIPTION
--               "Write access is not required."
--
--           OBJECT      ifPromiscuousMode
--           MIN-ACCESS  read-only
--           DESCRIPTION
--               "Write access is not required."
--
--           OBJECT      ifStackStatus
--           SYNTAX      INTEGER { active(1) }
						-- subset of RowStatus
--           MIN-ACCESS  read-only
--           DESCRIPTION
--               "Write access is not required, and only one of the six
--               enumerated values for the RowStatus textual convention
--               need be supported, specifically: active(1)."
--
--           OBJECT       ifAdminStatus
--           SYNTAX       INTEGER { up(1), down(2) }
--           MIN-ACCESS   read-only
--           DESCRIPTION
--               "Write access is not required, nor is support for the
--               value testing(3)."
--
--           OBJECT       ifAlias
--           MIN-ACCESS   read-only
--           DESCRIPTION
--               "Write access is not required."
--
--       ::= { ifCompliances 2 }

   -- units of conformance

--   ifGeneralInformationGroup    OBJECT-GROUP
--       OBJECTS { ifIndex, ifDescr, ifType, ifSpeed, ifPhysAddress,
--                 ifAdminStatus, ifOperStatus, ifLastChange,
--                 ifLinkUpDownTrapEnable, ifConnectorPresent,
--                 ifHighSpeed, ifName, ifNumber, ifAlias,
--                 ifTableLastChange }
--       STATUS  current
--       DESCRIPTION
--               "A collection of objects providing information
--               applicable to all network interfaces."
--       ::= { ifGroups 10 }

   -- the following five groups are mutually exclusive; at most
   -- one of these groups is implemented for any interface

--   ifFixedLengthGroup    OBJECT-GROUP
--       OBJECTS { ifInOctets, ifOutOctets, ifInUnknownProtos,
--                 ifInErrors, ifOutErrors }
--       STATUS  current
--       DESCRIPTION
--               "A collection of objects providing information
--               specific to non-high speed (non-high speed interfaces
--               transmit and receive at speeds less than or equal to
--               20,000,000 bits/second) character-oriented or fixed-
--               length-transmission network interfaces."
--       ::= { ifGroups 2 }

--   ifHCFixedLengthGroup    OBJECT-GROUP
--       OBJECTS { ifHCInOctets, ifHCOutOctets,
--                 ifInOctets, ifOutOctets, ifInUnknownProtos,
--                 ifInErrors, ifOutErrors }
--       STATUS  current
--       DESCRIPTION
--               "A collection of objects providing information
--               specific to high speed (greater than 20,000,000
--               bits/second) character-oriented or fixed-length-
--               transmission network interfaces."
--       ::= { ifGroups 3 }

--   ifPacketGroup    OBJECT-GROUP
--       OBJECTS { ifInOctets, ifOutOctets, ifInUnknownProtos,
--                 ifInErrors, ifOutErrors,
--                 ifMtu, ifInUcastPkts, ifInMulticastPkts,
--                 ifInBroadcastPkts, ifInDiscards,
--                 ifOutUcastPkts, ifOutMulticastPkts,
--                 ifOutBroadcastPkts, ifOutDiscards,
--                 ifPromiscuousMode }
--       STATUS  current
--       DESCRIPTION
--               "A collection of objects providing information
--               specific to non-high speed (non-high speed interfaces
--               transmit and receive at speeds less than or equal to
--               20,000,000 bits/second) packet-oriented network
--               interfaces."
--       ::= { ifGroups 4 }

--   ifHCPacketGroup    OBJECT-GROUP
--       OBJECTS { ifHCInOctets, ifHCOutOctets,
--                 ifInOctets, ifOutOctets, ifInUnknownProtos,
--                 ifInErrors, ifOutErrors,
--                 ifMtu, ifInUcastPkts, ifInMulticastPkts,
--                 ifInBroadcastPkts, ifInDiscards,
--                 ifOutUcastPkts, ifOutMulticastPkts,
--                 ifOutBroadcastPkts, ifOutDiscards,
--                 ifPromiscuousMode }
--       STATUS  current
--       DESCRIPTION
--               "A collection of objects providing information
--               specific to high speed (greater than 20,000,000
--               bits/second but less than or equal to 650,000,000
--               bits/second) packet-oriented network interfaces."
--       ::= { ifGroups 5 }

--   ifVHCPacketGroup    OBJECT-GROUP
--       OBJECTS { ifHCInUcastPkts, ifHCInMulticastPkts,
--                 ifHCInBroadcastPkts, ifHCOutUcastPkts,
--                 ifHCOutMulticastPkts, ifHCOutBroadcastPkts,
--                 ifHCInOctets, ifHCOutOctets,
--                 ifInOctets, ifOutOctets, ifInUnknownProtos,
--                 ifInErrors, ifOutErrors,
--                 ifMtu, ifInUcastPkts, ifInMulticastPkts,
--                 ifInBroadcastPkts, ifInDiscards,
--                 ifOutUcastPkts, ifOutMulticastPkts,
--                 ifOutBroadcastPkts, ifOutDiscards,
--                 ifPromiscuousMode }
--       STATUS  current
--       DESCRIPTION
--               "A collection of objects providing information
--               specific to higher speed (greater than 650,000,000
--               bits/second) packet-oriented network interfaces."
--       ::= { ifGroups 6 }

--   ifRcvAddressGroup    OBJECT-GROUP
--       OBJECTS { ifRcvAddressStatus, ifRcvAddressType }
--       STATUS  current
--       DESCRIPTION
--               "A collection of objects providing information on the
--               multiple addresses which an interface receives."
--       ::= { ifGroups 7 }

--   ifStackGroup2    OBJECT-GROUP
--       OBJECTS { ifStackStatus, ifStackLastChange }
--       STATUS  current
--       DESCRIPTION
--               "A collection of objects providing information on the
--               layering of MIB-II interfaces."
--       ::= { ifGroups 11 }

--   ifCounterDiscontinuityGroup  OBJECT-GROUP
--       OBJECTS { ifCounterDiscontinuityTime }
--       STATUS  current
--       DESCRIPTION
--               "A collection of objects providing information
--               specific to interface counter discontinuities."
--       ::= { ifGroups 13 }

   -- Deprecated Definitions - Objects


   --
   --    The Interface Test Table
   --
   -- This group of objects is optional.  However, a media-specific
   -- MIB may make implementation of this group mandatory.
   --
   -- This table replaces the ifExtnsTestTable
   --

--   ifTestTable   OBJECT-TYPE
--       SYNTAX      SEQUENCE OF IfTestEntry
--       MAX-ACCESS  not-accessible
--       STATUS      deprecated
--       DESCRIPTION
--               "This table contains one entry per interface.  It
--               defines objects which allow a network manager to
--               instruct an agent to test an interface for various
--               faults.  Tests for an interface are defined in the
--               media-specific MIB for that interface.  After invoking
--               a test, the object ifTestResult can be read to
--               determine the outcome.  If an agent can not perform
--               the test, ifTestResult is set to so indicate.  The
--               object ifTestCode can be used to provide further
--               test-specific or interface-specific (or even
--               enterprise-specific) information concerning the
--               outcome of the test.  Only one test can be in progress
--               on each interface at any one time.  If one test is in
--               progress when another test is invoked, the second test
--               is rejected.  Some agents may reject a test when a
--               prior test is active on another interface.
--
--               Before starting a test, a manager-station must first
--               obtain 'ownership' of the entry in the ifTestTable for
--               the interface to be tested.  This is accomplished with
--               the ifTestId and ifTestStatus objects as follows:
--
--            try_again:
--                get (ifTestId, ifTestStatus)
--                while (ifTestStatus != notInUse)
--                    /*
--                     * Loop while a test is running or some other
--                     * manager is configuring a test.
--                     */
--                    short delay
--                    get (ifTestId, ifTestStatus)
--                }
--
--                /*
--                 * Is not being used right now
						-- let's compete
--                 * to see who gets it.
--                 */
--                lock_value = ifTestId
--
--                if ( set(ifTestId = lock_value, ifTestStatus = inUse,
--                         ifTestOwner = 'my-IP-address') == FAILURE)
--                    /*
--                     * Another manager got the ifTestEntry
								-- go
--                     * try again
--                     */
--                    goto try_again;
--
--                /*
--                 * I have the lock
--                 */
--                set up any test parameters.
--
--                /*
--                 * This starts the test
--                 */
--                set(ifTestType = test_to_run);
--
--                wait for test completion by polling ifTestResult
--
--                when test completes, agent sets ifTestResult
--                     agent also sets ifTestStatus = 'notInUse'
--
--                retrieve any additional test results, and ifTestId
--
--                if (ifTestId == lock_value+1) results are valid
--
--              A manager station first retrieves the value of the
--              appropriate ifTestId and ifTestStatus objects,
--              periodically repeating the retrieval if necessary,
--              until the value of ifTestStatus is 'notInUse'.  The
--              manager station then tries to set the same ifTestId
--              object to the value it just retrieved, the same
--              ifTestStatus object to 'inUse', and the corresponding
--              ifTestOwner object to a value indicating itself.  If
--              the set operation succeeds then the manager has
--              obtained ownership of the ifTestEntry, and the value of
--              the ifTestId object is incremented by the agent (per
--              the semantics of TestAndIncr).  Failure of the set
--              operation indicates that some other manager has
--              obtained ownership of the ifTestEntry.
--
--              Once ownership is obtained, any test parameters can be
--              setup, and then the test is initiated by setting
--              ifTestType.  On completion of the test, the agent sets
--              ifTestStatus to 'notInUse'.  Once this occurs, the
--              manager can retrieve the results.  In the (rare) event
--              that the invocation of tests by two network managers
--              were to overlap, then there would be a possibility that
--              the first test's results might be overwritten by the
--              second test's results prior to the first results being
--              read.  This unlikely circumstance can be detected by a
--              network manager retrieving ifTestId at the same time as
--              retrieving the test results, and ensuring that the
--              results are for the desired request.
--
--              If ifTestType is not set within an abnormally long
--              period of time after ownership is obtained, the agent
--              should time-out the manager, and reset the value of the
--              ifTestStatus object back to 'notInUse'.  It is
--              suggested that this time-out period be 5 minutes.
--
--              In general, a management station must not retransmit a
--              request to invoke a test for which it does not receive
--              a response; instead, it properly inspects an agent's
--              MIB to determine if the invocation was successful.
--              Only if the invocation was unsuccessful, is the
--              invocation request retransmitted.
--
--              Some tests may require the interface to be taken off-
--              line in order to execute them, or may even require the
--              agent to reboot after completion of the test.  In these
--              circumstances, communication with the management
--              station invoking the test may be lost until after
--              completion of the test.  An agent is not required to
--              support such tests.  However, if such tests are
--              supported, then the agent should make every effort to
--              transmit a response to the request which invoked the
--              test prior to losing communication.  When the agent is
--              restored to normal service, the results of the test are
--              properly made available in the appropriate objects.
--              Note that this requires that the ifIndex value assigned
--              to an interface must be unchanged even if the test
--              causes a reboot.  An agent must reject any test for
--              which it cannot, perhaps due to resource constraints,
--              make available at least the minimum amount of
--              information after that test completes."
--       ::= { ifMIBObjects 3 }

--   ifTestEntry OBJECT-TYPE
--       SYNTAX       IfTestEntry
--       MAX-ACCESS   not-accessible
--       STATUS       deprecated
--       DESCRIPTION
--               "An entry containing objects for invoking tests on an
--               interface."
--       AUGMENTS  { ifEntry }
--       ::= { ifTestTable 1 }
--
--   IfTestEntry ::=
--       SEQUENCE {
--           ifTestId           TestAndIncr,
--           ifTestStatus       INTEGER,
--           ifTestType         AutonomousType,
--           ifTestResult       INTEGER,
--           ifTestCode         OBJECT IDENTIFIER,
--           ifTestOwner        OwnerString
--       }

--   ifTestId         OBJECT-TYPE
--       SYNTAX       TestAndIncr
--       MAX-ACCESS   read-write
--       STATUS       deprecated
--       DESCRIPTION
--               "This object identifies the current invocation of the
--               interface's test."
--       ::= { ifTestEntry 1 }

--   ifTestStatus     OBJECT-TYPE
--       SYNTAX       INTEGER { notInUse(1), inUse(2) }
--       MAX-ACCESS   read-write
--       STATUS       deprecated
--       DESCRIPTION
--               "This object indicates whether or not some manager
--               currently has the necessary 'ownership' required to
--               invoke a test on this interface.  A write to this
--               object is only successful when it changes its value
--               from 'notInUse(1)' to 'inUse(2)'.  After completion of
--               a test, the agent resets the value back to
--               'notInUse(1)'."
--       ::= { ifTestEntry 2 }

--   ifTestType       OBJECT-TYPE
--       SYNTAX       AutonomousType
--       MAX-ACCESS   read-write
--       STATUS       deprecated
--       DESCRIPTION
--               "A control variable used to start and stop operator-
--               initiated interface tests.  Most OBJECT IDENTIFIER
--               values assigned to tests are defined elsewhere, in
--               association with specific types of interface.
--               However, this document assigns a value for a full-
--               duplex loopback test, and defines the special meanings
--               of the subject identifier:
--
--                   noTest  OBJECT IDENTIFIER ::= { 0 0 }
--
--               When the value noTest is written to this object, no
--               action is taken unless a test is in progress, in which
--               case the test is aborted.  Writing any other value to
--               this object is only valid when no test is currently in
--               progress, in which case the indicated test is
--               initiated.
--
--               When read, this object always returns the most recent
--               value that ifTestType was set to.  If it has not been
--               set since the last initialization of the network
--               management subsystem on the agent, a value of noTest
--               is returned."
--       ::= { ifTestEntry 3 }

--   ifTestResult  OBJECT-TYPE
--       SYNTAX       INTEGER {
--                        none(1),
					-- no test yet requested
--                        success(2),
--                        inProgress(3),
--                        notSupported(4),
--                        unAbleToRun(5),
					-- due to state of system
--                        aborted(6),
--                        failed(7)
--                    }
--       MAX-ACCESS   read-only
--       STATUS       deprecated
--       DESCRIPTION
--               "This object contains the result of the most recently
--               requested test, or the value none(1) if no tests have
--               been requested since the last reset.  Note that this
--               facility provides no provision for saving the results
--               of one test when starting another, as could be
--               required if used by multiple managers concurrently."
--       ::= { ifTestEntry 4 }

--   ifTestCode  OBJECT-TYPE
--       SYNTAX       OBJECT IDENTIFIER
--       MAX-ACCESS   read-only
--       STATUS       deprecated
--       DESCRIPTION
--               "This object contains a code which contains more
--               specific information on the test result, for example
--               an error-code after a failed test.  Error codes and
--               other values this object may take are specific to the
--               type of interface and/or test.  The value may have the
--               semantics of either the AutonomousType or
--               InstancePointer textual conventions as defined in RFC
--               1903.  The identifier:
--
--                   testCodeUnknown  OBJECT IDENTIFIER ::= { 0 0 }
--
--               is defined for use if no additional result code is
--               available."
--       ::= { ifTestEntry 5 }

--   ifTestOwner      OBJECT-TYPE
--       SYNTAX       OwnerString
--       MAX-ACCESS   read-write
--       STATUS       deprecated
--       DESCRIPTION
--               "The entity which currently has the 'ownership'
--               required to invoke a test on this interface."
--       ::= { ifTestEntry 6 }

   -- Deprecated Definitions - Groups


--   ifGeneralGroup    OBJECT-GROUP
--       OBJECTS { ifDescr, ifType, ifSpeed, ifPhysAddress,
--                 ifAdminStatus, ifOperStatus, ifLastChange,
--                 ifLinkUpDownTrapEnable, ifConnectorPresent,
--                 ifHighSpeed, ifName }
--       STATUS  deprecated
--       DESCRIPTION
--               "A collection of objects deprecated in favour of
--               ifGeneralInformationGroup."
--       ::= { ifGroups 1 }


--   ifTestGroup    OBJECT-GROUP
--       OBJECTS { ifTestId, ifTestStatus, ifTestType,
--                 ifTestResult, ifTestCode, ifTestOwner }
--       STATUS  deprecated
--       DESCRIPTION
--               "A collection of objects providing the ability to
--               invoke tests on an interface."
--       ::= { ifGroups 8 }


--   ifStackGroup    OBJECT-GROUP
--       OBJECTS { ifStackStatus }
--       STATUS  deprecated
--       DESCRIPTION
--               "The previous collection of objects providing
--               information on the layering of MIB-II interfaces."
--       ::= { ifGroups 9 }


--   ifOldObjectsGroup    OBJECT-GROUP
--       OBJECTS { ifInNUcastPkts, ifOutNUcastPkts,
--                 ifOutQLen, ifSpecific }
--       STATUS  deprecated
--       DESCRIPTION
--               "The collection of objects deprecated from the
--               original MIB-II interfaces group."
--       ::= { ifGroups 12 }


   -- Deprecated Definitions - Compliance

--   ifCompliance MODULE-COMPLIANCE
--       STATUS  deprecated
--       DESCRIPTION
--               "The previous compliance statement for SNMPv2 entities
--               which have network interfaces."
--
--       MODULE
		-- this module
--           MANDATORY-GROUPS { ifGeneralGroup, ifStackGroup }
--
--           GROUP       ifFixedLengthGroup
--           DESCRIPTION
--               "This group is mandatory for all network interfaces
--               which are character-oriented or transmit data in
--               fixed-length transmission units."
--
--           GROUP       ifHCFixedLengthGroup
--           DESCRIPTION
--               "This group is mandatory only for those network
--               interfaces which are character-oriented or transmit
--               data in fixed-length transmission units, and for which
--               the value of the corresponding instance of ifSpeed is
--               greater than 20,000,000 bits/second."
--
--           GROUP       ifPacketGroup
--           DESCRIPTION
--               "This group is mandatory for all network interfaces
--               which are packet-oriented."
--
--           GROUP       ifHCPacketGroup
--           DESCRIPTION
--               "This group is mandatory only for those network
--               interfaces which are packet-oriented and for which the
--               value of the corresponding instance of ifSpeed is
--               greater than 650,000,000 bits/second."
--
--           GROUP       ifTestGroup
--           DESCRIPTION
--               "This group is optional.  Media-specific MIBs which
--               require interface tests are strongly encouraged to use
--               this group for invoking tests and reporting results.
--               A medium specific MIB which has mandatory tests may
--               make implementation of this group mandatory."
--
--           GROUP       ifRcvAddressGroup
--           DESCRIPTION
--               "The applicability of this group MUST be defined by
--               the media-specific MIBs.  Media-specific MIBs must
--               define the exact meaning, use, and semantics of the
--               addresses in this group."
--
--           OBJECT      ifLinkUpDownTrapEnable
--           MIN-ACCESS  read-only
--           DESCRIPTION
--               "Write access is not required."

--           OBJECT      ifPromiscuousMode
--           MIN-ACCESS  read-only
--           DESCRIPTION
--               "Write access is not required."

--           OBJECT      ifStackStatus
--           SYNTAX      INTEGER { active(1) }
						-- subset of RowStatus
--           MIN-ACCESS  read-only
--           DESCRIPTION
--               "Write access is not required, and only one of the six
--               enumerated values for the RowStatus textual convention
--               need be supported, specifically: active(1)."
--           OBJECT       ifAdminStatus
--           SYNTAX       INTEGER { up(1), down(2) }
--           MIN-ACCESS   read-only
--           DESCRIPTION
--               "Write access is not required, nor is support for the
--               value testing(3)."
--       ::= { ifCompliances 1 }


   END


--------------------------------------------------------------------------
-- Rfc1573a, IANAifType-MIB, all the ifTypes defined here
--------------------------------------------------------------------------
   IANAifType-MIB DEFINITIONS ::= BEGIN

   IMPORTS
       MODULE-IDENTITY, mib-2              FROM SNMPv2-SMI
       TEXTUAL-CONVENTION                  FROM SNMPv2-TC;
--       mib-2                               FROM RFC1213-MIB;

   ianaifType MODULE-IDENTITY
       LAST-UPDATED "9311082155Z"
       ORGANIZATION "IANA"
       CONTACT-INFO

                  "        Internet Assigned Numbers Authority

                   Postal: USC/Information Sciences Institute
                           4676 Admiralty Way, Marina del Rey, CA 90292

                   Tel:    +1  310 822 1511
                   E-Mail: iana@isi.edu"
       DESCRIPTION
               "The MIB module which defines the IANAifType textual
               convention, and thus the enumerated values of the
               ifType object defined in MIB-II's ifTable."
       ::= { mib-2 30 }


   IANAifType ::= TEXTUAL-CONVENTION
       STATUS       current
       DESCRIPTION
               "This data type is used as the syntax of the ifType
               object in the (updated) definition of MIB-II's
               ifTable.
               The definition of this textual convention with the
               addition of newly assigned values is published
               periodically by the IANA, in either the Assigned
               Numbers RFC, or some derivative of it specific to
               Internet Network Management number assignments.  (The
               latest arrangements can be obtained by contacting the
               IANA.)

               Requests for new values should be made to IANA via
               email (iana@isi.edu).

               The relationship between the assignment of ifType
               values and of OIDs to particular media-specific MIBs
               is solely the purview of IANA and is subject to change
               without notice.  Quite often, a media-specific MIB's
               OID-subtree assignment within MIB-II's 'transmission'
               subtree will be the same as its ifType value.
               However, in some circumstances this will not be the
               case, and implementors must not pre-assume any
               specific relationship between ifType values and
               transmission subtree OIDs."
       SYNTAX  INTEGER {
                   other(1),          -- none of the following
                   regular1822(2),
                   hdh1822(3),
                   ddnX25(4),
                   rfc877x25(5),
                   ethernetCsmacd(6),
                   iso88023Csmacd(7),
                   iso88024TokenBus(8),
                   iso88025TokenRing(9),
                   iso88026Man(10),
                   starLan(11),
                   proteon10Mbit(12),
                   proteon80Mbit(13),
                   hyperchannel(14),
                   fddi(15),
                   lapb(16),
                   sdlc(17),
                   ds1(18),           -- DS1/E1 (RFC 1406)
                   e1(19),            -- obsolete
                   basicISDN(20),
                   primaryISDN(21),
                   propPointToPointSerial(22), -- proprietary serial
                   ppp(23),
                   softwareLoopback(24),
                   eon(25),            -- CLNP over IP (RFC 1070)
                   ethernet3Mbit(26),
                   nsip(27),           -- XNS over IP
                   slip(28),           -- generic SLIP
                   ultra(29),          -- ULTRA technologies
                   ds3(30),            -- T-3
                   sip(31),            -- SMDS
                   frameRelay(32),    -- DTE only
                   rs232(33),
                   para(34),           -- parallel-port
                   arcnet(35),         -- arcnet
                   arcnetPlus(36),     -- arcnet plus
                   atm(37),            -- ATM cells
                   miox25(38),
                   sonet(39),          -- SONET or SDH
                   x25ple(40),
                   iso88022llc(41),
                   localTalk(42),
                   smdsDxi(43),
                   frameRelayService(44),  -- Frame relay DCE
                   v35(45),
                   hssi(46),
                   hippi(47),
                   modem(48),          -- Generic modem
                   aal5(49),           -- AAL5 over ATM
                   sonetPath(50),
                   sonetVT(51),
                   smdsIcip(52),       -- SMDS InterCarrier Interface
                   propVirtual(53),    -- proprietary virtual/internal
                   propMultiplexor(54), -- proprietary multiplexing
				   --
				   -- According to RFC2662 4.1
				   --
				   adsl(94),			-- Asymmetric Digital Subscriber Loop
		           adslInterleave(124), -- ADSL Interleaved Channel
				   adslFast(125),        -- ADSL Fast Channel
				   --
				   hdsl2 (168),			-- High Bit-Rate DSL, 2nd generation
                   shdsl (169)			-- Multirate HDSL2
				   --
               }

   END


--------------------------------------------------------------------------
-- Rfc2261, SNMP-FRAMEWORK-MIB, needed by Atm Mibs
--------------------------------------------------------------------------
   SNMP-FRAMEWORK-MIB DEFINITIONS ::= BEGIN

   IMPORTS
       MODULE-IDENTITY, OBJECT-TYPE,
       OBJECT-IDENTITY,
       snmpModules                           FROM SNMPv2-SMI
       TEXTUAL-CONVENTION                    FROM SNMPv2-TC
       MODULE-COMPLIANCE, OBJECT-GROUP       FROM SNMPv2-CONF;

   snmpFrameworkMIB MODULE-IDENTITY
       LAST-UPDATED "9901190000Z"            -- 19 January 1999
       ORGANIZATION "SNMPv3 Working Group"
       CONTACT-INFO "WG-EMail:   snmpv3@tis.com
                     Subscribe:  majordomo@tis.com
                                 In message body:  subscribe snmpv3

                     Chair:      Russ Mundy
                                 TIS Labs at Network Associates
                     postal:     3060 Washington Rd
                                 Glenwood MD 21738
                                 USA
                     EMail:      mundy@tis.com
                     phone:      +1 301-854-6889

                     Co-editor   Dave Harrington
                                 Cabletron Systems, Inc.
                     postal:     Post Office Box 5005
                                 Mail Stop: Durham
                                 35 Industrial Way
                                 Rochester, NH 03867-5005
                                 USA
                     EMail:      dbh@ctron.com
                     phone:      +1 603-337-7357

                     Co-editor   Randy Presuhn
                                 BMC Software, Inc.
                     postal:     965 Stewart Drive
                                 Sunnyvale, CA 94086
                                 USA
                     EMail:      randy_presuhn@bmc.com
                     phone:      +1 408-616-3100

                     Co-editor:  Bert Wijnen
                                 IBM T.J. Watson Research
                     postal:     Schagen 33
                                 3461 GL Linschoten
                                 Netherlands
                     EMail:      wijnen@vnet.ibm.com
                     phone:      +31 348-432-794
                    "
       DESCRIPTION  "The SNMP Management Architecture MIB"
   -- Revision History

       REVISION     "9901190000Z"            -- 19 January 1999
       DESCRIPTION  "Updated editors' addresses, fixed typos.
                     Published as RFC2571.
                    "
       REVISION     "9711200000Z"            -- 20 November 1997
       DESCRIPTION  "The initial version, published in RFC 2271.
                    "
       ::= { snmpModules 10 }

   -- Textual Conventions used in the SNMP Management Architecture ***

   SnmpEngineID ::= TEXTUAL-CONVENTION
       STATUS       current
       DESCRIPTION "An SNMP engine's administratively-unique identifier.
                    Objects of this type are for identification, not for
                    addressing, even though it is possible that an
                    address may have been used in the generation of
                    a specific value.

                    The value for this object may not be all zeros or
                    all 'ff'H or the empty (zero length) string.

                    The initial value for this object may be configured
                    via an operator console entry or via an algorithmic
                    function.  In the latter case, the following
                    example algorithm is recommended.

                    In cases where there are multiple engines on the
                    same system, the use of this algorithm is NOT
                    appropriate, as it would result in all of those
                    engines ending up with the same ID value.

                    1) The very first bit is used to indicate how the
                       rest of the data is composed.

                       0 - as defined by enterprise using former methods
                           that existed before SNMPv3. See item 2 below.

                       1 - as defined by this architecture, see item 3
                           below.

                       Note that this allows existing uses of the
                       engineID (also known as AgentID [RFC1910]) to
                       co-exist with any new uses.

                    2) The snmpEngineID has a length of 12 octets.

                       The first four octets are set to the binary
                       equivalent of the agent's SNMP management
                       private enterprise number as assigned by the
                       Internet Assigned Numbers Authority (IANA).
                       For example, if Acme Networks has been assigned
                       { enterprises 696 }, the first four octets would
                       be assigned '000002b8'H.

                       The remaining eight octets are determined via
                       one or more enterprise-specific methods. Such
                       methods must be designed so as to maximize the
                       possibility that the value of this object will
                       be unique in the agent's administrative domain.
                       For example, it may be the IP address of the SNMP
                       entity, or the MAC address of one of the
                       interfaces, with each address suitably padded
                       with random octets.  If multiple methods are
                       defined, then it is recommended that the first
                       octet indicate the method being used and the
                       remaining octets be a function of the method.

                    3) The length of the octet strings varies.

                       The first four octets are set to the binary
                       equivalent of the agent's SNMP management
                       private enterprise number as assigned by the
                       Internet Assigned Numbers Authority (IANA).
                       For example, if Acme Networks has been assigned
                       { enterprises 696 }, the first four octets would
                       be assigned '000002b8'H.

                       The very first bit is set to 1. For example, the
                       above value for Acme Networks now changes to be
                       '800002b8'H.

                       The fifth octet indicates how the rest (6th and
                       following octets) are formatted. The values for
                       the fifth octet are:

                         0     - reserved, unused.

                         1     - IPv4 address (4 octets)
                                 lowest non-special IP address

                         2     - IPv6 address (16 octets)
                                 lowest non-special IP address

                         3     - MAC address (6 octets)
                                 lowest IEEE MAC address, canonical
                                 order

                         4     - Text, administratively assigned
                                 Maximum remaining length 27

                         5     - Octets, administratively assigned
                                 Maximum remaining length 27

                         6-127 - reserved, unused

                       127-255 - as defined by the enterprise
                                 Maximum remaining length 27
                   "
       SYNTAX       OCTET STRING (SIZE(5..32))

   SnmpSecurityModel ::= TEXTUAL-CONVENTION
       STATUS       current
       DESCRIPTION "An identifier that uniquely identifies a
                    securityModel of the Security Subsystem within the
                    SNMP Management Architecture.

                    The values for securityModel are allocated as
                    follows:

                    - The zero value is reserved.
                    - Values between 1 and 255, inclusive, are reserved
                      for standards-track Security Models and are
                      managed by the Internet Assigned Numbers Authority
                      (IANA).
                    - Values greater than 255 are allocated to
                      enterprise-specific Security Models.  An
                      enterprise-specific securityModel value is defined
                      to be:

                      enterpriseID * 256 + security model within
                      enterprise

                      For example, the fourth Security Model defined by
                      the enterprise whose enterpriseID is 1 would be
                      260.

                    This scheme for allocation of securityModel
                    values allows for a maximum of 255 standards-
                    based Security Models, and for a maximum of
                    255 Security Models per enterprise.

                    It is believed that the assignment of new
                    securityModel values will be rare in practice
                    because the larger the number of simultaneously
                    utilized Security Models, the larger the
                    chance that interoperability will suffer.
                    Consequently, it is believed that such a range
                    will be sufficient.  In the unlikely event that
                    the standards committee finds this number to be
                    insufficient over time, an enterprise number
                    can be allocated to obtain an additional 255
                    possible values.

                    Note that the most significant bit must be zero;
                    hence, there are 23 bits allocated for various
                    organizations to design and define non-standard
                    securityModels.  This limits the ability to
                    define new proprietary implementations of Security
                    Models to the first 8,388,608 enterprises.

                    It is worthwhile to note that, in its encoded
                    form, the securityModel value will normally
                    require only a single byte since, in practice,
                    the leftmost bits will be zero for most messages
                    and sign extension is suppressed by the encoding
                    rules.

                    As of this writing, there are several values
                    of securityModel defined for use with SNMP or
                    reserved for use with supporting MIB objects.
                    They are as follows:

                        0  reserved for 'any'
                        1  reserved for SNMPv1
                        2  reserved for SNMPv2c
                        3  User-Based Security Model (USM)
                   "
       SYNTAX       INTEGER(0 .. 2147483647)

   SnmpMessageProcessingModel ::= TEXTUAL-CONVENTION
       STATUS       current
       DESCRIPTION "An identifier that uniquely identifies a Message
                    Processing Model of the Message Processing
                    Subsystem within a SNMP Management Architecture.
                    The values for messageProcessingModel are
                    allocated as follows:

                    - Values between 0 and 255, inclusive, are
                      reserved for standards-track Message Processing
                      Models and are managed by the Internet Assigned
                      Numbers Authority (IANA).

                    - Values greater than 255 are allocated to
                      enterprise-specific Message Processing Models.
                      An enterprise messageProcessingModel value is
                      defined to be:

                      enterpriseID * 256 +
                           messageProcessingModel within enterprise

                      For example, the fourth Message Processing Model
                      defined by the enterprise whose enterpriseID
                      is 1 would be 260.

                    This scheme for allocating messageProcessingModel
                    values allows for a maximum of 255 standards-
                    based Message Processing Models, and for a
                    maximum of 255 Message Processing Models per
                    enterprise.

                    It is believed that the assignment of new
                    messageProcessingModel values will be rare
                    in practice because the larger the number of
                    simultaneously utilized Message Processing Models,
                    the larger the chance that interoperability
                    will suffer. It is believed that such a range
                    will be sufficient.  In the unlikely event that
                    the standards committee finds this number to be
                    insufficient over time, an enterprise number
                    can be allocated to obtain an additional 256
                    possible values.

                    Note that the most significant bit must be zero;
                    hence, there are 23 bits allocated for various
                    organizations to design and define non-standard
                    messageProcessingModels.  This limits the ability
                    to define new proprietary implementations of
                    Message Processing Models to the first 8,388,608
                    enterprises.

                    It is worthwhile to note that, in its encoded
                    form, the messageProcessingModel value will
                    normally require only a single byte since, in
                    practice, the leftmost bits will be zero for
                    most messages and sign extension is suppressed
                    by the encoding rules.

                    As of this writing, there are several values of
                    messageProcessingModel defined for use with SNMP.
                    They are as follows:

                        0  reserved for SNMPv1
                        1  reserved for SNMPv2c
                        2  reserved for SNMPv2u and SNMPv2*
                        3  reserved for SNMPv3
                   "
       SYNTAX       INTEGER(0 .. 2147483647)

   SnmpSecurityLevel ::= TEXTUAL-CONVENTION
       STATUS       current
       DESCRIPTION "A Level of Security at which SNMP messages can be
                    sent or with which operations are being processed;
                    in particular, one of:

                      noAuthNoPriv - without authentication and
                                     without privacy,
                      authNoPriv   - with authentication but
                                     without privacy,
                      authPriv     - with authentication and
                                     with privacy.

                    These three values are ordered such that
                    noAuthNoPriv is less than authNoPriv and
                    authNoPriv is less than authPriv.
                   "
       SYNTAX       INTEGER { noAuthNoPriv(1),
                              authNoPriv(2),
                              authPriv(3)
                            }

   SnmpAdminString ::= TEXTUAL-CONVENTION
       DISPLAY-HINT "255a"
       STATUS       current
       DESCRIPTION "An octet string containing administrative
                    information, preferably in human-readable form.

                    To facilitate internationalization, this
                    information is represented using the ISO/IEC
                    IS 10646-1 character set, encoded as an octet
                    string using the UTF-8 transformation format
                    described in [RFC2279].

                    Since additional code points are added by
                    amendments to the 10646 standard from time
                    to time, implementations must be prepared to
                    encounter any code point from 0x00000000 to
                    0x7fffffff.  Byte sequences that do not
                    correspond to the valid UTF-8 encoding of a
                    code point or are outside this range are
                    prohibited.

                    The use of control codes should be avoided.

                    When it is necessary to represent a newline,
                    the control code sequence CR LF should be used.

                    The use of leading or trailing white space should
                    be avoided.

                    For code points not directly supported by user
                    interface hardware or software, an alternative
                    means of entry and display, such as hexadecimal,
                    may be provided.

                    For information encoded in 7-bit US-ASCII,
                    the UTF-8 encoding is identical to the
                    US-ASCII encoding.

                    UTF-8 may require multiple bytes to represent a
                    single character / code point; thus the length
                    of this object in octets may be different from
                    the number of characters encoded.  Similarly,
                    size constraints refer to the number of encoded
                    octets, not the number of characters represented
                    by an encoding.

                    Note that when this TC is used for an object that
                    is used or envisioned to be used as an index, then
                    a SIZE restriction MUST be specified so that the
                    number of sub-identifiers for any object instance
                    does not exceed the limit of 128, as defined by
                    [RFC1905].

                    Note that the size of an SnmpAdminString object is
                    measured in octets, not characters.
                   "
       SYNTAX       OCTET STRING (SIZE (0..255))

   -- Administrative assignments ***************************************

   snmpFrameworkAdmin
       OBJECT IDENTIFIER ::= { snmpFrameworkMIB 1 }
   snmpFrameworkMIBObjects
       OBJECT IDENTIFIER ::= { snmpFrameworkMIB 2 }
   snmpFrameworkMIBConformance
       OBJECT IDENTIFIER ::= { snmpFrameworkMIB 3 }

   -- the snmpEngine Group ********************************************

   snmpEngine OBJECT IDENTIFIER ::= { snmpFrameworkMIBObjects 1 }

   snmpEngineID     OBJECT-TYPE
       SYNTAX       SnmpEngineID
       MAX-ACCESS   read-only
       STATUS       current
       DESCRIPTION "An SNMP engine's administratively-unique identifier.
                   "
       ::= { snmpEngine 1 }

   snmpEngineBoots  OBJECT-TYPE
       SYNTAX       INTEGER (1..2147483647)
       MAX-ACCESS   read-only
       STATUS       current
       DESCRIPTION "The number of times that the SNMP engine has
                    (re-)initialized itself since snmpEngineID
                    was last configured.
                   "
       ::= { snmpEngine 2 }

   snmpEngineTime   OBJECT-TYPE
       SYNTAX       INTEGER (0..2147483647)
       UNITS        "seconds"
       MAX-ACCESS   read-only
       STATUS       current
       DESCRIPTION "The number of seconds since the value of
                    the snmpEngineBoots object last changed.
                    When incrementing this object's value would
                    cause it to exceed its maximum,
                    snmpEngineBoots is incremented as if a
                    re-initialization had occurred, and this
                    object's value consequently reverts to zero.
                   "
       ::= { snmpEngine 3 }

   snmpEngineMaxMessageSize OBJECT-TYPE
       SYNTAX       INTEGER (484..2147483647)
       MAX-ACCESS   read-only
       STATUS       current
       DESCRIPTION "The maximum length in octets of an SNMP message
                    which this SNMP engine can send or receive and
                    process, determined as the minimum of the maximum
                    message size values supported among all of the
                    transports available to and supported by the engine.
                   "
       ::= { snmpEngine 4 }


   -- Registration Points for Authentication and Privacy Protocols **

   snmpAuthProtocols OBJECT-IDENTITY
       STATUS        current
       DESCRIPTION  "Registration point for standards-track
                     authentication protocols used in SNMP Management
                     Frameworks.
                    "
       ::= { snmpFrameworkAdmin 1 }

   snmpPrivProtocols OBJECT-IDENTITY
       STATUS        current
       DESCRIPTION  "Registration point for standards-track privacy
                     protocols used in SNMP Management Frameworks.
                    "
       ::= { snmpFrameworkAdmin 2 }

   -- Conformance information ******************************************

   snmpFrameworkMIBCompliances
                  OBJECT IDENTIFIER ::= {snmpFrameworkMIBConformance 1}
   snmpFrameworkMIBGroups
                  OBJECT IDENTIFIER ::= {snmpFrameworkMIBConformance 2}

   -- compliance statements

   snmpFrameworkMIBCompliance MODULE-COMPLIANCE
       STATUS       current
       DESCRIPTION "The compliance statement for SNMP engines which
                    implement the SNMP Management Framework MIB.
                   "
       MODULE    -- this module
           MANDATORY-GROUPS { snmpEngineGroup }

       ::= { snmpFrameworkMIBCompliances 1 }

   -- units of conformance
   snmpEngineGroup OBJECT-GROUP
       OBJECTS {
                 snmpEngineID,
                 snmpEngineBoots,
                 snmpEngineTime,
                 snmpEngineMaxMessageSize
               }
       STATUS       current
       DESCRIPTION "A collection of objects for identifying and
                    determining the configuration and current timeliness
                    values of an SNMP engine.
                   "
       ::= { snmpFrameworkMIBGroups 1 }

   END



--------------------------------------------------------------------------
-- Rfc2493, PerfHist-TC-MIB, needed by Adsl Mibs
--------------------------------------------------------------------------
     PerfHist-TC-MIB DEFINITIONS ::= BEGIN

     IMPORTS
        MODULE-IDENTITY,
        Gauge32, mib-2
            FROM SNMPv2-SMI
        TEXTUAL-CONVENTION
            FROM SNMPv2-TC;


     perfHistTCMIB MODULE-IDENTITY
          LAST-UPDATED "9811071100Z"
          ORGANIZATION "IETF AToMMIB and TrunkMIB WGs"
          CONTACT-INFO
                       "Kaj Tesink
              Postal:  Bellcore
                       331 Newman Springs Road
                       Red Bank, NJ 07701
                       USA
              Tel:     +1 732 758 5254
              Fax:     +1 732 758 2269
              E-mail:  kaj@bellcore.com"
          DESCRIPTION
           "This MIB Module provides Textual Conventions
             to be used by systems supporting 15 minute
             based performance history counts."
          ::= { mib-2 58 }




     -- The Textual Conventions defined below are organized
     -- alphabetically

     -- Use of these TCs assumes the following:
     -- 0  The agent supports 15 minute based history
     --    counters.
     -- 0  The agent is capable of keeping a history of n
     --    intervals of 15 minute performance data. The
     --    value of n is defined by the specific MIB
     --    module but shall be 0 < n =< 96.
     -- 0  The agent may optionally support performance
     --    data aggregating the history intervals.
     -- 0  The agent will keep separate tables for the
     --    current interval, the history intervals, and
     --    the total aggregates.
     -- 0  The agent will keep the following objects.
     --    If performance data is kept for multiple instances
     --    of a measured entity, then
     --    these objects are applied to each instance of
     --    the measured entity (e.g., interfaces).
     --


     -- xyzTimeElapsed OBJECT-TYPE
     --       SYNTAX  INTEGER (0..899)
     --       MAX-ACCESS  read-only
     --       STATUS  current
     --       DESCRIPTION
     --       "The number of seconds that have elapsed since
     --       the beginning of the current measurement period.
     --       If, for some reason, such as an adjustment in the
     --       system's time-of-day clock, the current interval
     --       exceeds the maximum value, the agent will return
     --       the maximum value."
     --       ::= { xxx }

     -- xyzValidIntervals OBJECT-TYPE
     --       SYNTAX  INTEGER (0..<n>)
     --       MAX-ACCESS  read-only
     --       STATUS  current
     --       DESCRIPTION
     --       "The number of previous near end intervals
     --       for which data was collected.
     --          [ The overall constraint on <n> is 1 =< n =< 96; ]
     --          [ Define any additional constraints on <n> here. ]
     --       The value will be <n> unless the measurement was
     --       (re-)started within the last (<n>*15) minutes, in which
     --       case the value will be the number of complete 15
     --       minute intervals for which the agent has at least
     --       some data. In certain cases (e.g., in the case
     --       where the agent is a proxy) it is possible that some
     --       intervals are unavailable.  In this case, this
     --       interval is the maximum interval number for
     --       which data is available."
     --       ::= { xxx }

     -- xyzInvalidIntervals OBJECT-TYPE
     --     SYNTAX  INTEGER (0..<n>)
     --     MAX-ACCESS  read-only
     --     STATUS  current
     --     DESCRIPTION
     --       "The number of intervals in the range from
     --        0 to xyzValidIntervals for which no
     --        data is available. This object will typically
     --        be zero except in cases where the data for some
     --        intervals are not available (e.g., in proxy
     --        situations)."
     --       ::= { xxx }

     PerfCurrentCount ::= TEXTUAL-CONVENTION
           STATUS  current
           DESCRIPTION
              "A counter associated with a
               performance measurement in a current 15
               minute measurement interval. The value
               of this counter starts from zero and is
               increased when associated events occur,
               until the end of the 15 minute interval.
               At that time the value of the counter is
               stored in the first 15 minute history
               interval, and the CurrentCount is
               restarted at zero. In the
               case where the agent has no valid data
               available for the current interval the
               corresponding object instance is not
               available and upon a retrieval request
               a corresponding error message shall be
               returned to indicate that this instance
               does not exist (for example, a noSuchName
               error for SNMPv1 and a noSuchInstance for
               SNMPv2 GET operation)."
            SYNTAX  Gauge32

     PerfIntervalCount ::= TEXTUAL-CONVENTION
           STATUS  current
           DESCRIPTION
              "A counter associated with a
               performance measurement in a previous
               15 minute measurement interval. In the
               case where the agent has no valid data
               available for a particular interval the
               corresponding object instance is not
               available and upon a retrieval request
               a corresponding error message shall be
               returned to indicate that this instance
               does not exist (for example, a noSuchName
               error for SNMPv1 and a noSuchInstance for
               SNMPv2 GET operation).
               In a system supporting
               a history of n intervals with
               IntervalCount(1) and IntervalCount(n) the
               most and least recent intervals
               respectively, the following applies at
               the end of a 15 minute interval:
               - discard the value of IntervalCount(n)
               - the value of IntervalCount(i) becomes that
                 of IntervalCount(i-1) for n >= i > 1
               - the value of IntervalCount(1) becomes that
                 of CurrentCount
               - the TotalCount, if supported, is adjusted."
            SYNTAX  Gauge32

    PerfTotalCount ::= TEXTUAL-CONVENTION
          STATUS  current
          DESCRIPTION
              "A counter associated with a
               performance measurements aggregating the
               previous valid 15 minute measurement
               intervals. (Intervals for which no valid
               data was available are not counted)"
            SYNTAX  Gauge32


     END



--------------------------------------------------------------------------
-- Rfc2514, ATM-TC-MIB, needed by Rfc2515
--------------------------------------------------------------------------
     ATM-TC-MIB DEFINITIONS ::= BEGIN

     IMPORTS
        MODULE-IDENTITY, OBJECT-IDENTITY,
        TimeTicks, mib-2
            FROM SNMPv2-SMI
        TEXTUAL-CONVENTION
            FROM SNMPv2-TC;


     atmTCMIB MODULE-IDENTITY
          LAST-UPDATED "9810190200Z"
          ORGANIZATION "IETF AToMMIB Working Group"
          CONTACT-INFO
            "          Michael Noto
              Postal:  3Com Corporation
                       5400 Bayfront Plaza, M/S 3109
                       Santa Clara, CA 95052
                       USA
              Tel:     +1 408 326 2218
              E-mail:  mike_noto@3com.com

                       Ethan Mickey Spiegel
              Postal:  Cisco Systems
                       170 W. Tasman Dr.
                       San Jose, CA 95134
                       USA
              Tel:     +1 408 526 6408
              E-mail:  mspiegel@cisco.com

                       Kaj Tesink
              Postal:  Bellcore
                       331 Newman Springs Road
                       Red Bank, NJ 07701
                       USA
              Tel:     +1 732 758 5254
              Fax:     +1 732 758 4177
              E-mail:  kaj@bellcore.com"
          DESCRIPTION
           "This MIB Module provides Textual Conventions
           and OBJECT-IDENTITY Objects to be used by
           ATM systems."
          ::= { mib-2 37 3 } -- atmMIB 3 (see [3])

     -- The Textual Conventions defined below are organized
     -- alphabetically


     AtmAddr ::= TEXTUAL-CONVENTION
             DISPLAY-HINT "1x"
             STATUS  current
             DESCRIPTION
                 "An ATM address. The semantics are implied by
                 the length. The address types are: - no
                 address (0 octets) - E.164 (8 octets) - NSAP
                 (20 octets) In addition, when subaddresses
                 are used the AtmAddr may represent the
                 concatenation of address and subaddress. The
                 associated address types are: - E.164, E.164
                 (16 octets) - E.164, NSAP (28 octets) - NSAP,
                 NSAP (40 octets) Address lengths other than
                 defined in this definition imply address
                 types defined elsewhere.  Note: The E.164
                 address is encoded in BCD format."
            SYNTAX   OCTET STRING (SIZE(0..40))


    AtmConnCastType ::= TEXTUAL-CONVENTION
            STATUS  current
            DESCRIPTION
              "The type of topology of a connection (point-
              to-point, point-to-multipoint). In the case
              of point-to-multipoint, the orientation of
              this VPL or VCL in the connection.
              On a host:
              - p2mpRoot indicates that the host
                is the root of the p2mp connection.
              - p2mpLeaf indicates that the host
                is a leaf of the p2mp connection.
              On a switch interface:
              - p2mpRoot indicates that cells received
                by the switching fabric from the interface
                are from the root of the p2mp connection.
              - p2mpLeaf indicates that cells transmitted
                to the interface from the switching fabric
                are to the leaf of the p2mp connection."
            SYNTAX   INTEGER {
               p2p(1),
               p2mpRoot(2),
               p2mpLeaf(3)
               }

    AtmConnKind ::= TEXTUAL-CONVENTION
            STATUS  current
            DESCRIPTION
                "The type of call control used for an ATM
                connection at a particular interface. The use
                is as follows:
                   pvc(1)
                      Virtual link of a PVC. Should not be
                      used for an PVC/SVC (i.e., Soft PVC)
                      crossconnect.
                   svcIncoming(2)
                      Virtual link established after a
                      received signaling request to setup
                      an SVC.
                   svcOutgoing(3)
                      Virtual link established after a
                      transmitted or forwarded signaling
                      request to setup an SVC.
                   spvcInitiator(4)
                      Virtual link at the PVC side of an
                      SVC/PVC crossconnect, where the
                      switch is the initiator of the Soft PVC
                      setup.
                   spvcTarget(5)
                      Virtual link at the PVC side of an
                      SVC/PVC crossconnect, where the
                      switch is the target of the Soft PVC
                      setup.

                For PVCs, a pvc virtual link is always cross-
                connected to a pvc virtual link.

                For SVCs, an svcIncoming virtual link is always cross-
                connected to an svcOutgoing virtual link.

                For Soft PVCs, an spvcInitiator is either cross-connected to
                an svcOutgoing or an spvcTarget, and an spvcTarget is either
                cross-connected to an svcIncoming or an spvcInitiator."
        SYNTAX   INTEGER {
           pvc(1),
           svcIncoming(2),
           svcOutgoing(3),
           spvcInitiator(4),
           spvcTarget(5)
           }

    AtmIlmiNetworkPrefix ::= TEXTUAL-CONVENTION
        STATUS   current
        DESCRIPTION
            "A network prefix used for ILMI address
            registration.  In the case of ATM endsystem
            addresses (AESAs), the network prefix is the first
            13 octets of the address which includes the AFI,
            IDI, and HO-DSP fields.  In the case of native
            E.164 addresses, the network prefix is the entire
            E.164 address encoded in 8 octets, as if it were
            an E.164 IDP in an ATM endsystem address
            structure."
        REFERENCE
            "ATM Forum, Integrated Local Management Interface
               (ILMI) Specification, Version 4.0,
               af-ilmi-0065.000, September 1996, Section 9
             ATM Forum, ATM User-Network Interface Signalling
               Specification, Version 4.0 (UNI 4.0),
               af-sig-0061.000, June 1996, Section 3"
        SYNTAX   OCTET STRING (SIZE(8|13))

AtmInterfaceType ::= TEXTUAL-CONVENTION
        STATUS       current
        DESCRIPTION
            "The connection setup procedures used for the
            identified interface.

            Other: Connection setup procedures other than
               those listed below.

            Auto-configuration:
               Indicates that the connection setup
               procedures are to be determined dynamically,
               or that determination has not yet been
               completed. One such mechanism is via ATM
               Forum ILMI auto-configuration procedures.

            ITU-T DSS2:
            -  ITU-T Recommendation Q.2931, Broadband
               Integrated Service Digital Network (B-ISDN)
               Digital Subscriber Signalling System No.2
               (DSS2) User-Network Interface (UNI) Layer 3
               Specification for Basic Call/Connection
               Control (September 1994)
            -  ITU-T Draft Recommendation Q.2961,
               B-ISDN DSS 2 Support of Additional Traffic
               Parameters (May 1995)

            -  ITU-T Draft Recommendation Q.2971,
               B-ISDN DSS 2 User Network Interface Layer 3
               Specification for Point-to-multipoint
               Call/connection Control (May 1995)

            ATM Forum UNI 3.0:
               ATM Forum, ATM User-Network Interface,
               Version 3.0 (UNI 3.0) Specification,
               (1994).

            ATM Forum UNI 3.1:
               ATM Forum, ATM User-Network Interface,
               Version 3.1 (UNI 3.1) Specification,
               (November 1994).

            ATM Forum UNI Signalling 4.0:
               ATM Forum, ATM User-Network Interface (UNI)
               Signalling Specification Version 4.0,
               af-sig-0061.000 (June 1996).

            ATM Forum IISP (based on UNI 3.0 or UNI 3.1) :
               Interim Inter-switch Signaling Protocol
               (IISP) Specification, Version 1.0,
               af-pnni-0026.000, (December 1994).

            ATM Forum PNNI 1.0 :
               ATM Forum, Private Network-Network Interface
               Specification, Version 1.0, af-pnni-0055.000,
               (March 1996).

            ATM Forum B-ICI:
               ATM Forum, B-ICI Specification, Version 2.0,
               af-bici-0013.002, (November 1995).

            ATM Forum UNI PVC Only:
               An ATM Forum compliant UNI with the
               signalling disabled.
            ATM Forum NNI PVC Only:
               An ATM Forum compliant NNI with the
               signalling disabled."
        SYNTAX  INTEGER  {
                  other(1),
                  autoConfig(2),
                  ituDss2(3),
                  atmfUni3Dot0(4),
                  atmfUni3Dot1(5),
                  atmfUni4Dot0(6),
                  atmfIispUni3Dot0(7),
                  atmfIispUni3Dot1(8),
                  atmfIispUni4Dot0(9),
        atmfPnni1Dot0(10),
        atmfBici2Dot0(11),
        atmfUniPvcOnly(12),
        atmfNniPvcOnly(13)  }

AtmServiceCategory ::= TEXTUAL-CONVENTION
        STATUS  current
        DESCRIPTION
            "The service category for a connection."
        REFERENCE
            "ATM Forum Traffic Management Specification,
            Version 4.0, af-tm-0056.000, June 1996."
        SYNTAX   INTEGER {
           other(1),   -- none of the following
           cbr(2),     -- constant bit rate
           rtVbr(3),   -- real-time variable bit rate
           nrtVbr(4),  -- non real-time variable bit rate
           abr(5),     -- available bit rate
           ubr(6)      -- unspecified bit rate
           }

AtmSigDescrParamIndex ::= TEXTUAL-CONVENTION
        STATUS  current
        DESCRIPTION
            "The value of this object identifies a row in the
            atmSigDescrParamTable. The value 0 signifies that
            none of the signalling parameters defined in the
            atmSigDescrParamTable are applicable."
        SYNTAX  INTEGER (0..2147483647)

AtmTrafficDescrParamIndex ::= TEXTUAL-CONVENTION
        STATUS  current
        DESCRIPTION
            "The value of this object identifies a row in the
            atmTrafficDescrParamTable.  The value 0 signifies
            that no row has been identified."
        SYNTAX  INTEGER (0..2147483647)

AtmVcIdentifier ::= TEXTUAL-CONVENTION
        STATUS  current
        DESCRIPTION
            "The VCI value for a VCL. The maximum VCI value
            cannot exceed the value allowable by
            atmInterfaceMaxVciBits defined in ATM-MIB."
        SYNTAX   INTEGER (0..65535)

AtmVpIdentifier ::= TEXTUAL-CONVENTION
        STATUS  current
        DESCRIPTION
            "The VPI value for a VPL or VCL. The value VPI=0
            is only allowed for a VCL. For ATM UNIs supporting
            VPCs the VPI value ranges from 0 to 255.  The VPI
            value 0 is supported for ATM UNIs conforming to
            the ATM Forum UNI 4.0 Annex 8 (Virtual UNIs)
            specification. For ATM UNIs supporting VCCs the
            VPI value ranges from 0 to 255.  For ATM NNIs the
            VPI value ranges from 0 to 4095.  The maximum VPI
            value cannot exceed the value allowable by
            atmInterfaceMaxVpiBits defined in ATM-MIB."
        SYNTAX    INTEGER (0..4095)

AtmVorXAdminStatus ::= TEXTUAL-CONVENTION
        STATUS  current
        DESCRIPTION
            "The value determines the desired administrative
            status of a virtual link or cross-connect. The up
            and down states indicate that the traffic flow is
            enabled or disabled respectively on the virtual
            link or cross-connect."
        SYNTAX   INTEGER {
           up(1),
           down(2)
            }

AtmVorXLastChange ::= TEXTUAL-CONVENTION
        STATUS  current
        DESCRIPTION
            "The value of MIB II's sysUpTime at the time a
            virtual link or cross-connect entered its current
            operational state. If the current state was
            entered prior to the last re-initialization of the
            agent then this object contains a zero value."
        SYNTAX   TimeTicks

AtmVorXOperStatus ::= TEXTUAL-CONVENTION
        STATUS  current
        DESCRIPTION
            "The value determines the operational status of a
            virtual link or cross-connect. The up and down
            states indicate that the traffic flow is enabled
            or disabled respectively on the virtual link or
            cross-connect. The unknown state indicates that
            the state of it cannot be determined. The state
            will be down or unknown if the supporting ATM
            interface(s) is down or unknown respectively."
        SYNTAX   INTEGER {
           up(1),
           down(2),
           unknown(3)
           }


-- OBJECT-IDENTITIES:

-- The following atmTrafficDescriptorTypes has been moved
-- from RFC1695 and no longer appear in the revision of
-- RFC1695[3].

atmTrafficDescriptorTypes OBJECT IDENTIFIER ::= {mib-2 37 1 1}
                                            -- atmMIBObjects
                                            -- See [3].

-- All other and new OBJECT IDENTITIES
-- are defined under the following subtree:

    atmObjectIdentities OBJECT IDENTIFIER ::= {atmTCMIB 1}

-- The following values are defined for use as
-- possible values of the ATM traffic descriptor type.

atmNoTrafficDescriptor  OBJECT-IDENTITY
    STATUS  deprecated
    DESCRIPTION
        "This identifies the no ATM traffic
        descriptor type.  Parameters 1, 2, 3, 4,
        and 5 are not used.  This traffic descriptor
        type can be used for best effort traffic."
    ::= {atmTrafficDescriptorTypes 1}

atmNoClpNoScr  OBJECT-IDENTITY
    STATUS  current
    DESCRIPTION
        "This traffic descriptor type is for no CLP
        and no Sustained Cell Rate.  The use of the
        parameter vector for this type:
        Parameter 1: peak cell rate in cells/second
                     for CLP=0+1 traffic
        Parameter 2: not used
        Parameter 3: not used
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 2}

atmClpNoTaggingNoScr  OBJECT-IDENTITY
    STATUS  deprecated
    DESCRIPTION
        "This traffic descriptor is for CLP without
        tagging and no Sustained Cell Rate.  The use
        of the parameter vector for this type:
        Parameter 1: peak cell rate in cells/second
                     for CLP=0+1 traffic
        Parameter 2: peak cell rate in cells/second
                     for CLP=0 traffic
        Parameter 3: not used
        Parameter 4: not used
        Parameter 5: not used."
    ::= {atmTrafficDescriptorTypes 3}

atmClpTaggingNoScr  OBJECT-IDENTITY
    STATUS  deprecated
    DESCRIPTION
        "This traffic descriptor is for CLP with
        tagging and no Sustained Cell Rate.  The use
        of the parameter vector for this type:
        Parameter 1: peak cell rate in cells/second
                     for CLP=0+1 traffic
        Parameter 2: peak cell rate in cells/second
                     for CLP=0 traffic, excess
                     tagged as CLP=1
        Parameter 3: not used
        Parameter 4: not used
        Parameter 5: not used."
    ::= {atmTrafficDescriptorTypes 4}

atmNoClpScr  OBJECT-IDENTITY
    STATUS  current
    DESCRIPTION
        "This traffic descriptor type is for no CLP
        with Sustained Cell Rate.  The use of the
        parameter vector for this type:
        Parameter 1: peak cell rate in cells/second
                     for CLP=0+1 traffic
        Parameter 2: sustainable cell rate in cells/second
                     for CLP=0+1 traffic
        Parameter 3: maximum burst size in cells
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 5}

atmClpNoTaggingScr  OBJECT-IDENTITY
    STATUS  current
    DESCRIPTION
        "This traffic descriptor type is for CLP with
        Sustained Cell Rate and no tagging.  The use
        of the parameter vector for this type:
        Parameter 1: peak cell rate in cells/second
                     for CLP=0+1 traffic
        Parameter 2: sustainable cell rate in cells/second
                     for CLP=0 traffic
        Parameter 3: maximum burst size in cells
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 6}

atmClpTaggingScr  OBJECT-IDENTITY
    STATUS  current
    DESCRIPTION
        "This traffic descriptor type is for CLP with
        tagging and Sustained Cell Rate.  The use of
        the parameter vector for this type:
        Parameter 1: peak cell rate in cells/second
                     for CLP=0+1 traffic
        Parameter 2: sustainable cell rate in cells/second
                     for CLP=0 traffic, excess tagged as
                     CLP=1
        Parameter 3: maximum burst size in cells
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 7}

atmClpNoTaggingMcr  OBJECT-IDENTITY
    STATUS  current
    DESCRIPTION
        "This traffic descriptor type is for CLP with
        Minimum Cell Rate and no tagging.  The use of
        the parameter vector for this type:
        Parameter 1: peak cell rate in cells/second
                     for CLP=0+1 traffic
        Parameter 2: CDVT in tenths of microseconds
        Parameter 3: minimum cell rate in cells/second
        Parameter 4: unused
        Parameter 5: unused."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 8}

atmClpTransparentNoScr  OBJECT-IDENTITY
    STATUS  current
    DESCRIPTION
        "This traffic descriptor type is for the CLP-
        transparent model and no Sustained Cell Rate.
        The use of the parameter vector for this type:
        Parameter 1: peak cell rate in cells/second
                     for CLP=0+1 traffic
        Parameter 2: CDVT in tenths of microseconds
        Parameter 3: not used
        Parameter 4: not used
        Parameter 5: not used.

        This traffic descriptor type is applicable to
        connections following the CBR.1 conformance
        definition.

        Connections specifying this traffic descriptor
        type will be rejected at UNI 3.0 or UNI 3.1
        interfaces.  For a similar traffic descriptor
        type that can be accepted at UNI 3.0 and
        UNI 3.1 interfaces, see atmNoClpNoScr."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 9}

atmClpTransparentScr  OBJECT-IDENTITY
    STATUS  current
    DESCRIPTION
        "This traffic descriptor type is for the CLP-
        transparent model with Sustained Cell Rate.
        The use of the parameter vector for this type:
        Parameter 1: peak cell rate in cells/second
                     for CLP=0+1 traffic
        Parameter 2: sustainable cell rate in cells/second
                     for CLP=0+1 traffic
        Parameter 3: maximum burst size in cells
        Parameter 4: CDVT in tenths of microseconds
        Parameter 5: not used.

        This traffic descriptor type is applicable to
        connections following the VBR.1 conformance
        definition.

        Connections specifying this traffic descriptor
        type will be rejected at UNI 3.0 or UNI 3.1
        interfaces.  For a similar traffic descriptor
        type that can be accepted at UNI 3.0 and
        UNI 3.1 interfaces, see atmNoClpScr."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 10}

atmNoClpTaggingNoScr  OBJECT-IDENTITY
    STATUS  current
    DESCRIPTION
        "This traffic descriptor type is for no CLP
        with tagging and no Sustained Cell Rate.  The
        use of the parameter vector for this type:
        Parameter 1: peak cell rate in cells/second
                     for CLP=0+1 traffic
        Parameter 2: CDVT in tenths of microseconds
        Parameter 3: not used
        Parameter 4: not used
        Parameter 5: not used.

        This traffic descriptor type is applicable to
        connections following the UBR.2 conformance
        definition ."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 11}

atmNoClpNoScrCdvt  OBJECT-IDENTITY
    STATUS  current
    DESCRIPTION
        "This traffic descriptor type is for no CLP
        and no Sustained Cell Rate.  The use of the
        parameter vector for this type:
        Parameter 1: peak cell rate in cells/second
                     for CLP=0+1 traffic
        Parameter 2: CDVT in tenths of microseconds
        Parameter 3: not used
        Parameter 4: not used
        Parameter 5: not used.

        This traffic descriptor type is applicable to
        CBR connections following the UNI 3.0/3.1
        conformance definition for PCR CLP=0+1.
        These CBR connections differ from CBR.1
        connections in that the CLR objective
        applies only to the CLP=0 cell flow.

        This traffic descriptor type is also
        applicable to connections following the UBR.1
        conformance definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 12}

atmNoClpScrCdvt  OBJECT-IDENTITY
    STATUS  current
    DESCRIPTION
        "This traffic descriptor type is for no CLP
        with Sustained Cell Rate.  The use of the
        parameter vector for this type:
        Parameter 1: peak cell rate in cells/second
                     for CLP=0+1 traffic
        Parameter 2: sustainable cell rate in cells/second
                     for CLP=0+1 traffic
        Parameter 3: maximum burst size in cells
        Parameter 4: CDVT in tenths of microseconds
        Parameter 5: not used.

        This traffic descriptor type is applicable
        to VBR connections following the UNI 3.0/3.1
        conformance definition for PCR CLP=0+1 and
        SCR CLP=0+1.  These VBR connections
        differ from VBR.1 connections in that
        the CLR objective applies only to the CLP=0
        cell flow."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 13}

atmClpNoTaggingScrCdvt  OBJECT-IDENTITY
    STATUS  current
    DESCRIPTION
        "This traffic descriptor type is for CLP with
        Sustained Cell Rate and no tagging.  The use
        of the parameter vector for this type:
        Parameter 1: peak cell rate in cells/second
                     for CLP=0+1 traffic
        Parameter 2: sustainable cell rate in cells/second
                     for CLP=0 traffic
        Parameter 3: maximum burst size in cells
        Parameter 4: CDVT in tenths of microseconds
        Parameter 5: not used.

        This traffic descriptor type is applicable to
        connections following the VBR.2 conformance
        definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 14}

atmClpTaggingScrCdvt  OBJECT-IDENTITY
    STATUS  current
    DESCRIPTION
        "This traffic descriptor type is for CLP with
        tagging and Sustained Cell Rate.  The use of
        the parameter vector for this type:
        Parameter 1: peak cell rate in cells/second
                     for CLP=0+1 traffic
        Parameter 2: sustainable cell rate in cells/second
                     for CLP=0 traffic, excess tagged as
                     CLP=1
        Parameter 3: maximum burst size in cells
        Parameter 4: CDVT in tenths of microseconds
        Parameter 5: not used.

        This traffic descriptor type is applicable to
        connections following the VBR.3 conformance
        definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 15}

END

--------------------------------------------------------------------------
-- Rfc2515, ATM-MIB
--------------------------------------------------------------------------
     ATM-MIB DEFINITIONS ::= BEGIN

     IMPORTS
        MODULE-IDENTITY, OBJECT-TYPE,
        Counter32, Integer32, IpAddress, mib-2
            FROM SNMPv2-SMI
        DisplayString, RowStatus, TruthValue
            FROM SNMPv2-TC
        MODULE-COMPLIANCE, OBJECT-GROUP
            FROM SNMPv2-CONF
        InterfaceIndex, ifIndex
            FROM IF-MIB
        AtmAddr, AtmConnKind, AtmConnCastType,
        AtmServiceCategory, AtmTrafficDescrParamIndex,
        AtmVpIdentifier, AtmVcIdentifier,
        AtmVorXAdminStatus, AtmVorXLastChange,
        AtmVorXOperStatus, atmNoClpNoScr
            FROM ATM-TC-MIB;


     atmMIB MODULE-IDENTITY
          LAST-UPDATED "9810191200Z"
          ORGANIZATION "IETF AToM MIB Working Group"
          CONTACT-INFO
            "          Kaj Tesink
              Postal:  Bellcore
                       331 Newman Springs Road
                       Red Bank, NJ 07701
              Tel:     732-758-5254
              Fax:     732-758-2269
              E-mail:  kaj@bellcore.com"
          DESCRIPTION
           "This is the MIB Module for ATM and AAL5-related
            objects for managing ATM interfaces, ATM virtual
            links, ATM cross-connects, AAL5 entities, and
            and AAL5 connections."
          REVISION      "9810191200Z"
          DESCRIPTION
           "The initial revision of this module was published
            as RFC 1695. Key revisions include:
            o  Textual Conventions and OBJECT IDENTITIES have
               been moved to a separate MIB module.
            o  Applicability of objects to PVCs, SVCs and Soft
               PVCs has been clarified.
            o  DEFVAL clauses have been added.
            o  The relationship of ifIndex values with different
               layers and sublayers related to ATM has been
               clarified.
            o  atmTrafficQosClass has been deprecated
               and replaced with atmServiceCategory.
            o  atmInterfaceCurrentMaxVpiBits and
               atmInterfaceCurrentMaxVciBits have been added with
               a description on their relationship with other
               objects.
            o  atmInterfaceAddressType and atmInterfaceAdminAddress
               have been deprecated and replaced by
               atmInterfaceSubscrAddress.
            o  atmInterfaceTCAlarmState has been clarified.
            o  atmTrafficDescrParamIndexNext has been introduced
               in order to provide a manager a free
               atmTrafficDescrParamIndex value.
            o  The atmTrafficFrameDiscard capability has been added.
            o  A connection topology type (atmVpl/VclCastType) and
               a call control type (atmVpl/VclConnKind) have been
               added.
            o  aal2 has been added to atmVccAalType."
          REVISION      "9406072245Z"
          DESCRIPTION
           "The RFC1695 version of this MIB module."
          ::= { mib-2 37 }


     atmMIBObjects  OBJECT IDENTIFIER ::= {atmMIB 1}

     -- {atmMIBObjects 1} has been moved to a separate
     -- specification [1.


     -- This ATM MIB Module consists of the following tables:
     -- (1) ATM Interface configuration table
     -- (2) ATM Interface DS3 PLCP table
     -- (3) ATM Interface TC Sublayer table
     -- (4) Atm Traffic Descriptor table
     -- (5) ATM Interface VPL configuration table
     -- (6) ATM Interface VCL configuration table
     -- (7) ATM VP Cross Connect table (for PVCs)
     -- (8) ATM VC Cross Connect table (for PVCs)
     -- (9) ATM Interface AAL5 VCC performance statistics
     --     table

     --    ATM Interface Configuration Parameters Table

     -- This table contains ATM specific
     -- configuration information associated with
     -- an ATM interface beyond those
     -- supported using the ifTable.




     atmInterfaceConfTable  OBJECT-TYPE
          SYNTAX         SEQUENCE OF AtmInterfaceConfEntry
          MAX-ACCESS     not-accessible
          STATUS         current
          DESCRIPTION
           "This table contains ATM local interface
            configuration parameters, one entry per ATM
            interface port."
          ::= { atmMIBObjects 2 }

     atmInterfaceConfEntry    OBJECT-TYPE
          SYNTAX         AtmInterfaceConfEntry
          MAX-ACCESS     not-accessible
          STATUS         current
          DESCRIPTION
           "This list contains ATM interface configuration
            parameters and state variables and is indexed
            by ifIndex values of ATM interfaces."
          INDEX { ifIndex }
          ::= { atmInterfaceConfTable  1}

     AtmInterfaceConfEntry    ::= SEQUENCE  {
          atmInterfaceMaxVpcs             INTEGER,
          atmInterfaceMaxVccs             INTEGER,
          atmInterfaceConfVpcs            INTEGER,
          atmInterfaceConfVccs            INTEGER,
          atmInterfaceMaxActiveVpiBits    INTEGER,
          atmInterfaceMaxActiveVciBits    INTEGER,
          atmInterfaceIlmiVpi             AtmVpIdentifier,
          atmInterfaceIlmiVci             AtmVcIdentifier,
          atmInterfaceAddressType         INTEGER,
          atmInterfaceAdminAddress        AtmAddr,
          atmInterfaceMyNeighborIpAddress IpAddress,
          atmInterfaceMyNeighborIfName    DisplayString,
          atmInterfaceCurrentMaxVpiBits   INTEGER,
          atmInterfaceCurrentMaxVciBits   INTEGER,
          atmInterfaceSubscrAddress       AtmAddr
               }


     atmInterfaceMaxVpcs OBJECT-TYPE
          SYNTAX         INTEGER  (0..4096)
          MAX-ACCESS     read-write
          STATUS         current
          DESCRIPTION
           "The maximum number of VPCs (PVPCs and SVPCs)
            supported at this ATM interface. At the ATM UNI,
            the maximum number of VPCs (PVPCs and SVPCs)
            ranges from 0 to 256 only."
          ::= { atmInterfaceConfEntry 1}

     atmInterfaceMaxVccs OBJECT-TYPE
          SYNTAX         INTEGER  (0..65536)
          MAX-ACCESS     read-write
          STATUS         current
          DESCRIPTION
           "The maximum number of VCCs (PVCCs and SVCCs)
            supported at this ATM interface."
          ::= { atmInterfaceConfEntry 2}

     atmInterfaceConfVpcs  OBJECT-TYPE
          SYNTAX         INTEGER  (0..4096)
          MAX-ACCESS     read-only
          STATUS         current
          DESCRIPTION
           "The number of VPCs (PVPC, Soft PVPC and SVPC)
            currently in use at this ATM interface.  It includes
            the number of PVPCs and Soft PVPCs that are configured
            at the interface, plus the number of SVPCs
            that are currently  established at the
            interface.

            At the ATM UNI, the configured number of
            VPCs (PVPCs and SVPCs) can range from
            0 to 256 only."
          ::= { atmInterfaceConfEntry 3}

     atmInterfaceConfVccs  OBJECT-TYPE
          SYNTAX         INTEGER  (0..65536)
          MAX-ACCESS     read-only
          STATUS         current
          DESCRIPTION
           "The number of VCCs (PVCC, Soft PVCC and SVCC)
            currently in use at this ATM interface.  It includes
            the number of PVCCs and Soft PVCCs that are configured
            at the interface, plus the number of SVCCs
            that are currently  established at the
            interface."
          ::= { atmInterfaceConfEntry 4}

     atmInterfaceMaxActiveVpiBits  OBJECT-TYPE
          SYNTAX         INTEGER (0..12)
          MAX-ACCESS     read-write
          STATUS         current
          DESCRIPTION
           "The  maximum number of active VPI bits
            configured for use at the ATM interface.
            At the ATM UNI, the maximum number of active
            VPI bits configured for use ranges from
            0 to 8 only."
          ::= { atmInterfaceConfEntry 5}

     atmInterfaceMaxActiveVciBits  OBJECT-TYPE
          SYNTAX         INTEGER (0..16)
          MAX-ACCESS     read-write
          STATUS         current
          DESCRIPTION
           "The maximum number of active VCI bits
            configured for use at this ATM interface."
          ::= { atmInterfaceConfEntry 6}

     atmInterfaceIlmiVpi OBJECT-TYPE
          SYNTAX         AtmVpIdentifier
          MAX-ACCESS     read-write
          STATUS         current
          DESCRIPTION
           "The VPI value of the VCC supporting
            the ILMI at this ATM interface.  If the values of
            atmInterfaceIlmiVpi and atmInterfaceIlmiVci are
            both equal to zero then the ILMI is not
            supported at this ATM interface."
          DEFVAL { 0 }
          ::= { atmInterfaceConfEntry 7}

     atmInterfaceIlmiVci OBJECT-TYPE
          SYNTAX         AtmVcIdentifier
          MAX-ACCESS     read-write
          STATUS         current
          DESCRIPTION
           "The VCI value of the VCC supporting
            the ILMI at this ATM interface.  If the values of
            atmInterfaceIlmiVpi and atmInterfaceIlmiVci are
            both equal to zero then the ILMI is not
            supported at this ATM interface."
          DEFVAL { 16 }
          ::= { atmInterfaceConfEntry 8}

     atmInterfaceAddressType  OBJECT-TYPE
          SYNTAX         INTEGER {
                            private(1),
                            nsapE164(2),
                            nativeE164(3),
                            other(4)
                              }
          MAX-ACCESS     read-only
          STATUS         deprecated
          DESCRIPTION
           "The type of primary ATM address configured
            for use at this ATM interface."
          ::= { atmInterfaceConfEntry 9 }

     --  The atmInterfaceAdminAddress object has been replaced by
     --  atmInterfaceSubscrAddress.

     atmInterfaceAdminAddress OBJECT-TYPE
          SYNTAX         AtmAddr
          MAX-ACCESS     read-only
          STATUS         deprecated
          DESCRIPTION
           "The primary address assigned for administrative purposes,
            for example, an address associated with the
            service provider side of a public network UNI
            (thus, the value of this address corresponds
            with the value of ifPhysAddress at the host side).
            If this interface has no assigned administrative
            address, or when the address used for
            administrative purposes is the same as that used
            for ifPhysAddress, then this is an octet string of
            zero length."
          ::= { atmInterfaceConfEntry 10 }

     atmInterfaceMyNeighborIpAddress OBJECT-TYPE
          SYNTAX         IpAddress
          MAX-ACCESS     read-write
          STATUS         current
          DESCRIPTION
           "The IP address of the neighbor system connected to
            the  far end of this interface, to which a Network
            Management Station can send SNMP messages, as IP
            datagrams sent to UDP port 161, in order to access
            network management information concerning the
            operation of that system.  Note that the value
            of this object may be obtained in different ways,
            e.g., by manual configuration, or through ILMI
            interaction with the neighbor system."
          ::= { atmInterfaceConfEntry 11 }

     atmInterfaceMyNeighborIfName OBJECT-TYPE
          SYNTAX         DisplayString
          MAX-ACCESS     read-write
          STATUS         current
          DESCRIPTION
           "The textual name of the interface on the neighbor
            system on the far end of this interface, and to
            which this interface connects.  If the neighbor
            system is manageable through SNMP and supports
            the object ifName, the value of this object must
            be identical with that of ifName for the ifEntry
            of the lowest level physical interface
            for this port.  If this interface does not have a
            textual name, the value of this object is a zero
            length string.  Note that the value of this object
            may be obtained in different ways, e.g., by manual
            configuration, or through ILMI interaction with
            the neighbor system."
          ::= { atmInterfaceConfEntry 12 }

     atmInterfaceCurrentMaxVpiBits    OBJECT-TYPE
          SYNTAX         INTEGER  (0..12)
          MAX-ACCESS     read-only
          STATUS         current
          DESCRIPTION
           "The maximum number of VPI Bits that may
            currently be used at this ATM interface.
            The value is the minimum of
            atmInterfaceMaxActiveVpiBits, and the
            atmInterfaceMaxActiveVpiBits of the interface's
            UNI/NNI peer.

            If the interface does not negotiate with
            its peer to determine the number of VPI Bits
            that can be used on the interface, then the
            value of this object must equal
            atmInterfaceMaxActiveVpiBits."
          ::= { atmInterfaceConfEntry 13 }

     atmInterfaceCurrentMaxVciBits    OBJECT-TYPE
          SYNTAX         INTEGER  (0..16)
          MAX-ACCESS     read-only
          STATUS         current
          DESCRIPTION
           "The maximum number of VCI Bits that may
            currently be used at this ATM interface.
            The value is the minimum of
            atmInterfaceMaxActiveVciBits, and the
            atmInterfaceMaxActiveVciBits of the interface's
            UNI/NNI peer.

            If the interface does not negotiate with
            its peer to determine the number of VCI Bits
            that can be used on the interface, then the
            value of this object must equal
            atmInterfaceMaxActiveVciBits."
          ::= { atmInterfaceConfEntry 14 }

     atmInterfaceSubscrAddress OBJECT-TYPE
          SYNTAX         AtmAddr
          MAX-ACCESS     read-write
          STATUS         current
          DESCRIPTION
           "The identifier assigned by a service provider
            to the network side of a public network UNI.
            If this interface has no assigned service provider
            address, or for other interfaces this is an octet string
            of zero length."
          ::= { atmInterfaceConfEntry 15 }

     -- The ATM Interface DS3 PLCP Table

     -- This table contains the DS3 PLCP configuration and
     -- state parameters of those ATM interfaces
     -- which use DS3 PLCP for carrying ATM cells over DS3.

     atmInterfaceDs3PlcpTable  OBJECT-TYPE
          SYNTAX       SEQUENCE OF AtmInterfaceDs3PlcpEntry
          MAX-ACCESS   not-accessible
          STATUS       current
          DESCRIPTION
           "This table contains ATM interface DS3 PLCP
            parameters and state variables, one entry per
            ATM interface port."
          ::= { atmMIBObjects 3}

     atmInterfaceDs3PlcpEntry OBJECT-TYPE
          SYNTAX         AtmInterfaceDs3PlcpEntry
          MAX-ACCESS     not-accessible
          STATUS         current
          DESCRIPTION
           "This list contains DS3 PLCP parameters and
            state variables at the ATM interface and is
            indexed by the ifIndex value of the ATM interface."
          INDEX    { ifIndex }
          ::= { atmInterfaceDs3PlcpTable 1}

     AtmInterfaceDs3PlcpEntry    ::= SEQUENCE  {
          atmInterfaceDs3PlcpSEFSs       Counter32,
          atmInterfaceDs3PlcpAlarmState  INTEGER,
          atmInterfaceDs3PlcpUASs        Counter32
            }


     atmInterfaceDs3PlcpSEFSs  OBJECT-TYPE
          SYNTAX         Counter32
          MAX-ACCESS     read-only
          STATUS         current
          DESCRIPTION
           "The number of DS3 PLCP Severely Errored Framing
            Seconds (SEFS). Each SEFS represents a
            one-second interval which contains
            one or more SEF events."
          ::= { atmInterfaceDs3PlcpEntry 1}

     atmInterfaceDs3PlcpAlarmState    OBJECT-TYPE
          SYNTAX         INTEGER {
                            noAlarm(1),
                            receivedFarEndAlarm(2),
                            incomingLOF(3)
                                 }
          MAX-ACCESS     read-only
          STATUS         current
          DESCRIPTION
           "This variable indicates if there is an
            alarm present for the DS3 PLCP.  The value
            receivedFarEndAlarm means that the DS3 PLCP
            has received an incoming Yellow
            Signal, the value incomingLOF means that
            the DS3 PLCP has declared a loss of frame (LOF)
            failure condition, and the value noAlarm
            means that there are no alarms present.
            Transition from the failure to the no alarm state
            occurs when no defects (e.g., LOF) are received
            for more than 10 seconds."
          ::= { atmInterfaceDs3PlcpEntry 2}

     atmInterfaceDs3PlcpUASs  OBJECT-TYPE
          SYNTAX         Counter32
          MAX-ACCESS     read-only
          STATUS         current
          DESCRIPTION
           "The counter associated with the number of
            Unavailable Seconds encountered by the PLCP."
          ::= { atmInterfaceDs3PlcpEntry 3}


     -- The ATM Interface TC Sublayer Table

     -- This table contains TC sublayer configuration and
     -- state parameters of those ATM interfaces
     -- which use TC sublayer for carrying ATM cells over
     -- SONET/SDH or DS3.


     atmInterfaceTCTable  OBJECT-TYPE
          SYNTAX         SEQUENCE OF AtmInterfaceTCEntry
          MAX-ACCESS     not-accessible
          STATUS         current
          DESCRIPTION
           "This table contains ATM interface TC
            Sublayer parameters and state variables,
            one entry per ATM interface port."
          ::= { atmMIBObjects 4}

     atmInterfaceTCEntry OBJECT-TYPE
          SYNTAX         AtmInterfaceTCEntry
          MAX-ACCESS     not-accessible
          STATUS         current
          DESCRIPTION
           "This list contains TC Sublayer parameters
            and state variables at the ATM interface and is
            indexed by the ifIndex value of the ATM interface."
          INDEX  {ifIndex }
          ::= { atmInterfaceTCTable 1}

     AtmInterfaceTCEntry    ::= SEQUENCE  {
          atmInterfaceOCDEvents      Counter32,
          atmInterfaceTCAlarmState   INTEGER
            }

     atmInterfaceOCDEvents  OBJECT-TYPE
          SYNTAX         Counter32
          MAX-ACCESS     read-only
          STATUS         current
          DESCRIPTION
           "The number of times the Out of Cell
            Delineation (OCD) events occur.  If seven
            consecutive ATM cells have Header Error
            Control (HEC) violations, an OCD event occurs.
            A high number of OCD events may indicate a
            problem with the TC Sublayer."
          ::= { atmInterfaceTCEntry 1}


     atmInterfaceTCAlarmState    OBJECT-TYPE
          SYNTAX         INTEGER {
                            noAlarm(1),
                            lcdFailure(2)
                                  }
          MAX-ACCESS     read-only
          STATUS         current
          DESCRIPTION
           "This variable indicates if there is an
            alarm present for the TC Sublayer.  The value
            lcdFailure(2) indicates that the TC Sublayer
            is currently in the Loss of Cell Delineation
            (LCD) defect maintenance state.  The value
            noAlarm(1) indicates that the TC Sublayer
            is currently not in the LCD defect
            maintenance state."
           ::= { atmInterfaceTCEntry 2}

     --  ATM Traffic Descriptor Parameter Table

     -- This table contains a set of self-consistent
     -- ATM traffic parameters including the
     -- ATM traffic service category.

     -- The ATM virtual link tables (i.e., VPL and VCL tables)
     -- will use this ATM Traffic Descriptor table
     -- to assign traffic parameters and service category
     -- to the receive and transmit directions of
     -- the ATM virtual links (i.e., VPLs and VCLs).
     -- The ATM VPL or VCL table will indicate a row
     -- in the atmTrafficDescrParamTable
     -- using its atmTrafficDescrParamIndex value.
     -- The management application can then compare a set of
     -- ATM traffic parameters with a single value.

     -- If no suitable row(s) in the atmTrafficDescrParamTable
     -- exists, the manager must create a new row(s) in this
     -- table. If such a row is created, agent checks the
     -- sanity of that set of ATM traffic parameter values.

     -- The manager may use atmTrafficDescrParamIndexNext
     -- in order to obtain a free atmTrafficDescrParamIndex
     -- value.

     -- When creating a new row, the parameter values
     -- will be checked for self-consistency.
     -- Predefined/template rows may be supported.

     -- A row in the atmTrafficDescrParamTable is deleted
     -- by setting the atmTrafficDescrRowStatus to destroy(6).
     -- The agent will check whether this row is still in use
     -- by any entry of the atmVplTable or atmVclTable.
     -- The agent denies the request if the row is still in
     -- use.

     --  The ATM Traffic Descriptor Parameter Table


     atmTrafficDescrParamTable    OBJECT-TYPE
          SYNTAX       SEQUENCE OF AtmTrafficDescrParamEntry
          MAX-ACCESS   not-accessible
          STATUS       current
          DESCRIPTION
           "This table contains information on ATM traffic
            descriptor type and the associated parameters."
          ::= { atmMIBObjects 5}

     atmTrafficDescrParamEntry    OBJECT-TYPE
          SYNTAX         AtmTrafficDescrParamEntry
          MAX-ACCESS     not-accessible
          STATUS         current
          DESCRIPTION
           "This list contains ATM traffic descriptor
            type and the associated parameters."
          INDEX  {atmTrafficDescrParamIndex}
          ::= { atmTrafficDescrParamTable 1}

     AtmTrafficDescrParamEntry   ::= SEQUENCE  {
       atmTrafficDescrParamIndex  AtmTrafficDescrParamIndex,
       atmTrafficDescrType        OBJECT IDENTIFIER,
       atmTrafficDescrParam1      Integer32,
       atmTrafficDescrParam2      Integer32,
       atmTrafficDescrParam3      Integer32,
       atmTrafficDescrParam4      Integer32,
       atmTrafficDescrParam5      Integer32,
       atmTrafficQoSClass         INTEGER,
       atmTrafficDescrRowStatus   RowStatus,
       atmServiceCategory         AtmServiceCategory,
       atmTrafficFrameDiscard     TruthValue
                    }

     atmTrafficDescrParamIndex OBJECT-TYPE
          SYNTAX  AtmTrafficDescrParamIndex (1..2147483647)
          MAX-ACCESS     not-accessible
          STATUS         current
          DESCRIPTION
           "This object is used by the virtual link
            table (i.e., VPL or VCL table)
            to identify the row of this table.
            When creating a new row in the table
            the value of this index may be obtained
            by retrieving the value of
            atmTrafficDescrParamIndexNext."
          ::= { atmTrafficDescrParamEntry  1}

     atmTrafficDescrType OBJECT-TYPE
          SYNTAX         OBJECT IDENTIFIER
          MAX-ACCESS     read-create
          STATUS         current
          DESCRIPTION
           "The value of this object identifies the type
            of ATM traffic descriptor.
            The type may indicate no traffic descriptor or
            traffic descriptor with one or more parameters.
            These parameters are specified as a parameter
            vector, in the corresponding instances of the
            objects:
                atmTrafficDescrParam1
                atmTrafficDescrParam2
                atmTrafficDescrParam3
                atmTrafficDescrParam4
                atmTrafficDescrParam5."
           DEFVAL  { atmNoClpNoScr }
           ::= { atmTrafficDescrParamEntry 2}

     atmTrafficDescrParam1 OBJECT-TYPE
          SYNTAX         Integer32
          MAX-ACCESS     read-create
          STATUS         current
          DESCRIPTION
           "The first parameter of the ATM traffic descriptor
            used according to the value of
            atmTrafficDescrType."
          DEFVAL  { 0 }
          ::= { atmTrafficDescrParamEntry 3}

     atmTrafficDescrParam2 OBJECT-TYPE
          SYNTAX         Integer32
          MAX-ACCESS     read-create
          STATUS         current
          DESCRIPTION
           "The second parameter of the ATM traffic descriptor
            used according to the value of
            atmTrafficDescrType."
          DEFVAL  { 0 }
          ::= { atmTrafficDescrParamEntry 4}

     atmTrafficDescrParam3 OBJECT-TYPE
          SYNTAX         Integer32
          MAX-ACCESS     read-create
          STATUS         current
          DESCRIPTION
           "The third parameter of the ATM traffic descriptor
            used according to the value of
            atmTrafficDescrType."
          DEFVAL  { 0 }
          ::= { atmTrafficDescrParamEntry 5}

     atmTrafficDescrParam4 OBJECT-TYPE
          SYNTAX         Integer32
          MAX-ACCESS     read-create
          STATUS         current
          DESCRIPTION
           "The fourth parameter of the ATM traffic descriptor
            used according to the value of
            atmTrafficDescrType."
          DEFVAL  { 0 }
          ::= { atmTrafficDescrParamEntry 6}

     atmTrafficDescrParam5 OBJECT-TYPE
          SYNTAX         Integer32
          MAX-ACCESS     read-create
          STATUS         current
          DESCRIPTION
           "The fifth parameter of the ATM traffic descriptor
            used according to the value of
            atmTrafficDescrType."
          DEFVAL  { 0 }
          ::= { atmTrafficDescrParamEntry 7}

     atmTrafficQoSClass  OBJECT-TYPE
          SYNTAX         INTEGER (0..255)
          MAX-ACCESS     read-create
          STATUS         deprecated
          DESCRIPTION
           "The value of this object identifies the QoS Class.
            Four Service classes have been
            specified in the ATM Forum UNI Specification:
            Service Class A: Constant bit rate video and
                             Circuit emulation
            Service Class B: Variable bit rate video/audio
            Service Class C: Connection-oriented data
            Service Class D: Connectionless data
            Four QoS classes numbered 1, 2, 3, and 4 have
            been specified with the aim to support service
            classes A, B, C, and D respectively.
            An unspecified QoS Class numbered `0' is used
            for best effort traffic."
          DEFVAL  { 0 }
          ::= { atmTrafficDescrParamEntry 8}

     atmTrafficDescrRowStatus  OBJECT-TYPE
          SYNTAX         RowStatus
          MAX-ACCESS     read-create
          STATUS         current
          DESCRIPTION
           "This object is used to create
            a new row or modify or delete an
            existing row in this table."
          DEFVAL  { active }
          ::= {atmTrafficDescrParamEntry 9}

     atmServiceCategory  OBJECT-TYPE
          SYNTAX         AtmServiceCategory
          MAX-ACCESS     read-create
          STATUS         current
          DESCRIPTION
           "The ATM service category."
          DEFVAL  { ubr }
          ::= { atmTrafficDescrParamEntry 10}


     atmTrafficFrameDiscard    OBJECT-TYPE
          SYNTAX       TruthValue
          MAX-ACCESS   read-create
          STATUS       current
          DESCRIPTION
           "If set to 'true', this object indicates that the network
            is requested to treat data for this connection, in the
            given direction, as frames (e.g. AAL5 CPCS_PDU's) rather
            than as individual cells.  While the precise
            implementation is network-specific, this treatment may
            for example involve discarding entire frames during
            congestion, rather than a few cells from many frames."
          DEFVAL { true }
          ::= { atmTrafficDescrParamEntry 11 }

     --  ATM Interface Virtual Path Link (VPL) Table

     -- This table contains configuration and state
     -- information of a bi-directional Virtual Path Link
     -- (VPL)

     -- This table can be used to create, delete or modify
     -- a VPL that is terminated in an ATM host or switch.
     -- This table can also be used to create, delete or
     -- modify a VPL which is cross-connected to another
     -- VPL.

     -- In the example below, the traffic flows on the receive
     -- and transmit directions of the VPLs are characterized
     -- by atmVplReceiveTrafficDescrIndex and
     -- atmVplTransmitTrafficDescrIndex respectively.
     -- The cross-connected VPLs are identified by
     -- atmVplCrossConnectIdentifier.



     --           ________________________________
     --           |                              |
     --  VPL      | ATM Host, Switch, or Network |   VPL
     -- receive   |                              |  receive
     -- ========> X                              X <=======
     -- <======== X                              X ========>
     -- transmit  |                              |  transmit
     --           |______________________________|



     --  The ATM Interface VPL Table

     atmVplTable         OBJECT-TYPE
          SYNTAX         SEQUENCE OF AtmVplEntry
          MAX-ACCESS     not-accessible
          STATUS         current
          DESCRIPTION
           "The Virtual Path Link (VPL) table.  A
            bi-directional VPL is modeled as one entry
            in this table. This table can be used for
            PVCs, SVCs and Soft PVCs.
            Entries are not present in this table for
            the VPIs used by entries in the atmVclTable."
          ::= { atmMIBObjects 6}

     atmVplEntry         OBJECT-TYPE
          SYNTAX         AtmVplEntry
          MAX-ACCESS     not-accessible
          STATUS         current
          DESCRIPTION
           "An entry in the VPL table.  This entry is
            used to model a bi-directional VPL.
            To create a VPL at an ATM interface,
            either of the following procedures are used:

            Negotiated VPL establishment

          (1) The management application creates
              a VPL entry in the atmVplTable
              by setting atmVplRowStatus to createAndWait(5).
              This may fail for the following reasons:
              - The selected VPI value is unavailable,
              - The selected VPI value is in use.
              Otherwise, the agent creates a row and
              reserves the VPI value on that port.

          (2) The manager selects an existing row(s) in the
              atmTrafficDescrParamTable,
              thereby, selecting a set of self-consistent
              ATM traffic parameters and the service category
              for receive and transmit directions of the VPL.

         (2a) If no suitable row(s) in the
              atmTrafficDescrParamTable exists,
              the manager must create a new row(s)
              in that table.

         (2b) The manager characterizes the VPL's traffic
              parameters through setting the
              atmVplReceiveTrafficDescrIndex and the
              atmVplTransmitTrafficDescrIndex values
              in the VPL table, which point to the rows
              containing desired ATM traffic parameter values
              in the atmTrafficDescrParamTable.  The agent
              will check the availability of resources and
              may refuse the request.
              If the transmit and receive service categories
              are inconsistent, the agent should refuse the
              request.

          (3) The manager activates the VPL by setting the
              the atmVplRowStatus to active(1).
              If this set is successful, the agent has
              reserved the resources to satisfy the requested
              traffic parameter values and the service category
              for that VPL.

          (4) If the VPL terminates a VPC in the ATM host
              or switch, the manager turns on the
              atmVplAdminStatus to up(1) to turn the VPL
              traffic flow on.  Otherwise, the
              atmVpCrossConnectTable  must be used
              to cross-connect the VPL to another VPL(s)
              in an ATM switch or network.

            One-Shot VPL Establishment

            A VPL may also be established in one step by a
            set-request with all necessary VPL parameter
            values and atmVplRowStatus set to createAndGo(4).

            In contrast to the negotiated VPL establishment
            which allows for detailed error checking
            (i.e., set errors are explicitly linked to
            particular resource acquisition failures),
            the one-shot VPL establishment
            performs the setup on one operation but
            does not have the advantage of step-wise
            error checking.

            VPL Retirement

            A VPL is released by setting atmVplRowStatus to
            destroy(6), and the agent may release all
            associated resources."
          INDEX  {ifIndex, atmVplVpi }
          ::= { atmVplTable  1}

     AtmVplEntry    ::= SEQUENCE  {
          atmVplVpi          AtmVpIdentifier,
          atmVplAdminStatus  AtmVorXAdminStatus,
          atmVplOperStatus   AtmVorXOperStatus,
          atmVplLastChange   AtmVorXLastChange,
          atmVplReceiveTrafficDescrIndex
                         AtmTrafficDescrParamIndex,
          atmVplTransmitTrafficDescrIndex
                         AtmTrafficDescrParamIndex,
          atmVplCrossConnectIdentifier INTEGER,
          atmVplRowStatus    RowStatus,
          atmVplCastType     AtmConnCastType,
          atmVplConnKind     AtmConnKind
             }


     atmVplVpi           OBJECT-TYPE
          SYNTAX         AtmVpIdentifier
          MAX-ACCESS     not-accessible
          STATUS         current
          DESCRIPTION
           "The VPI value of the VPL."
          ::= { atmVplEntry 1}

     atmVplAdminStatus   OBJECT-TYPE
          SYNTAX         AtmVorXAdminStatus
          MAX-ACCESS     read-create
          STATUS         current
          DESCRIPTION
           "This object is instanciated only for a VPL
            which terminates a VPC (i.e., one which is
            NOT cross-connected to other VPLs).
            Its value specifies the desired
            administrative state of the VPL."
          DEFVAL { down }
          ::= { atmVplEntry 2}

     atmVplOperStatus    OBJECT-TYPE
          SYNTAX         AtmVorXOperStatus
          MAX-ACCESS     read-only
          STATUS         current
          DESCRIPTION
           "The current operational status of the VPL."
          ::= { atmVplEntry 3}

     atmVplLastChange    OBJECT-TYPE
          SYNTAX         AtmVorXLastChange
          MAX-ACCESS     read-only
          STATUS         current
          DESCRIPTION
           "The value of sysUpTime at the time this
            VPL entered its current operational state."
          ::= { atmVplEntry 4 }

     atmVplReceiveTrafficDescrIndex  OBJECT-TYPE
          SYNTAX         AtmTrafficDescrParamIndex
          MAX-ACCESS     read-create
          STATUS         current
          DESCRIPTION
           "The value of this object identifies the row
            in the atmTrafficDescrParamTable which
            applies to the receive direction of the VPL."
          DEFVAL { 0 }
           ::= { atmVplEntry 5}

     atmVplTransmitTrafficDescrIndex  OBJECT-TYPE
          SYNTAX         AtmTrafficDescrParamIndex
          MAX-ACCESS     read-create
          STATUS         current
          DESCRIPTION
           "The value of this object identifies the row
            in the atmTrafficDescrParamTable which
            applies to the transmit direction of the VPL."
          DEFVAL { 0 }
           ::= { atmVplEntry 6}

     atmVplCrossConnectIdentifier   OBJECT-TYPE
          SYNTAX         INTEGER (0..2147483647)
          MAX-ACCESS     read-only
          STATUS         current
          DESCRIPTION
           "This object is instantiated only for a VPL
            which is cross-connected to other VPLs
            that belong to the same VPC.  All such
            associated VPLs have the same value of this
            object, and all their cross-connections are
            identified either by entries that are indexed
            by the same value of atmVpCrossConnectIndex in
            the atmVpCrossConnectTable of this MIB module or by
            the same value of the cross-connect index in
            the cross-connect table for SVCs and Soft PVCs
            (defined in a separate MIB module).
            At no time should entries in these respective
            cross-connect tables exist simultaneously
            with the same cross-connect index value.
            The value of this object is initialized by the
            agent after the associated entries in the
            atmVpCrossConnectTable have been created."
          ::= {atmVplEntry 7}

     atmVplRowStatus     OBJECT-TYPE
          SYNTAX         RowStatus
          MAX-ACCESS     read-create
          STATUS         current
          DESCRIPTION
           "This object is used to create, delete
            or modify a row in this table.
            To create a new VCL, this object is
            initially set to 'createAndWait' or
            'createAndGo'.  This object should not be
            set to 'active' unless the following columnar
            objects have been set to their desired value
            in this row:
            atmVplReceiveTrafficDescrIndex and
            atmVplTransmitTrafficDescrIndex.
            The DESCRIPTION of atmVplEntry provides
            further guidance to row treatment in this table."
          DEFVAL { createAndWait }
          ::= {atmVplEntry 8}

     atmVplCastType      OBJECT-TYPE
          SYNTAX         AtmConnCastType
          MAX-ACCESS     read-create
          STATUS         current
          DESCRIPTION
           "The connection topology type."
          DEFVAL { p2p }
          ::= {atmVplEntry 9}

     atmVplConnKind      OBJECT-TYPE
          SYNTAX         AtmConnKind
          MAX-ACCESS     read-create
          STATUS         current
          DESCRIPTION
           "The use of call control."
          DEFVAL { pvc }
          ::= {atmVplEntry 10}

     --  ATM Interface Virtual Channel Link (VCL) Table

     -- This table contains configuration and state
     -- information of a bi-directional Virtual Channel
     -- Link (VCL) at an ATM interface.
     -- This table can be used to create, delete or modify
     -- a VCL that is terminated in an ATM host or switch.
     -- This table can also be
     -- used to create, delete or modify a VCL that is
     -- cross-connected to another VCL.


     --  The ATM Interface VCL Table


     atmVclTable         OBJECT-TYPE
          SYNTAX         SEQUENCE OF AtmVclEntry
          MAX-ACCESS     not-accessible
          STATUS         current
          DESCRIPTION
           "The Virtual Channel Link (VCL) table.  A
            bi-directional VCL is modeled as one entry
            in this table. This table can be used for
            PVCs, SVCs and Soft PVCs."
          ::= { atmMIBObjects 7}

     atmVclEntry         OBJECT-TYPE
          SYNTAX         AtmVclEntry
          MAX-ACCESS     not-accessible
          STATUS         current
          DESCRIPTION
           "An entry in the VCL table. This entry is
            used to model a bi-directional VCL.
            To create a VCL at an ATM interface,
            either of the following procedures are used:

            Negotiated VCL establishment

          (1) The management application creates
              a VCL entry in the atmVclTable
              by setting atmVclRowStatus to createAndWait(5).
              This may fail for the following reasons:
              - The selected VPI/VCI values are unavailable,
              - The selected VPI/VCI values are in use.
              Otherwise, the agent creates a row and
              reserves the VPI/VCI values on that port.

          (2) The manager selects an existing row(s) in the
              atmTrafficDescrParamTable,
              thereby, selecting a set of self-consistent
              ATM traffic parameters and the service category
              for receive and transmit directions of the VCL.

         (2a) If no suitable row(s) in the
              atmTrafficDescrParamTable exists,
              the manager must create a new row(s)
              in that table.

         (2b) The manager characterizes the VCL's traffic
              parameters through setting the
              atmVclReceiveTrafficDescrIndex and the
              atmVclTransmitTrafficDescrIndex values
              in the VCL table, which point to the rows
              containing desired ATM traffic parameter values
              in the atmTrafficDescrParamTable.  The agent
              will check the availability of resources and
              may refuse the request.
              If the transmit and receive service categories
              are inconsistent, the agent should refuse the
              request.

          (3) The manager activates the VCL by setting the
              the atmVclRowStatus to active(1) (for
              requirements on this activation see the
              description of atmVclRowStatus).
              If this set is successful, the agent has
              reserved the resources to satisfy the requested
              traffic parameter values and the service category
              for that VCL.
          (4) If the VCL terminates a VCC in the ATM host
              or switch, the manager turns on the
              atmVclAdminStatus to up(1) to turn the VCL
              traffic flow on.  Otherwise, the
              atmVcCrossConnectTable  must be used
              to cross-connect the VCL to another VCL(s)
              in an ATM switch or network.

           One-Shot VCL Establishment

           A VCL may also be established in one step by a
           set-request with all necessary VCL parameter
           values and atmVclRowStatus set to createAndGo(4).

           In contrast to the negotiated VCL establishment
           which allows for detailed error checking
           (i.e., set errors are explicitly linked to
           particular resource acquisition failures),
           the one-shot VCL establishment
           performs the setup on one operation but
           does not have the advantage of step-wise
           error checking.

           VCL Retirement

           A VCL is released by setting atmVclRowStatus to
           destroy(6), and the agent may release all
           associated resources."
          INDEX  {ifIndex, atmVclVpi, atmVclVci }
          ::= { atmVclTable  1}

     AtmVclEntry    ::= SEQUENCE  {
          atmVclVpi                     AtmVpIdentifier,
          atmVclVci                     AtmVcIdentifier,
          atmVclAdminStatus             AtmVorXAdminStatus,
          atmVclOperStatus              AtmVorXOperStatus,
          atmVclLastChange              AtmVorXLastChange,
          atmVclReceiveTrafficDescrIndex
                                AtmTrafficDescrParamIndex,
          atmVclTransmitTrafficDescrIndex
                                AtmTrafficDescrParamIndex,
--          atmVccAalType                 INTEGER,
--          atmVccAal5CpcsTransmitSduSize INTEGER,
--          atmVccAal5CpcsReceiveSduSize  INTEGER,
--          atmVccAal5EncapsType          INTEGER,
          atmVclCrossConnectIdentifier  INTEGER,
          atmVclRowStatus               RowStatus,
          atmVclCastType                AtmConnCastType,
          atmVclConnKind                AtmConnKind
                 }

     atmVclVpi           OBJECT-TYPE
          SYNTAX         AtmVpIdentifier
          MAX-ACCESS     not-accessible
          STATUS         current
          DESCRIPTION
           "The VPI value of the VCL."
          ::= { atmVclEntry 1}

     atmVclVci           OBJECT-TYPE
          SYNTAX         AtmVcIdentifier
          MAX-ACCESS     not-accessible
          STATUS         current
          DESCRIPTION
           "The VCI value of the VCL."
          ::= { atmVclEntry 2}

     atmVclAdminStatus   OBJECT-TYPE
          SYNTAX         AtmVorXAdminStatus
          MAX-ACCESS     read-create
          STATUS         current
          DESCRIPTION
           "This object is instanciated only for a VCL which
            terminates a VCC (i.e., one which is NOT
            cross-connected to other VCLs). Its value
            specifies the desired administrative state of
            the VCL."
          DEFVAL { down }
          ::= { atmVclEntry 3}

     atmVclOperStatus    OBJECT-TYPE
          SYNTAX         AtmVorXOperStatus
          MAX-ACCESS     read-only
          STATUS         current
          DESCRIPTION
           "The current operational status of the VCL."
          ::= { atmVclEntry 4}

     atmVclLastChange    OBJECT-TYPE
          SYNTAX         AtmVorXLastChange
          MAX-ACCESS     read-only
          STATUS         current
          DESCRIPTION
           "The value of sysUpTime at the time this VCL
            entered its current operational state."
          ::= { atmVclEntry 5 }

     atmVclReceiveTrafficDescrIndex  OBJECT-TYPE
          SYNTAX         AtmTrafficDescrParamIndex
          MAX-ACCESS     read-create
          STATUS         current
          DESCRIPTION
           "The value of this object identifies the row
            in the ATM Traffic Descriptor Table which
            applies to the receive direction of this VCL."
          DEFVAL { 0 }
           ::= { atmVclEntry 6}

     atmVclTransmitTrafficDescrIndex  OBJECT-TYPE
          SYNTAX         AtmTrafficDescrParamIndex
          MAX-ACCESS     read-create
          STATUS         current
          DESCRIPTION
           "The value of this object identifies the row
            of the ATM Traffic Descriptor Table which applies
            to the transmit direction of this VCL."
          DEFVAL { 0 }
           ::= { atmVclEntry 7}

--     atmVccAalType       OBJECT-TYPE
--          SYNTAX         INTEGER {
--                            aal1(1),
--                            aal34(2),
--                            aal5(3),
--                            other(4),
--                            unknown(5),
--                            aal2(6)
--                              }
--          MAX-ACCESS    read-create
--          STATUS        current
--          DESCRIPTION
--           "An instance of this object only exists when the
--            local VCL end-point is also the VCC end-point,
--            and AAL is in use.
--            The type of AAL used on this VCC.
--            The AAL type includes AAL1, AAL2, AAL3/4,
--            and AAL5. The other(4) may be user-defined
--            AAL type.  The unknown type indicates that
--            the AAL type cannot be determined."
--          DEFVAL { aal5 }
--          ::= { atmVclEntry 8 }

--     atmVccAal5CpcsTransmitSduSize OBJECT-TYPE
--          SYNTAX         INTEGER (1..65535)
--          MAX-ACCESS     read-create
--          STATUS         current
--          DESCRIPTION
--           "An instance of this object only exists when the
--            local VCL end-point is also the VCC end-point,
--            and AAL5 is in use.
--            The maximum AAL5 CPCS SDU size in octets that is
--            supported on the transmit direction of this VCC."
--          DEFVAL { 9188 }
--                ::= { atmVclEntry 9 }

--     atmVccAal5CpcsReceiveSduSize OBJECT-TYPE
--          SYNTAX         INTEGER (1..65535)
--          MAX-ACCESS     read-create
--          STATUS         current
--          DESCRIPTION
--           "An instance of this object only exists when the
--            local VCL end-point is also the VCC end-point,
--            and AAL5 is in use.
--            The maximum AAL5 CPCS SDU size in octets that is
--            supported on the receive direction of this VCC."
--          DEFVAL { 9188 }
--                ::= { atmVclEntry 10 }

--     atmVccAal5EncapsType  OBJECT-TYPE
--          SYNTAX         INTEGER {
--                         vcMultiplexRoutedProtocol(1),
--                         vcMultiplexBridgedProtocol8023(2),
--                         vcMultiplexBridgedProtocol8025(3),
--                         vcMultiplexBridgedProtocol8026(4),
--                         vcMultiplexLANemulation8023(5),
--                         vcMultiplexLANemulation8025(6),
--                         llcEncapsulation(7),
--                         multiprotocolFrameRelaySscs(8),
--                         other(9),
--                         unknown(10)
--                            }
--          MAX-ACCESS     read-create
--          STATUS         current
--          DESCRIPTION
--           "An instance of this object only exists when the
--            local VCL end-point is also the VCC end-point,
--            and AAL5 is in use.
--            The type of data encapsulation used over
--            the AAL5 SSCS layer. The definitions reference
--            RFC 1483 Multiprotocol Encapsulation
--            over ATM AAL5 and to the ATM Forum
--            LAN Emulation specification."
--          DEFVAL { llcEncapsulation }
--                ::= { atmVclEntry 11 }

     atmVclCrossConnectIdentifier   OBJECT-TYPE
          SYNTAX         INTEGER (0..2147483647)
          MAX-ACCESS     read-only
          STATUS         current
          DESCRIPTION
           "This object is instantiated only for a VCL
            which is cross-connected to other VCLs
            that belong to the same VCC.  All such
            associated VCLs have the same value of this
            object, and all their cross-connections are
            identified either by entries that are indexed
            by the same value of atmVcCrossConnectIndex in
            the atmVcCrossConnectTable of this MIB module or by
            the same value of the cross-connect index in
            the cross-connect table for SVCs and Soft PVCs
            (defined in a separate MIB module).

            At no time should entries in these respective
            cross-connect tables exist simultaneously
            with the same cross-connect index value.
            The value of this object is initialized by the
            agent after the associated entries in the
            atmVcCrossConnectTable have been created."
          ::= {atmVclEntry 12}

     atmVclRowStatus     OBJECT-TYPE
          SYNTAX         RowStatus
          MAX-ACCESS     read-create
          STATUS         current
          DESCRIPTION
           "This object is used to create, delete or
            modify a row in this table.  To create
            a new VCL, this object is initially set
            to 'createAndWait' or 'createAndGo'.
            This object should not be
            set to 'active' unless the following columnar
            objects have been set to their desired value
            in this row:
            atmVclReceiveTrafficDescrIndex,
            atmVclTransmitTrafficDescrIndex.
            In addition, if the local VCL end-point
            is also the VCC end-point:
            atmVccAalType.
            In addition, for AAL5 connections only:
            atmVccAal5CpcsTransmitSduSize,
            atmVccAal5CpcsReceiveSduSize, and
            atmVccAal5EncapsType. (The existence
            of these objects imply the AAL connection type.).
            The DESCRIPTION of atmVclEntry provides
            further guidance to row treatment in this table."
          DEFVAL { createAndWait }
                ::= {atmVclEntry 13}

     atmVclCastType      OBJECT-TYPE
          SYNTAX         AtmConnCastType
          MAX-ACCESS     read-create
          STATUS         current
          DESCRIPTION
           "The connection topology type."
          DEFVAL { p2p }
                ::= {atmVclEntry 14}


     atmVclConnKind      OBJECT-TYPE
          SYNTAX         AtmConnKind
          MAX-ACCESS     read-create
          STATUS         current
          DESCRIPTION
           "The use of call control."
          DEFVAL { pvc }
          ::= {atmVclEntry 15}


     --     ATM Virtual Path (VP) Cross Connect Table

     -- This table contains configuration and state
     -- information of point-to-point,
     -- point-to-multipoint, or multipoint-to-multipoint
     -- VP cross-connects for PVCs.

     -- This table has read-create access and can be used
     -- to cross-connect the VPLs together in an ATM switch
     -- or network. The atmVpCrossConnectIndex
     -- is used to associate the related
     -- VPLs that are cross-connected together.

     -- The ATM VP Cross Connect Table
     -- models each bi-directional VPC
     -- cross-connect as a set of entries in
     -- the atmVpCrossConnectTable. A
     -- point-to-point VPC cross-connect is modeled
     -- as one entry; a point-to-multipoint (N leafs) VPC
     -- cross-connect as N entries in this table; and
     -- a multipoint-to-multipoint (N parties) VPC cross-
     -- connect as N(N-1)/2 entries in this table.
     -- In the latter cases, all the N (or N(N-1)/2) entries
     -- are associated with a single VPC cross-connect by
     -- having the same value of atmVpCrossConnectIndex.


     --      _________________________________________
     --      |                                       |
     --  Low |         ATM Switch or Network         | High
     --  port|                                       | port
     -- _____|>> from low to high VPC traffic flow >>|______
     --      |<< from high to low VPC traffic flow <<|
     --      |                                       |
     --      |_______________________________________|
     --

     -- The terms low and high are chosen to represent
     -- numerical ordering of the two interfaces associated
     -- with a VPC cross-connect. That is, the ATM interface
     -- with the lower value of ifIndex is termed 'low',
     -- while the other ATM interface associated with the
     -- VPC cross-connect is termed 'high'. This terminology
     -- is used to provide directional information; for
     -- example, the atmVpCrossConnectL2HOperStatus applies
     -- to the low->high direction, and
     -- atmVpCrossConnectH2LOperStatus applies to the
     -- high->low  direction, as illustrated above.




     atmVpCrossConnectIndexNext  OBJECT-TYPE
          SYNTAX         INTEGER (0..2147483647)
          MAX-ACCESS     read-only
          STATUS         current
          DESCRIPTION
           "This object contains an appropriate value to
            be used for atmVpCrossConnectIndex when creating
            entries in the atmVpCrossConnectTable.  The value
            0 indicates that no unassigned entries are
            available. To obtain the atmVpCrossConnectIndex
            value for a new entry, the manager issues a
            management protocol retrieval operation to obtain
            the current value of this object.  After each
            retrieval, the agent should modify the value to
            the next unassigned index.
            After a manager retrieves a value the agent will
            determine through its local policy when this index
            value will be made available for reuse."
          ::= { atmMIBObjects 8 }


     --  The ATM VP Cross Connect Table


     atmVpCrossConnectTable OBJECT-TYPE
          SYNTAX         SEQUENCE OF AtmVpCrossConnectEntry
          MAX-ACCESS     not-accessible
          STATUS         current
          DESCRIPTION
           "The ATM VP Cross Connect table for PVCs.
            An entry in this table models two
            cross-connected VPLs.
            Each VPL must have its atmConnKind set
            to pvc(1)."
          ::= { atmMIBObjects 9 }


     atmVpCrossConnectEntry OBJECT-TYPE
          SYNTAX         AtmVpCrossConnectEntry
          MAX-ACCESS     not-accessible
          STATUS         current
          DESCRIPTION
           "An entry in the ATM VP Cross Connect table.
            This entry is used to model a bi-directional
            ATM VP cross-connect which cross-connects
            two VPLs.

            Step-wise Procedures to set up a VP Cross-connect

            Once the entries in the atmVplTable are created,
            the following procedures are used
            to cross-connect the VPLs together.

           (1) The manager obtains a unique
               atmVpCrossConnectIndex by reading the
               atmVpCrossConnectIndexNext object.

           (2) Next, the manager creates a set of one
               or more rows in the ATM VP Cross Connect
               Table, one for each cross-connection between
               two VPLs.  Each row is indexed by the ATM
               interface port numbers and VPI values of the
               two ends of that cross-connection.
               This set of rows specifies the topology of the
               VPC cross-connect and is identified by a single
               value of atmVpCrossConnectIndex.

            Negotiated VP Cross-Connect Establishment

          (2a) The manager creates a row in this table by
               setting atmVpCrossConnectRowStatus to
               createAndWait(5).  The agent checks the
               requested topology and the mutual sanity of
               the ATM traffic parameters and
               service categories, i.e., the row creation
               fails if:
               - the requested topology is incompatible with
                 associated values of atmVplCastType,
               - the requested topology is not supported
                 by the agent,
               - the traffic/service category parameter values
                 associated with the requested row are
                 incompatible with those of already existing
                 rows for this VP cross-connect.
               [For example, for setting up
               a point-to-point VP cross-connect, the
               ATM traffic parameters in the receive direction
               of a VPL at the low end of the cross-connect
               must equal to the traffic parameters in the
               transmit direction of the other VPL at the
               high end of the cross-connect,
               otherwise, the row creation fails.]
               The agent also checks for internal errors
               in building the cross-connect.

               The atmVpCrossConnectIndex values in the
               corresponding atmVplTable rows are filled
               in by the agent at this point.

          (2b) The manager promotes the row in the
               atmVpCrossConnectTable by setting
               atmVpCrossConnectRowStatus to active(1).  If
               this set is successful, the agent has reserved
               the resources specified by the ATM traffic
               parameter and Service category values
               for each direction of the VP cross-connect
               in an ATM switch or network.

           (3) The manager sets the
               atmVpCrossConnectAdminStatus to up(1) in all
               rows of this VP cross-connect to turn the
               traffic flow on.


            One-Shot VP Cross-Connect Establishment

            A VP cross-connect may also be established in
            one step by a set-request with all necessary
            parameter values and atmVpCrossConnectRowStatus
            set to createAndGo(4).

            In contrast to the negotiated VP cross-connect
            establishment which allows for detailed error
            checking (i.e., set errors are explicitly linked
            to particular resource acquisition failures),
            the one-shot VP cross-connect establishment
            performs the setup on one operation but does not
            have the advantage of step-wise error checking.

            VP Cross-Connect Retirement

            A VP cross-connect identified by a particular
            value of atmVpCrossConnectIndex is released by:

           (1) Setting atmVpCrossConnectRowStatus of all
               rows identified by this value of
               atmVpCrossConnectIndex to destroy(6).
               The agent may release all
               associated resources, and the
               atmVpCrossConnectIndex values in the
               corresponding atmVplTable row are removed.
               Note that a situation when only a subset of
               the associated rows are deleted corresponds
               to a VP topology change.

           (2) After deletion of the appropriate
               atmVpCrossConnectEntries, the manager may
               set atmVplRowStatus to destroy(6) the
               associated VPLs.  The agent releases
               the resources and removes the associated
               rows in the atmVplTable.

            VP Cross-connect Reconfiguration

            At the discretion of the agent, a VP
            cross-connect may be reconfigured by
            adding and/or deleting leafs to/from
            the VP topology as per the VP cross-connect
            establishment/retirement procedures.
            Reconfiguration of traffic/service category parameter
            values requires release of the VP cross-connect
            before those parameter values may by changed
            for individual VPLs."
          INDEX { atmVpCrossConnectIndex,
                atmVpCrossConnectLowIfIndex,
                atmVpCrossConnectLowVpi,
                atmVpCrossConnectHighIfIndex,
                atmVpCrossConnectHighVpi }
          ::= { atmVpCrossConnectTable 1 }

     AtmVpCrossConnectEntry ::= SEQUENCE {
          atmVpCrossConnectIndex          INTEGER,
          atmVpCrossConnectLowIfIndex     InterfaceIndex,
          atmVpCrossConnectLowVpi         AtmVpIdentifier,
          atmVpCrossConnectHighIfIndex    InterfaceIndex,
          atmVpCrossConnectHighVpi        AtmVpIdentifier,
          atmVpCrossConnectAdminStatus    AtmVorXAdminStatus,
          atmVpCrossConnectL2HOperStatus  AtmVorXOperStatus,
          atmVpCrossConnectH2LOperStatus  AtmVorXOperStatus,
          atmVpCrossConnectL2HLastChange  AtmVorXLastChange,
          atmVpCrossConnectH2LLastChange  AtmVorXLastChange,
          atmVpCrossConnectRowStatus      RowStatus
                  }

     atmVpCrossConnectIndex OBJECT-TYPE
          SYNTAX         INTEGER (1..2147483647)
          MAX-ACCESS     not-accessible
          STATUS         current
          DESCRIPTION
           "A unique value to identify this VP cross-connect.
            For each VPL associated with this cross-connect,
            the agent reports this cross-connect index value
            in the atmVplCrossConnectIdentifier attribute of
            the corresponding atmVplTable entries."
          ::= { atmVpCrossConnectEntry 1 }

     atmVpCrossConnectLowIfIndex OBJECT-TYPE
          SYNTAX         InterfaceIndex
          MAX-ACCESS     not-accessible
          STATUS         current
          DESCRIPTION
           "The ifIndex value of the ATM interface for
            this VP cross-connect. The term low implies
            that this ATM interface has the numerically lower
            ifIndex value than the other ATM interface
            identified in the same atmVpCrossConnectEntry."
          ::= { atmVpCrossConnectEntry 2 }

     atmVpCrossConnectLowVpi OBJECT-TYPE
          SYNTAX         AtmVpIdentifier
          MAX-ACCESS     not-accessible
          STATUS         current
          DESCRIPTION
           "The VPI value at the ATM interface
            associated with the VP cross-connect that is
            identified by atmVpCrossConnectLowIfIndex."
          ::= { atmVpCrossConnectEntry 3 }

     atmVpCrossConnectHighIfIndex OBJECT-TYPE
          SYNTAX         InterfaceIndex
          MAX-ACCESS     not-accessible
          STATUS  current
          DESCRIPTION
           "The ifIndex value of the ATM interface for
            this VP cross-connect. The term high implies that
            this ATM interface has the numerically higher
            ifIndex value than the  other ATM interface
            identified in the same atmVpCrossConnectEntry."
          ::= { atmVpCrossConnectEntry 4 }

     atmVpCrossConnectHighVpi OBJECT-TYPE
          SYNTAX         AtmVpIdentifier
          MAX-ACCESS     not-accessible
          STATUS         current
          DESCRIPTION
           "The VPI value at the ATM interface
            associated with the VP cross-connect that is
            identified by atmVpCrossConnectHighIfIndex."
          ::= { atmVpCrossConnectEntry 5 }

     atmVpCrossConnectAdminStatus OBJECT-TYPE
          SYNTAX         AtmVorXAdminStatus
          MAX-ACCESS     read-create
          STATUS         current
          DESCRIPTION
           "The desired administrative status of this
            bi-directional VP cross-connect."
          DEFVAL { down }
          ::= { atmVpCrossConnectEntry 6 }

     atmVpCrossConnectL2HOperStatus OBJECT-TYPE
          SYNTAX         AtmVorXOperStatus
          MAX-ACCESS     read-only
          STATUS         current
          DESCRIPTION
           "The operational status of the VP cross-connect
            in one direction; (i.e., from the low to
            high direction)."
          ::= { atmVpCrossConnectEntry 7 }

     atmVpCrossConnectH2LOperStatus OBJECT-TYPE
          SYNTAX         AtmVorXOperStatus
          MAX-ACCESS     read-only
          STATUS         current
          DESCRIPTION
           "The operational status of the VP cross-connect
            in one direction; (i.e., from the high to
            low direction)."
          ::= { atmVpCrossConnectEntry 8 }

     atmVpCrossConnectL2HLastChange OBJECT-TYPE
          SYNTAX         AtmVorXLastChange
          MAX-ACCESS     read-only
          STATUS         current
          DESCRIPTION
           "The value of sysUpTime at the time this
            VP cross-connect entered its current operational
            state in the low to high direction."
          ::= { atmVpCrossConnectEntry 9 }

     atmVpCrossConnectH2LLastChange OBJECT-TYPE
          SYNTAX         AtmVorXLastChange
          MAX-ACCESS     read-only
          STATUS         current
          DESCRIPTION
            "The value of sysUpTime at the time this
            VP cross-connect entered its current operational
            in the high to low direction."
          ::= { atmVpCrossConnectEntry 10 }

     atmVpCrossConnectRowStatus OBJECT-TYPE
          SYNTAX         RowStatus
          MAX-ACCESS     read-create
          STATUS         current
          DESCRIPTION
           "The status of this entry in the
            atmVpCrossConnectTable.  This object is used to
            create a cross-connect for cross-connecting
            VPLs which are created using the atmVplTable
            or to change or delete an existing cross-connect.
            This object must be initially set
            to `createAndWait' or 'createAndGo'.
            To turn on a VP cross-connect,
            the atmVpCrossConnectAdminStatus
            is set to `up'."
          DEFVAL { createAndWait }
          ::= { atmVpCrossConnectEntry 11 }


     --     ATM Virtual Channel (VC) Cross Connect Table

     -- This table contains configuration and state
     -- information of point-to-point,
     -- point-to-multipoint or multipoint-to-multipoint
     -- VC cross-connects for PVCs.

     -- This table has read-create access and is used
     -- to cross-connect the VCLs together in an ATM switch
     -- or network that belong to a VC connection.
     -- The atmVcCrossConnectIndex is used to associate
     -- the related VCLs that are cross-connected together.



     -- The model using step-wise procedures described for setting
     -- up a VP cross-connect is also used for setting up
     -- a VC cross-connect.

     atmVcCrossConnectIndexNext  OBJECT-TYPE
          SYNTAX         INTEGER (0..2147483647)
          MAX-ACCESS     read-only
          STATUS         current
          DESCRIPTION
           "This object contains an appropriate value to
            be used for atmVcCrossConnectIndex when creating
            entries in the atmVcCrossConnectTable.  The value
            0 indicates that no unassigned entries are
            available. To obtain the atmVcCrossConnectIndex
            value for a new entry, the manager issues a
            management protocol retrieval operation to obtain
            the current value of this object.  After each
            retrieval, the agent should modify the value to
            the next unassigned index.
            After a manager retrieves a value the agent will
            determine through its local policy when this index
            value will be made available for reuse."
          ::= { atmMIBObjects 10 }


     --  The ATM VC Cross Connect Table


     atmVcCrossConnectTable OBJECT-TYPE
          SYNTAX         SEQUENCE OF AtmVcCrossConnectEntry
          MAX-ACCESS     not-accessible
          STATUS         current
          DESCRIPTION
           "The ATM VC Cross Connect table for PVCs.
            An entry in this table models two
            cross-connected VCLs.
            Each VCL must have its atmConnKind set
            to pvc(1)."
          ::= { atmMIBObjects 11 }


     atmVcCrossConnectEntry OBJECT-TYPE
          SYNTAX       AtmVcCrossConnectEntry
          MAX-ACCESS   not-accessible
          STATUS       current
          DESCRIPTION
           "An entry in the ATM VC Cross Connect table.
            This entry is used to model a bi-directional ATM
            VC cross-connect cross-connecting two end points.

            Step-wise Procedures to set up a VC Cross-connect
            Once the entries in the atmVclTable are created,
            the following procedures are used
            to cross-connect the VCLs together to
            form a VCC segment.

           (1) The manager obtains a unique
               atmVcCrossConnectIndex by reading the
               atmVcCrossConnectIndexNext object.

           (2) Next, the manager creates a set of one
               or more rows in the ATM VC Cross Connect
               Table, one for each cross-connection between
               two VCLs.  Each row is indexed by the ATM
               interface port numbers and VPI/VCI values of
               the two ends of that cross-connection.
               This set of rows specifies the topology of the
               VCC cross-connect and is identified by a single
               value of atmVcCrossConnectIndex.

            Negotiated VC Cross-Connect Establishment

          (2a) The manager creates a row in this table by
               setting atmVcCrossConnectRowStatus to
               createAndWait(5).  The agent checks the
               requested topology and the mutual sanity of
               the ATM traffic parameters and
               service categories, i.e., the row creation
               fails if:
               - the requested topology is incompatible with
                 associated values of atmVclCastType,
               - the requested topology is not supported
                 by the agent,
               - the traffic/service category parameter values
                 associated with the requested row are
                 incompatible with those of already existing
                 rows for this VC cross-connect.
               [For example, for setting up
               a point-to-point VC cross-connect, the
               ATM traffic parameters in the receive direction
               of a VCL at the low end of the cross-connect
               must equal to the traffic parameters in the
               transmit direction of the other VCL at the
               high end of the cross-connect,
               otherwise, the row creation fails.]
               The agent also checks for internal errors
               in building the cross-connect.

               The atmVcCrossConnectIndex values in the
               corresponding atmVclTable rows are filled
               in by the agent at this point.

          (2b) The manager promotes the row in the
               atmVcCrossConnectTable by setting
               atmVcCrossConnectRowStatus to active(1).  If
               this set is successful, the agent has reserved
               the resources specified by the ATM traffic
               parameter and Service category values
               for each direction of the VC cross-connect
               in an ATM switch or network.

           (3) The manager sets the
               atmVcCrossConnectAdminStatus to up(1)
               in all rows of this VC cross-connect to
               turn the traffic flow on.


            One-Shot VC Cross-Connect Establishment

            A VC cross-connect may also be established in
            one step by a set-request with all necessary
            parameter values and atmVcCrossConnectRowStatus
            set to createAndGo(4).

            In contrast to the negotiated VC cross-connect
            establishment which allows for detailed error
            checking i.e., set errors are explicitly linked to
            particular resource acquisition failures), the
            one-shot VC cross-connect establishment
            performs the setup on one operation but does
            not have the advantage of step-wise error
            checking.

            VC Cross-Connect Retirement

            A VC cross-connect identified by a particular
            value of atmVcCrossConnectIndex is released by:

           (1) Setting atmVcCrossConnectRowStatus of all rows
               identified by this value of
               atmVcCrossConnectIndex to destroy(6).
               The agent may release all
               associated resources, and the
               atmVcCrossConnectIndex values in the
               corresponding atmVclTable row are removed.
               Note that a situation when only a subset of
               the associated rows are deleted corresponds
               to a VC topology change.

           (2) After deletion of the appropriate
               atmVcCrossConnectEntries, the manager may
               set atmVclRowStatus to destroy(6) the
               associated VCLs.  The agent releases
               the resources and removes the associated
               rows in the atmVclTable.

            VC Cross-Connect Reconfiguration

            At the discretion of the agent, a VC
            cross-connect may be reconfigured by
            adding and/or deleting leafs to/from
            the VC topology as per the VC cross-connect
            establishment/retirement procedures.
            Reconfiguration of traffic/service category parameter
            values requires release of the VC cross-connect
            before those parameter values may by changed
            for individual VCLs."
          INDEX { atmVcCrossConnectIndex,
                atmVcCrossConnectLowIfIndex,
                atmVcCrossConnectLowVpi,
                atmVcCrossConnectLowVci,
                atmVcCrossConnectHighIfIndex,
                atmVcCrossConnectHighVpi,
                atmVcCrossConnectHighVci }
          ::= { atmVcCrossConnectTable 1 }

     AtmVcCrossConnectEntry ::= SEQUENCE {
          atmVcCrossConnectIndex          INTEGER,
          atmVcCrossConnectLowIfIndex     InterfaceIndex,
          atmVcCrossConnectLowVpi         AtmVpIdentifier,
          atmVcCrossConnectLowVci         AtmVcIdentifier,
          atmVcCrossConnectHighIfIndex    InterfaceIndex,
          atmVcCrossConnectHighVpi        AtmVpIdentifier,
          atmVcCrossConnectHighVci        AtmVcIdentifier,
          atmVcCrossConnectAdminStatus    AtmVorXAdminStatus,
          atmVcCrossConnectL2HOperStatus  AtmVorXOperStatus,
          atmVcCrossConnectH2LOperStatus  AtmVorXOperStatus,
          atmVcCrossConnectL2HLastChange  AtmVorXLastChange,
          atmVcCrossConnectH2LLastChange  AtmVorXLastChange,
          atmVcCrossConnectRowStatus      RowStatus
                  }

     atmVcCrossConnectIndex OBJECT-TYPE
          SYNTAX         INTEGER (1..2147483647)
          MAX-ACCESS     not-accessible
          STATUS         current
          DESCRIPTION
           "A unique value to identify this VC cross-connect.
            For each VCL associated with this cross-connect,
            the agent reports this cross-connect index value
            in the atmVclCrossConnectIdentifier attribute of
            the corresponding atmVclTable entries."
          ::= { atmVcCrossConnectEntry 1 }

     atmVcCrossConnectLowIfIndex OBJECT-TYPE
          SYNTAX         InterfaceIndex
          MAX-ACCESS     not-accessible
          STATUS         current
          DESCRIPTION
           "The ifIndex value of the ATM interface for this
            VC cross-connect. The term low implies
            that this ATM interface has the numerically lower
            ifIndex value than the other ATM interface
            identified in the same atmVcCrossConnectEntry."
          ::= { atmVcCrossConnectEntry 2 }

     atmVcCrossConnectLowVpi OBJECT-TYPE
          SYNTAX         AtmVpIdentifier
          MAX-ACCESS     not-accessible
          STATUS         current
          DESCRIPTION
           "The VPI value at the ATM interface
            associated with the VC cross-connect that is
            identified by atmVcCrossConnectLowIfIndex."
          ::= { atmVcCrossConnectEntry 3 }

     atmVcCrossConnectLowVci OBJECT-TYPE
          SYNTAX         AtmVcIdentifier
          MAX-ACCESS     not-accessible
          STATUS         current
          DESCRIPTION
           "The VCI value at the ATM interface
            associated with this VC cross-connect that is
            identified by atmVcCrossConnectLowIfIndex."
          ::= { atmVcCrossConnectEntry 4 }

     atmVcCrossConnectHighIfIndex OBJECT-TYPE
          SYNTAX         InterfaceIndex
          MAX-ACCESS     not-accessible
          STATUS         current
          DESCRIPTION
           "The ifIndex value for the ATM interface for
            this VC cross-connect. The term high implies
            that this ATM interface has the numerically higher
            ifIndex value than the other ATM interface
            identified in the same atmVcCrossConnectEntry."
          ::= { atmVcCrossConnectEntry 5 }

     atmVcCrossConnectHighVpi OBJECT-TYPE
          SYNTAX         AtmVpIdentifier
          MAX-ACCESS     not-accessible
          STATUS         current
          DESCRIPTION
           "The VPI value at the ATM interface
            associated with the VC cross-connect that is
            identified by atmVcCrossConnectHighIfIndex."
          ::= { atmVcCrossConnectEntry 6 }

     atmVcCrossConnectHighVci OBJECT-TYPE
          SYNTAX         AtmVcIdentifier
          MAX-ACCESS     not-accessible
          STATUS         current
          DESCRIPTION
           "The VCI value at the ATM interface
            associated with the VC cross-connect that is
            identified by atmVcCrossConnectHighIfIndex."
          ::= { atmVcCrossConnectEntry 7 }

     atmVcCrossConnectAdminStatus OBJECT-TYPE
          SYNTAX         AtmVorXAdminStatus
          MAX-ACCESS     read-create
          STATUS         current
          DESCRIPTION
           "The desired administrative status of this
            bi-directional VC cross-connect."
          DEFVAL { down }
          ::= { atmVcCrossConnectEntry 8 }

     atmVcCrossConnectL2HOperStatus OBJECT-TYPE
          SYNTAX         AtmVorXOperStatus
          MAX-ACCESS     read-only
          STATUS         current
          DESCRIPTION
           "The current operational status of the
            VC cross-connect in one direction; (i.e.,
            from the low to high direction)."
          ::= { atmVcCrossConnectEntry 9 }


     atmVcCrossConnectH2LOperStatus OBJECT-TYPE
          SYNTAX         AtmVorXOperStatus
          MAX-ACCESS     read-only
          STATUS         current
          DESCRIPTION
           "The current operational status of the
            VC cross-connect in one direction; (i.e.,
            from the high to low direction)."
          ::= { atmVcCrossConnectEntry 10 }

     atmVcCrossConnectL2HLastChange OBJECT-TYPE
          SYNTAX         AtmVorXLastChange
          MAX-ACCESS     read-only
          STATUS         current
          DESCRIPTION
           "The value of sysUpTime at the time this
            VC cross-connect entered its current
            operational state in low to high direction."
          ::= { atmVcCrossConnectEntry 11 }

     atmVcCrossConnectH2LLastChange OBJECT-TYPE
          SYNTAX         AtmVorXLastChange
          MAX-ACCESS     read-only
          STATUS         current
          DESCRIPTION
           "The value of sysUpTime at the time this
            VC cross-connect entered its current
            operational state in high to low direction."
          ::= { atmVcCrossConnectEntry 12 }

     atmVcCrossConnectRowStatus OBJECT-TYPE
          SYNTAX         RowStatus
          MAX-ACCESS     read-create
          STATUS         current
          DESCRIPTION
           "The status of this entry in the
            atmVcCrossConnectTable.  This object is used to
            create a new cross-connect for cross-connecting
            VCLs which are created using the atmVclTable
            or to change or delete existing cross-connect.
            This object must be initially set to
            `createAndWait' or 'createAndGo'.
            To turn on a VC cross-connect,
            the atmVcCrossConnectAdminStatus
            is set to `up'."
          DEFVAL { createAndWait }
          ::= { atmVcCrossConnectEntry 13 }


     -- AAL5 Virtual Channel Connection Performance Statistics
     -- Table

     -- This table contains the AAL5
     -- performance statistics of a VCC at the
     -- interface associated with an AAL5 entity in an ATM
     -- host or ATM switch.


--     aal5VccTable        OBJECT-TYPE
--          SYNTAX         SEQUENCE OF Aal5VccEntry
--          MAX-ACCESS     not-accessible
--          STATUS         current
--          DESCRIPTION
--           "This table contains AAL5 VCC performance
--            parameters."
--          ::= { atmMIBObjects 12 }

--     aal5VccEntry        OBJECT-TYPE
--          SYNTAX         Aal5VccEntry
--          MAX-ACCESS     not-accessible
--          STATUS         current
--          DESCRIPTION
--           "This list contains the AAL5 VCC
--            performance parameters and is indexed
--            by ifIndex values of AAL5 interfaces
--            and the associated VPI/VCI values."
--          INDEX { ifIndex, aal5VccVpi, aal5VccVci }
--          ::= { aal5VccTable 1 }

--     Aal5VccEntry    ::= SEQUENCE  {
--          aal5VccVpi             AtmVpIdentifier,
--          aal5VccVci             AtmVcIdentifier,
--          aal5VccCrcErrors       Counter32,
--          aal5VccSarTimeOuts     Counter32,
--          aal5VccOverSizedSDUs   Counter32
--               }


--     aal5VccVpi          OBJECT-TYPE
--          SYNTAX         AtmVpIdentifier
--          MAX-ACCESS     not-accessible
--          STATUS         current
--          DESCRIPTION
--           "The VPI value of the AAL5 VCC at the
--            interface identified by the ifIndex."
--          ::= { aal5VccEntry 1 }

--     aal5VccVci          OBJECT-TYPE
--          SYNTAX         AtmVcIdentifier
--          MAX-ACCESS     not-accessible
--          STATUS         current
--          DESCRIPTION
--           "The VCI value of the AAL5 VCC at the
--            interface identified by the ifIndex."
--          ::= { aal5VccEntry 2 }

--     aal5VccCrcErrors    OBJECT-TYPE
--          SYNTAX         Counter32
--          MAX-ACCESS     read-only
--          STATUS         current
--          DESCRIPTION
--           "The number of AAL5 CPCS PDUs received with
--            CRC-32 errors on this AAL5 VCC at the
--            interface associated with an AAL5 entity."
--          ::= { aal5VccEntry 3 }

--     aal5VccSarTimeOuts  OBJECT-TYPE
--          SYNTAX         Counter32
--          MAX-ACCESS     read-only
--          STATUS         current
--          DESCRIPTION
--           "The number of partially re-assembled AAL5
--            CPCS PDUs which were discarded
--            on this AAL5 VCC at the interface associated
--            with an AAL5 entity because they
--            were not fully re-assembled within the
--            required time period.  If the re-assembly
--            timer is not supported, then this object
--            contains a zero value."
--          ::= { aal5VccEntry 4 }
--
--     aal5VccOverSizedSDUs OBJECT-TYPE
--          SYNTAX         Counter32
--          MAX-ACCESS     read-only
--          STATUS         current
--          DESCRIPTION
--           "The number of AAL5 CPCS PDUs discarded
--            on this AAL5 VCC at the interface
--            associated with an AAL5 entity because the
--            AAL5 SDUs were too large."
--          ::= { aal5VccEntry 5 }


     --
     -- The following object may be used in conjunction with
     -- the atmTrafficDescrParamTable for the creation of
     -- new table entries.
     --

     atmTrafficDescrParamIndexNext  OBJECT-TYPE
          SYNTAX         INTEGER (0..2147483647)
          MAX-ACCESS     read-only
          STATUS         current
          DESCRIPTION
           "This object contains an appropriate value to
            be used for atmTrafficDescrParamIndex when
            creating entries in the
            atmTrafficDescrParamTable.
            The value 0 indicates that no unassigned
            entries are available. To obtain the
            atmTrafficDescrParamIndex value for a new
            entry, the manager issues a management
            protocol retrieval operation to obtain the
            current value of this object.  After each
            retrieval, the agent should modify the value
            to the next unassigned index.
            After a manager retrieves a value the agent will
            determine through its local policy when this index
            value will be made available for reuse."
          ::= { atmMIBObjects 13 }

     END


--------------------------------------------------------------------------
-- Rfc2662, ADSL-TC-MIB
--------------------------------------------------------------------------
   ADSL-TC-MIB DEFINITIONS ::= BEGIN

   IMPORTS
       transmission,
       MODULE-IDENTITY, Gauge32            FROM SNMPv2-SMI
       TEXTUAL-CONVENTION                  FROM SNMPv2-TC;

   adsltcmib MODULE-IDENTITY

   LAST-UPDATED "9908190000Z"

   ORGANIZATION "IETF ADSL MIB Working Group"

   CONTACT-INFO
       "
       Gregory Bathrick
       AG Communication Systems
       A Subsidiary of Lucent Technologies
       2500 W Utopia Rd.
       Phoenix, AZ 85027 USA
       Tel: +1 602-582-7679
       Fax: +1 602-582-7697
       E-mail: bathricg@agcs.com

       Faye Ly
       Copper Mountain Networks
       Norcal Office
       2470 Embarcadero Way
       Palo Alto, CA 94303
       Tel: +1 650-858-8500
       Fax: +1 650-858-8085
       E-Mail: faye@coppermountain.com
       IETF ADSL MIB Working Group (adsl@xlist.agcs.com)
       "
       DESCRIPTION
           "The MIB module which provides a ADSL
           Line Coding Textual Convention to be used
           by ADSL Lines."

       --  Revision history
       REVISION     "9908190000Z"  -- 19 August 1999, midnight
       DESCRIPTION  "Initial Version, published as RFC 2662"

       ::= { transmission 94 2 } -- adslMIB 2

       AdslLineCodingType ::= TEXTUAL-CONVENTION
           STATUS       current
           DESCRIPTION
               "This data type is used as the syntax for the ADSL
               Line Code."
           SYNTAX  INTEGER {
               other(1),-- none of the following
               dmt (2), -- Discrete MultiTone
               cap (3), -- Carrierless Amplitude & Phase modulation
               qam (4),  -- Quadrature Amplitude Modulation
               lite (5) -- g.lite
           }

       AdslPerfCurrDayCount ::= TEXTUAL-CONVENTION
           STATUS  current
           DESCRIPTION
               "A counter associated with interface performance
               measurements in a current 1-day (24 hour) measurement
               interval.

               The value of this counter starts at zero at the
               beginning of an interval and is increased when
               associated events occur, until the end of the
               1-day interval.  At that time the value of the
               counter is stored in the previous 1-day history
               interval, if available, and the current interval
               counter is restarted at zero.

               In the case where the agent has no valid data available
               for this interval the corresponding object
               instance is not available and upon a retrieval
               request a corresponding error message shall be
               returned to indicate that this instance does
               not exist (for example, a noSuchName error for
               SNMPv1 and a noSuchInstance for SNMPv2 GET
               operation)."
            SYNTAX  Gauge32

       AdslPerfPrevDayCount ::= TEXTUAL-CONVENTION
           STATUS  current
           DESCRIPTION
               "A counter associated with interface performance
               measurements during the most previous 1-day (24 hour)
               measurement interval.  The value of this counter is
               equal to the value of the current day counter at
               the end of its most recent interval.

               In the case where the agent has no valid data available
               for this interval the corresponding object
               instance is not available and upon a retrieval
               request a corresponding error message shall be
               returned to indicate that this instance does
               not exist (for example, a noSuchName error for
               SNMPv1 and a noSuchInstance for SNMPv2 GET
               operation)."
           SYNTAX  Gauge32

       AdslPerfTimeElapsed ::= TEXTUAL-CONVENTION
           STATUS current
           DESCRIPTION
               "The number of seconds that have elapsed since
               the beginning of the current measurement period.
               If, for some reason, such as an adjustment in the
               system's time-of-day clock, the current interval
               exceeds the maximum value, the agent will return
               the maximum value."
           SYNTAX  Gauge32

   END

   ADSL-LINE-MIB DEFINITIONS ::= BEGIN

   IMPORTS
       MODULE-IDENTITY, OBJECT-TYPE,
       Counter32, Gauge32,
       NOTIFICATION-TYPE,
       transmission, Unsigned32          FROM SNMPv2-SMI
       RowStatus,
       TruthValue, VariablePointer       FROM SNMPv2-TC
       MODULE-COMPLIANCE, OBJECT-GROUP,
       NOTIFICATION-GROUP                FROM SNMPv2-CONF
       ifIndex                           FROM IF-MIB
       PerfCurrentCount,
       PerfIntervalCount                 FROM PerfHist-TC-MIB
       SnmpAdminString                   FROM SNMP-FRAMEWORK-MIB
       AdslPerfCurrDayCount,
       AdslPerfPrevDayCount,
       AdslPerfTimeElapsed,
       AdslLineCodingType                FROM ADSL-TC-MIB
       ;

   adslMIB MODULE-IDENTITY

   LAST-UPDATED "9908190000Z"

   ORGANIZATION "IETF ADSL MIB Working Group"

   CONTACT-INFO
       "
       Gregory Bathrick
       AG Communication Systems
       A Subsidiary of Lucent Technologies
       2500 W Utopia Rd.
       Phoenix, AZ 85027 USA
       Tel: +1 602-582-7679
       Fax: +1 602-582-7697
       E-mail: bathricg@agcs.com

       Faye Ly
       Copper Mountain Networks
       Norcal Office
       2470 Embarcadero Way
       Palo Alto, CA 94303
       Tel: +1 650-858-8500
       Fax: +1 650-858-8085
       E-Mail: faye@coppermountain.com

       (ADSL Forum input only)
       John Burgess
       Predictive Systems, Inc.
       25A Vreeland Rd.
       Florham Park, NJ 07932 USA
       Tel: +1 973-301-5610
       Fax: +1 973-301-5699
       E-mail: jtburgess@predictive.com

       IETF ADSL MIB Working Group (adsl@xlist.agcs.com)
       "

   DESCRIPTION
       "The MIB module defining objects for the management of a pair of
       ADSL modems at each end of the ADSL line.  Each such line has
       an entry in an ifTable which may include multiple modem lines.
       An agent may reside at either end of the ADSL line however the
       MIB is designed to require no management communication between
       them beyond that inherent in the low-level ADSL line protocol.
       The agent may monitor and control this protocol for its needs.

       ADSL lines may support optional Fast or Interleaved channels.
       If these are supported, additional entries corresponding to the
       supported channels must be created in the ifTable. Thus an ADSL
       line that supports both channels will have three entries in the
       ifTable, one for each physical, fast, and interleaved, whose
       ifType values are equal to adsl(94), fast(125), and
       interleaved(124), respectively. The ifStackTable is used to
       represent the relationship between the entries.

       Naming Conventions:
                 Atuc -- (ATUC) modem at near (Central) end of line
                 Atur -- (ATUR) modem at Remote end of line
                 Curr -- Current
                 Prev -- Previous
                 Atn -- Attenuation
                 ES  -- Errored Second.
                 LCS -- Line Code Specific
                 Lof -- Loss of Frame
                 Lol -- Loss of Link
                 Los -- Loss of Signal
                 Lpr -- Loss of Power
                 xxxs-- interval of Seconds in which xxx occurs
                         (e.g., xxx=Lof, Los, Lpr)
                 Max -- Maximum
                 Mgn -- Margin
                 Min -- Minimum
                 Psd -- Power Spectral Density
                 Snr -- Signal to Noise Ratio
                 Tx  -- Transmit
                 Blks-- Blocks, a data unit, see
                        adslAtuXChanCrcBlockLength
         "
         --  Revision history
         REVISION     "9908190000Z"  -- 19 August 1999, midnight
         DESCRIPTION  "Initial Version, published as RFC 2662"

   ::= { transmission 94 }

   adslLineMib OBJECT IDENTIFIER ::= { adslMIB 1 }

   adslMibObjects OBJECT IDENTIFIER ::= { adslLineMib 1 }

   -- objects
         adslLineTable   OBJECT-TYPE
             SYNTAX          SEQUENCE OF AdslLineEntry
             MAX-ACCESS      not-accessible
             STATUS          current
             DESCRIPTION
                 "This table includes common attributes describing
                 both ends of the line.  It is required for all ADSL
                 physical interfaces.  ADSL physical interfaces are
                 those ifEntries where ifType is equal to adsl(94)."
         ::= { adslMibObjects 1 }

         adslLineEntry   OBJECT-TYPE
             SYNTAX          AdslLineEntry
             MAX-ACCESS      not-accessible
             STATUS          current
             DESCRIPTION     "An entry in adslLineTable."
             INDEX           { ifIndex }
         ::= { adslLineTable 1 }

         AdslLineEntry ::=
             SEQUENCE {
             adslLineCoding           AdslLineCodingType,
             adslLineType             INTEGER,
             adslLineSpecific         VariablePointer,
             adslLineConfProfile      SnmpAdminString,
             adslLineAlarmConfProfile SnmpAdminString
             }

         adslLineCoding OBJECT-TYPE
             SYNTAX      AdslLineCodingType
             MAX-ACCESS  read-write
             STATUS      current
             DESCRIPTION
                 "Specifies the ADSL coding type used on this
                 line."
         ::= { adslLineEntry 1 }

        adslLineType OBJECT-TYPE
             SYNTAX      INTEGER {
                 noChannel (1),        -- no channels exist
                 fastOnly (2),         -- fast channel exists only
                 interleavedOnly (3),  -- interleaved channel exists
                                       -- only
                 fastOrInterleaved (4),-- either fast or interleaved
                                       -- channels can exist, but
                                       -- only one at any time
                 fastAndInterleaved (5)-- both fast or interleaved
                                    -- channels exist
             }
             MAX-ACCESS  read-write
             STATUS      current
             DESCRIPTION
                 "Defines the type of ADSL physical line
                 entity that exists, by defining whether and how
                 the line is channelized.  If the line is channelized,
                 the value will be other than noChannel(1).  This
                 object defines which channel type(s) are supported.

                 In the case that the line is channelized, the manager
                 can use the ifStackTable to determine the ifIndex for
                 the associated channel(s)."
         ::= { adslLineEntry 2 }

         adslLineSpecific OBJECT-TYPE
             SYNTAX      VariablePointer
             MAX-ACCESS  read-only
             STATUS      current
             DESCRIPTION
                 "OID instance in vendor-specific MIB. The Instance may
                 be used to determine shelf/slot/port of the ATUC
                 interface in a DSLAM."
         ::= { adslLineEntry 3 }

        adslLineConfProfile OBJECT-TYPE
             SYNTAX      SnmpAdminString (SIZE (1..32))
             MAX-ACCESS  read-write
             STATUS      current
             DESCRIPTION
                 "The value of this object identifies the row
                 in the ADSL Line Configuration Profile Table,
                 (adslLineConfProfileTable), which applies for this
                 ADSL line, and channels if applicable.

                 For `dynamic' mode, in the case which the
                 configuration profile has not been set, the
                 value will be set to `DEFVAL'.

                 If the implementator of this MIB has chosen not
                 to implement `dynamic assignment' of profiles, this
                 object's MIN-ACCESS is read-only."
         ::= { adslLineEntry 4 }

        adslLineAlarmConfProfile OBJECT-TYPE
             SYNTAX      SnmpAdminString (SIZE (1..32))
             MAX-ACCESS  read-write
             STATUS      current
             DESCRIPTION
                 "The value of this object identifies the row
                 in the ADSL Line Alarm Configuration Profile Table,
                 (adslLineAlarmConfProfileTable), which applies to this
                 ADSL line, and channels if applicable.

                 For `dynamic' mode, in the case which the
                 alarm profile has not been set, the
                 value will be set to `DEFVAL'.

                 If the implementator of this MIB has chosen not
                 to implement `dynamic assignment' of profiles, this
                 object's MIN-ACCESS is read-only."
         ::= { adslLineEntry 5 }

         adslAtucPhysTable       OBJECT-TYPE
             SYNTAX          SEQUENCE OF AdslAtucPhysEntry
             MAX-ACCESS      not-accessible
             STATUS          current
             DESCRIPTION
                 "This table provides one row for each ATUC.
                 Each row contains the Physical Layer Parameters
                 table for that ATUC. ADSL physical interfaces are
                 those ifEntries where ifType is equal to adsl(94)."
         ::= { adslMibObjects 2 }

         adslAtucPhysEntry       OBJECT-TYPE
             SYNTAX          AdslAtucPhysEntry
             MAX-ACCESS      not-accessible
             STATUS          current
             DESCRIPTION     "An entry in the adslAtucPhysTable."
             INDEX           { ifIndex }
         ::= { adslAtucPhysTable 1 }

         AdslAtucPhysEntry ::=
             SEQUENCE {
             adslAtucInvSerialNumber         SnmpAdminString,
             adslAtucInvVendorID             SnmpAdminString,
             adslAtucInvVersionNumber        SnmpAdminString,
             adslAtucCurrSnrMgn              INTEGER,
             adslAtucCurrAtn                 Gauge32,
             adslAtucCurrStatus              BITS,
             adslAtucCurrOutputPwr           INTEGER,
             adslAtucCurrAttainableRate      Gauge32
             }

         -- inventory group
         --
         -- These items should describe the lowest level identifiable
         -- component, be it a stand-alone modem, a card in a rack,
         -- a child-board, etc.
         --
         adslAtucInvSerialNumber OBJECT-TYPE
             SYNTAX      SnmpAdminString (SIZE (0..32))
             MAX-ACCESS  read-only
             STATUS      current
             DESCRIPTION
                 "The vendor specific string that identifies the
                 vendor equipment."
         ::= { adslAtucPhysEntry 1 }

         adslAtucInvVendorID OBJECT-TYPE
             SYNTAX      SnmpAdminString (SIZE (0..16))
             MAX-ACCESS  read-only
             STATUS      current
             DESCRIPTION
                 "The vendor ID code is a copy of the binary
                 vendor identification field defined by the
                 PHY[10] and expressed as readable characters."

             REFERENCE "ANSI T1.413[10]"
         ::= { adslAtucPhysEntry 2 }

         adslAtucInvVersionNumber OBJECT-TYPE
             SYNTAX      SnmpAdminString (SIZE (0..16))
             MAX-ACCESS  read-only
             STATUS      current
             DESCRIPTION
                 "The vendor specific version number sent by this ATU
                 as part of the initialization messages.  It is a copy
                 of the binary version number field defined by the
                 PHY[10] and expressed as readable characters."
             REFERENCE "ANSI T1.413[10]"
         ::= { adslAtucPhysEntry 3 }

         -- current status group
         --
         adslAtucCurrSnrMgn OBJECT-TYPE
             SYNTAX      INTEGER (-640..640)
             UNITS       "tenth dB"
             MAX-ACCESS  read-only
             STATUS      current
             DESCRIPTION
                 "Noise Margin as seen by this ATU with respect to its
                 received signal in tenth dB."
         ::= { adslAtucPhysEntry 4 }

         adslAtucCurrAtn OBJECT-TYPE
             SYNTAX      Gauge32(0..630)
             UNITS       "tenth dB"
             MAX-ACCESS  read-only
             STATUS      current
             DESCRIPTION
                 "Measured difference in the total power transmitted by
                 the peer ATU and the total power received by this ATU."
         ::= { adslAtucPhysEntry 5 }

        adslAtucCurrStatus OBJECT-TYPE
             SYNTAX      BITS {
                               noDefect(0),
                               lossOfFraming(1),
                               lossOfSignal(2),
                               lossOfPower(3),
                               lossOfSignalQuality(4),
                               lossOfLink(5),
                               dataInitFailure(6),
                               configInitFailure(7),
                               protocolInitFailure(8),
                               noPeerAtuPresent(9)
                              }
             MAX-ACCESS  read-only
             STATUS      current
             DESCRIPTION
                 "Indicates current state of the ATUC line.  This is a
                 bit-map of possible conditions.  The various bit
                 positions are:

          0      noDefect             There no defects on the line

          1      lossOfFraming        ATUC failure due to not
                                      receiving valid frame.

          2      lossOfSignal         ATUC failure due to not
                                      receiving signal.

          3      lossOfPower          ATUC failure due to loss of
                                      power.
                                      Note: the Agent may still
                                      function.

          4      lossOfSignalQuality  Loss of Signal Quality is
                                      declared when the Noise Margin
                                      falls below the Minimum Noise
                                      Margin, or the bit-error-rate
                                      exceeds 10^-7.

          5      lossOfLink           ATUC failure due to inability
                                      to link with ATUR.

          6      dataInitFailure      ATUC failure during
                                      initialization due to bit
                                      errors corrupting startup
                                      exchange data.

          7      configInitFailure    ATUC failure during
                                      initialization due to peer
                                      ATU not able to support
                                      requested configuration

          8      protocolInitFailure  ATUC failure during
                                      initialization due to
                                      incompatible protocol used by
                                      the peer ATU.

          9      noPeerAtuPresent     ATUC failure during
                                      initialization due to no
                                      activation sequence detected
                                      from peer ATU.

                 This is intended to supplement ifOperStatus."
         ::= { adslAtucPhysEntry 6 }

         adslAtucCurrOutputPwr OBJECT-TYPE
             SYNTAX      INTEGER (-310..310)
             UNITS       "tenth dBm"
             MAX-ACCESS  read-only
             STATUS      current
             DESCRIPTION
                 "Measured total output power transmitted by this ATU.
                 This is the measurement that was reported during
                 the last activation sequence."
         ::= { adslAtucPhysEntry 7 }

         adslAtucCurrAttainableRate OBJECT-TYPE
             SYNTAX      Gauge32
             UNITS       "bps"
             MAX-ACCESS  read-only
             STATUS      current
             DESCRIPTION
                 "Indicates the maximum currently attainable data rate
                 by the ATU.  This value will be equal or greater than
                 the current line rate."
         ::= { adslAtucPhysEntry 8 }

         adslAturPhysTable        OBJECT-TYPE
             SYNTAX          SEQUENCE OF AdslAturPhysEntry
             MAX-ACCESS      not-accessible
             STATUS          current
             DESCRIPTION
                 "This table provides one row for each ATUR
                 Each row contains the Physical Layer Parameters
                 table for that ATUR. ADSL physical interfaces are
                 those ifEntries where ifType is equal to adsl(94)."
         ::= { adslMibObjects 3 }

         adslAturPhysEntry       OBJECT-TYPE
             SYNTAX          AdslAturPhysEntry
             MAX-ACCESS      not-accessible
             STATUS          current
             DESCRIPTION     "An entry in the adslAturPhysTable."
             INDEX           { ifIndex }
         ::= { adslAturPhysTable 1 }

         AdslAturPhysEntry ::=
             SEQUENCE {
             adslAturInvSerialNumber         SnmpAdminString,
             adslAturInvVendorID             SnmpAdminString,
             adslAturInvVersionNumber        SnmpAdminString,
             adslAturCurrSnrMgn              INTEGER,
             adslAturCurrAtn                 Gauge32,
             adslAturCurrStatus              BITS,
             adslAturCurrOutputPwr           INTEGER,
             adslAturCurrAttainableRate      Gauge32
             }

         -- inventory group
         --
         adslAturInvSerialNumber OBJECT-TYPE
             SYNTAX      SnmpAdminString (SIZE (0..32))
             MAX-ACCESS  read-only
             STATUS      current
             DESCRIPTION
                 "The vendor specific string that identifies the
                 vendor equipment."
         ::= { adslAturPhysEntry 1 }

         adslAturInvVendorID OBJECT-TYPE
             SYNTAX      SnmpAdminString (SIZE (0..16))
             MAX-ACCESS  read-only
             STATUS      current
             DESCRIPTION
                 "The vendor ID code is a copy of the binary
                 vendor identification field defined by the
                 PHY[10] and expressed as readable characters."
             REFERENCE "ANSI T1.413"
         ::= { adslAturPhysEntry 2 }

         adslAturInvVersionNumber OBJECT-TYPE
             SYNTAX      SnmpAdminString (SIZE (0..16))
             MAX-ACCESS  read-only
             STATUS      current
             DESCRIPTION
                 "The vendor specific version number sent by this ATU
                 as part of the initialization messages.  It is a copy
                 of the binary version number field defined by the
                 PHY[10] and expressed as readable characters."
             REFERENCE "ANSI T1.413"
         ::= { adslAturPhysEntry 3 }

         -- current status group
         --
         adslAturCurrSnrMgn OBJECT-TYPE
             SYNTAX      INTEGER (-640..640)
             UNITS       "tenth dB"
             MAX-ACCESS  read-only
             STATUS      current
             DESCRIPTION
                 "Noise Margin as seen by this ATU with respect to its
                 received signal in tenth dB."
         ::= { adslAturPhysEntry 4 }

         adslAturCurrAtn OBJECT-TYPE
             SYNTAX      Gauge32(0..630)
             UNITS       "tenth dB"
             MAX-ACCESS  read-only
             STATUS      current
             DESCRIPTION
                 "Measured difference in the total power transmitted by
                 the peer ATU and the total power received by this ATU."
         ::= { adslAturPhysEntry 5 }

        adslAturCurrStatus OBJECT-TYPE
             SYNTAX     BITS {
                              noDefect(0),
                              lossOfFraming(1),
                              lossOfSignal(2),
                              lossOfPower(3),
                              lossOfSignalQuality(4)
                             }
             MAX-ACCESS  read-only
             STATUS      current
             DESCRIPTION
                 "Indicates current state of the ATUR line.  This is a
                 bit-map of possible conditions.  Due to the isolation
                 of the ATUR when line problems occur, many state
                 conditions like loss of power, loss of quality signal,
                 and initialization errors,  can not be determined.
                 While trouble shooting ATUR, also use object,
                 adslAtucCurrStatus.  The various bit positions are:

          0      noDefect             There no defects on the line

          1      lossOfFraming        ATUR failure due to not
                                      receiving valid frame

          2      lossOfSignal         ATUR failure due to not
                                      receiving signal

          3      lossOfPower          ATUR failure due to loss of
                                      power

          4      lossOfSignalQuality  Loss of Signal Quality is
                                      declared when the Noise Margin
                                      falls below the Minimum Noise
                                      Margin, or the
                                      bit-error-rate exceeds 10^-7.

                 This is intended to supplement ifOperStatus."
         ::= { adslAturPhysEntry 6 }

         adslAturCurrOutputPwr OBJECT-TYPE
             SYNTAX      INTEGER (-310..310)
             UNITS       "tenth dBm"
             MAX-ACCESS  read-only
             STATUS      current
             DESCRIPTION
                 "Measured total output power transmitted by this ATU.
                 This is the measurement that was reported during
                 the last activation sequence."
         ::= { adslAturPhysEntry 7 }

         adslAturCurrAttainableRate OBJECT-TYPE
             SYNTAX      Gauge32
             UNITS       "bps"
             MAX-ACCESS  read-only
             STATUS      current
             DESCRIPTION
                 "Indicates the maximum currently attainable data rate
                 by the ATU.  This value will be equal or greater than
                 the current line rate."
         ::= { adslAturPhysEntry 8 }

         adslAtucChanTable       OBJECT-TYPE
             SYNTAX          SEQUENCE OF AdslAtucChanEntry
             MAX-ACCESS      not-accessible
             STATUS          current
             DESCRIPTION
                 "This table provides one row for each ATUC channel.
                 ADSL channel interfaces are those ifEntries
                 where ifType is equal to adslInterleave(124)
                 or adslFast(125)."
         ::= { adslMibObjects 4 }

         adslAtucChanEntry       OBJECT-TYPE
             SYNTAX          AdslAtucChanEntry
             MAX-ACCESS      not-accessible
             STATUS          current
             DESCRIPTION     "An entry in the adslAtucChanTable."
             INDEX           { ifIndex }
         ::= { adslAtucChanTable 1 }

         AdslAtucChanEntry ::=
             SEQUENCE {
             adslAtucChanInterleaveDelay     Gauge32,
             adslAtucChanCurrTxRate          Gauge32,
             adslAtucChanPrevTxRate          Gauge32,
             adslAtucChanCrcBlockLength      Gauge32
             }

         -- current group
         --
         adslAtucChanInterleaveDelay OBJECT-TYPE
             SYNTAX      Gauge32
             UNITS       "milli-seconds"
             MAX-ACCESS  read-only
             STATUS      current
             DESCRIPTION
                 "Interleave Delay for this channel.

                 Interleave delay applies only to the
                 interleave channel and defines the mapping
                 (relative spacing) between subsequent input
                 bytes at the interleaver input and their placement
                 in the bit stream at the interleaver output.
                 Larger numbers provide greater separation between
                 consecutive input bytes in the output bit stream
                 allowing for improved impulse noise immunity at
                 the expense of payload latency.

                 In the case where the ifType is Fast(125), use
                 noSuchObject."
         ::= { adslAtucChanEntry 1 }

         adslAtucChanCurrTxRate  OBJECT-TYPE
             SYNTAX      Gauge32
             UNITS       "bps"
             MAX-ACCESS  read-only
             STATUS      current
             DESCRIPTION
                 "Actual transmit rate on this channel."
         ::= { adslAtucChanEntry 2 }

         adslAtucChanPrevTxRate OBJECT-TYPE
             SYNTAX      Gauge32
             UNITS        "bps"
             MAX-ACCESS  read-only
             STATUS      current
             DESCRIPTION
                 "The rate at the time of the last
                 adslAtucRateChangeTrap event. It is also set at
                 initialization to prevent a trap being sent.

                 Rate changes less than adslAtucThresh(*)RateDown
                 or less than adslAtucThresh(*)RateUp will not
                 cause a trap or cause this object to change.
                 (*) == Fast or Interleave.
                 See AdslLineAlarmConfProfileEntry."
         ::= { adslAtucChanEntry 3 }

         adslAtucChanCrcBlockLength OBJECT-TYPE
             SYNTAX      Gauge32
             UNITS        "byte"
             MAX-ACCESS  read-only
             STATUS      current
             DESCRIPTION
                 "Indicates the length of the channel data-block
                 on which the CRC operates.  Refer to Line Code
                 Specific MIBs, [11] and [12] for more
                 information."
         ::= { adslAtucChanEntry 4 }

        adslAturChanTable       OBJECT-TYPE
             SYNTAX          SEQUENCE OF AdslAturChanEntry
             MAX-ACCESS      not-accessible
             STATUS          current
             DESCRIPTION
                 "This table provides one row for each ATUR channel.
                 ADSL channel interfaces are those ifEntries
                 where ifType is equal to adslInterleave(124)
                 or adslFast(125)."
         ::= { adslMibObjects 5 }

         adslAturChanEntry       OBJECT-TYPE
             SYNTAX          AdslAturChanEntry
             MAX-ACCESS      not-accessible
             STATUS          current
             DESCRIPTION     "An entry in the adslAturChanTable."
             INDEX           { ifIndex }
         ::= { adslAturChanTable 1 }

         AdslAturChanEntry ::=
             SEQUENCE {
             adslAturChanInterleaveDelay     Gauge32,
             adslAturChanCurrTxRate          Gauge32,
             adslAturChanPrevTxRate          Gauge32,
             adslAturChanCrcBlockLength      Gauge32
             }

         -- current group
         --
         adslAturChanInterleaveDelay OBJECT-TYPE
             SYNTAX      Gauge32
             UNITS       "milli-seconds"
             MAX-ACCESS  read-only
             STATUS      current
             DESCRIPTION
                 "Interleave Delay for this channel.

                 Interleave delay applies only to the
                 interleave channel and defines the mapping
                 (relative spacing) between subsequent input
                 bytes at the interleaver input and their placement
                 in the bit stream at the interleaver output.
                 Larger numbers provide greater separation between
                 consecutive input bytes in the output bit stream
                 allowing for improved impulse noise immunity at
                 the expense of payload latency.

                 In the case where the ifType is Fast(125), use
                 noSuchObject."
         ::= { adslAturChanEntry 1 }

         adslAturChanCurrTxRate  OBJECT-TYPE
             SYNTAX      Gauge32
             UNITS       "bps"
             MAX-ACCESS  read-only
             STATUS      current
             DESCRIPTION
                 "Actual transmit rate on this channel."
         ::= { adslAturChanEntry 2 }

         adslAturChanPrevTxRate OBJECT-TYPE
             SYNTAX      Gauge32
             UNITS       "bps"
             MAX-ACCESS  read-only
             STATUS      current
             DESCRIPTION
                "The rate at the time of the last
                 adslAturRateChangeTrap event. It is also set at
                 initialization to prevent a trap being sent.
                 Rate changes less than adslAturThresh(*)RateDown
                 or less than adslAturThresh(*)RateUp will not
                 cause a trap or cause this object to change.
                 (*) == Fast or Interleave.
                 See AdslLineAlarmConfProfileEntry."
         ::= { adslAturChanEntry 3 }

         adslAturChanCrcBlockLength OBJECT-TYPE
             SYNTAX      Gauge32
             MAX-ACCESS  read-only
             STATUS      current
             DESCRIPTION
                 "Indicates the length of the channel data-block
                 on which the CRC operates.  Refer to Line Code
                 Specific MIBs, [11] and [12] for more
                 information."
         ::= { adslAturChanEntry 4 }

         adslAtucPerfDataTable   OBJECT-TYPE
             SYNTAX          SEQUENCE OF AdslAtucPerfDataEntry
             MAX-ACCESS      not-accessible
             STATUS          current
             DESCRIPTION
                 "This table provides one row for each ATUC.
                 ADSL physical interfaces are
                 those ifEntries where ifType is equal to adsl(94)."
         ::= { adslMibObjects 6 }

         adslAtucPerfDataEntry       OBJECT-TYPE
             SYNTAX          AdslAtucPerfDataEntry
             MAX-ACCESS      not-accessible
             STATUS          current
             DESCRIPTION     "An entry in adslAtucPerfDataTable."
             INDEX           { ifIndex }
         ::= { adslAtucPerfDataTable 1 }

         AdslAtucPerfDataEntry ::=
             SEQUENCE {
             adslAtucPerfLofs                 Counter32,
             adslAtucPerfLoss                 Counter32,
             adslAtucPerfLols                 Counter32,
             adslAtucPerfLprs                 Counter32,
             adslAtucPerfESs                  Counter32,
             adslAtucPerfInits                Counter32,
             adslAtucPerfValidIntervals       INTEGER,
             adslAtucPerfInvalidIntervals     INTEGER,
             adslAtucPerfCurr15MinTimeElapsed AdslPerfTimeElapsed,
             adslAtucPerfCurr15MinLofs        PerfCurrentCount,
             adslAtucPerfCurr15MinLoss        PerfCurrentCount,
             adslAtucPerfCurr15MinLols        PerfCurrentCount,
             adslAtucPerfCurr15MinLprs        PerfCurrentCount,
             adslAtucPerfCurr15MinESs         PerfCurrentCount,
             adslAtucPerfCurr15MinInits       PerfCurrentCount,
             adslAtucPerfCurr1DayTimeElapsed  AdslPerfTimeElapsed,
             adslAtucPerfCurr1DayLofs         AdslPerfCurrDayCount,
             adslAtucPerfCurr1DayLoss         AdslPerfCurrDayCount,
             adslAtucPerfCurr1DayLols         AdslPerfCurrDayCount,
             adslAtucPerfCurr1DayLprs         AdslPerfCurrDayCount,
             adslAtucPerfCurr1DayESs          AdslPerfCurrDayCount,
             adslAtucPerfCurr1DayInits        AdslPerfCurrDayCount,
             adslAtucPerfPrev1DayMoniSecs     INTEGER,
             adslAtucPerfPrev1DayLofs         AdslPerfPrevDayCount,
             adslAtucPerfPrev1DayLoss         AdslPerfPrevDayCount,
             adslAtucPerfPrev1DayLols         AdslPerfPrevDayCount,
             adslAtucPerfPrev1DayLprs         AdslPerfPrevDayCount,
             adslAtucPerfPrev1DayESs          AdslPerfPrevDayCount,
             adslAtucPerfPrev1DayInits        AdslPerfPrevDayCount
             }

         -- Event Counters
         --
         -- Also see adslAtucIntervalTable for 15 minute interval
         -- elapsed counters.
         --
         adslAtucPerfLofs OBJECT-TYPE
             SYNTAX      Counter32
             MAX-ACCESS  read-only
             STATUS      current
             DESCRIPTION
                 "Count of the number of Loss of Framing failures since
                 agent reset."
         ::= { adslAtucPerfDataEntry 1 }

         adslAtucPerfLoss  OBJECT-TYPE
             SYNTAX      Counter32
             MAX-ACCESS  read-only
             STATUS      current
             DESCRIPTION
                 "Count of the number of Loss of Signal failures since
                 agent reset."
         ::= { adslAtucPerfDataEntry 2 }

         adslAtucPerfLols OBJECT-TYPE
             SYNTAX      Counter32
             MAX-ACCESS  read-only
             STATUS      current
             DESCRIPTION
                 "Count of the number of Loss of Link failures since
                 agent reset."
         ::= { adslAtucPerfDataEntry 3 }

         adslAtucPerfLprs OBJECT-TYPE
             SYNTAX      Counter32
             MAX-ACCESS  read-only
             STATUS      current
             DESCRIPTION
                 "Count of the number of Loss of Power failures since
                 agent reset."
         ::= { adslAtucPerfDataEntry 4 }

         adslAtucPerfESs OBJECT-TYPE
             SYNTAX      Counter32
             MAX-ACCESS  read-only
             STATUS      current
             DESCRIPTION
                 "Count of the number of Errored Seconds since agent
                 reset.  The errored second parameter is a count of
                 one-second intervals containing one or more crc
                 anomalies, or one or more los or sef defects."
         ::= { adslAtucPerfDataEntry 5 }

         adslAtucPerfInits OBJECT-TYPE
             SYNTAX      Counter32
             MAX-ACCESS  read-only
             STATUS      current
             DESCRIPTION
                 "Count of the line initialization attempts since
                 agent reset. Includes both successful and failed
                 attempts."
         ::= { adslAtucPerfDataEntry 6 }

         -- general 15 min interval information
         --

         adslAtucPerfValidIntervals OBJECT-TYPE
             SYNTAX      INTEGER(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adslAtucPerfDataEntry 7 }

         adslAtucPerfInvalidIntervals OBJECT-TYPE
             SYNTAX      INTEGER(0..96)
             MAX-ACCESS  read-only
             STATUS      current
             DESCRIPTION
                 "The number of intervals in the range from
                 0 to the value of adslAtucPerfValidIntervals
                 for which no data is available. This object
                 will typically be zero except in cases where
                 the data for some intervals are not available
                 (e.g., in proxy situations)."
         ::= { adslAtucPerfDataEntry 8 }

         -- 15 min current performance group
         --
         adslAtucPerfCurr15MinTimeElapsed OBJECT-TYPE
             SYNTAX      AdslPerfTimeElapsed(0..899)
             UNITS       "seconds"
             MAX-ACCESS  read-only
             STATUS      current
             DESCRIPTION
                 "Total elapsed seconds in this interval."
         ::= { adslAtucPerfDataEntry 9 }

         adslAtucPerfCurr15MinLofs OBJECT-TYPE
             SYNTAX      PerfCurrentCount
             UNITS       "seconds"
             MAX-ACCESS  read-only
             STATUS      current
             DESCRIPTION
                 "Count of seconds in the current 15 minute interval
                 when there was Loss of Framing."
         ::= { adslAtucPerfDataEntry 10 }

         adslAtucPerfCurr15MinLoss  OBJECT-TYPE
             SYNTAX      PerfCurrentCount
             UNITS       "seconds"
             MAX-ACCESS  read-only
             STATUS      current
             DESCRIPTION
                 "Count of seconds in the current 15 minute interval
                 when there was Loss of Signal."
         ::= { adslAtucPerfDataEntry 11 }

         adslAtucPerfCurr15MinLols  OBJECT-TYPE
             SYNTAX      PerfCurrentCount
             UNITS       "seconds"
             MAX-ACCESS  read-only
             STATUS      current
             DESCRIPTION
                 "Count of seconds in the current 15 minute interval
                 when there was Loss of Link."
         ::= { adslAtucPerfDataEntry 12 }

         adslAtucPerfCurr15MinLprs  OBJECT-TYPE
             SYNTAX      PerfCurrentCount
             UNITS       "seconds"
             MAX-ACCESS  read-only
             STATUS      current
             DESCRIPTION
                 "Count of seconds in the current 15 minute interval
                 when there was Loss of Power."
         ::= { adslAtucPerfDataEntry 13 }

         adslAtucPerfCurr15MinESs OBJECT-TYPE
             SYNTAX      PerfCurrentCount
             UNITS       "seconds"
             MAX-ACCESS  read-only
             STATUS      current
             DESCRIPTION
                 "Count of Errored Seconds in the current 15 minute
                 interval.  The errored second parameter is a count of
                 one-second intervals containing one or more crc
                 anomalies, or one or more los or sef defects."
         ::= { adslAtucPerfDataEntry 14 }

         adslAtucPerfCurr15MinInits  OBJECT-TYPE
             SYNTAX      PerfCurrentCount
             MAX-ACCESS  read-only
             STATUS      current
             DESCRIPTION
                 "Count of the line initialization attempts in the
                 current 15 minute interval. Includes both successful
                 and failed attempts."
         ::= { adslAtucPerfDataEntry 15 }

         -- 1-day current and previous performance group
         --
         adslAtucPerfCurr1DayTimeElapsed OBJECT-TYPE
             SYNTAX      AdslPerfTimeElapsed(0..86399)
             UNITS       "seconds"
             MAX-ACCESS  read-only
             STATUS      current
             DESCRIPTION
                 "Number of seconds that have elapsed since the
                 beginning of the current 1-day interval."
         ::= { adslAtucPerfDataEntry 16 }

         adslAtucPerfCurr1DayLofs  OBJECT-TYPE
             SYNTAX      AdslPerfCurrDayCount
             UNITS       "seconds"
             MAX-ACCESS  read-only
             STATUS      current
             DESCRIPTION
                 "Count of the number of seconds when there was Loss of
                 Framing during the current day as measured by
                 adslAtucPerfCurr1DayTimeElapsed."
         ::= { adslAtucPerfDataEntry 17 }

         adslAtucPerfCurr1DayLoss  OBJECT-TYPE
             SYNTAX      AdslPerfCurrDayCount
             UNITS       "seconds"
             MAX-ACCESS  read-only
             STATUS      current
             DESCRIPTION
                 "Count of the number of seconds when there was Loss of
                 Signal during the current day as measured by
                 adslAtucPerfCurr1DayTimeElapsed."
         ::= { adslAtucPerfDataEntry 18 }

         adslAtucPerfCurr1DayLols  OBJECT-TYPE
             SYNTAX      AdslPerfCurrDayCount
             UNITS       "seconds"
             MAX-ACCESS  read-only
             STATUS      current
             DESCRIPTION
                 "Count of the number of seconds when there was Loss of
                 Link during the current day as measured by
                 adslAtucPerfCurr1DayTimeElapsed."
         ::= { adslAtucPerfDataEntry 19 }

         adslAtucPerfCurr1DayLprs  OBJECT-TYPE
             SYNTAX      AdslPerfCurrDayCount
             UNITS       "seconds"
             MAX-ACCESS  read-only
             STATUS      current
             DESCRIPTION
                 "Count of the number of seconds when there was Loss of
                 Power during the current day as measured by
                 adslAtucPerfCurr1DayTimeElapsed."
         ::= { adslAtucPerfDataEntry 20 }

         adslAtucPerfCurr1DayESs OBJECT-TYPE
             SYNTAX      AdslPerfCurrDayCount
             UNITS       "seconds"
             MAX-ACCESS  read-only
             STATUS      current
             DESCRIPTION
                 "Count of Errored Seconds during the current day as
                 measured by adslAtucPerfCurr1DayTimeElapsed.
                 The errored second parameter is a count of
                 one-second intervals containing one or more crc
                 anomalies, or one or more los or sef defects."
         ::= { adslAtucPerfDataEntry 21 }

         adslAtucPerfCurr1DayInits  OBJECT-TYPE
             SYNTAX      AdslPerfCurrDayCount
             MAX-ACCESS  read-only
             STATUS      current
             DESCRIPTION
                 "Count of the line initialization attempts in the
                 day as measured by adslAtucPerfCurr1DayTimeElapsed.
                 Includes both successful and failed attempts."
         ::= { adslAtucPerfDataEntry 22 }

         adslAtucPerfPrev1DayMoniSecs OBJECT-TYPE
             SYNTAX      INTEGER(0..86400)
             UNITS       "seconds"
             MAX-ACCESS  read-only
             STATUS      current
             DESCRIPTION
                 "The amount of time in the previous 1-day interval
                 over which the performance monitoring information
                 is actually counted. This value will be the same as
                 the interval duration except in a situation where
                 performance monitoring data could not be collected
                 for any reason."
         ::= { adslAtucPerfDataEntry 23 }

         adslAtucPerfPrev1DayLofs  OBJECT-TYPE
             SYNTAX      AdslPerfPrevDayCount
             UNITS       "seconds"
             MAX-ACCESS  read-only
             STATUS      current
             DESCRIPTION
                 "Count of seconds in the interval when there was
                 Loss of Framing within the most recent previous
                 1-day period."
         ::= { adslAtucPerfDataEntry 24 }

         adslAtucPerfPrev1DayLoss  OBJECT-TYPE
             SYNTAX      AdslPerfPrevDayCount
             UNITS       "seconds"
             MAX-ACCESS  read-only
             STATUS      current
             DESCRIPTION
                 "Count of seconds in the interval when there was
                 Loss of Signal within the most recent previous
                 1-day period."
         ::= { adslAtucPerfDataEntry 25 }

         adslAtucPerfPrev1DayLols  OBJECT-TYPE
             SYNTAX      AdslPerfPrevDayCount
             UNITS       "seconds"
             MAX-ACCESS  read-only
             STATUS      current
             DESCRIPTION
                 "Count of seconds in the interval when there was
                 Loss of Link within the most recent previous
                 1-day period."
         ::= { adslAtucPerfDataEntry 26 }

         adslAtucPerfPrev1DayLprs  OBJECT-TYPE
             SYNTAX      AdslPerfPrevDayCount
             UNITS       "seconds"
             MAX-ACCESS  read-only
             STATUS      current
             DESCRIPTION
                 "Count of seconds in the interval when there was
                 Loss of Power within the most recent previous
                 1-day period."
         ::= { adslAtucPerfDataEntry 27 }

         adslAtucPerfPrev1DayESs OBJECT-TYPE
             SYNTAX      AdslPerfPrevDayCount
             UNITS       "seconds"
             MAX-ACCESS  read-only
             STATUS      current
             DESCRIPTION
                 "Count of Errored Seconds within the most recent
                 previous 1-day period. The errored second parameter is
                 a count of one-second intervals containing one or more
                 crc anomalies, or one or more los or sef defects."
         ::= { adslAtucPerfDataEntry 28 }

         adslAtucPerfPrev1DayInits  OBJECT-TYPE
             SYNTAX      AdslPerfPrevDayCount
             MAX-ACCESS  read-only
             STATUS      current
             DESCRIPTION
                 "Count of the line initialization attempts in the most
                 recent previous 1-day period. Includes both successful
                 and failed attempts."
         ::= { adslAtucPerfDataEntry 29 }

         adslAturPerfDataTable   OBJECT-TYPE
             SYNTAX          SEQUENCE OF AdslAturPerfDataEntry
             MAX-ACCESS      not-accessible
             STATUS          current
             DESCRIPTION
                 "This table provides one row for each ATUR.
                 ADSL physical interfaces are
                 those ifEntries where ifType is equal to adsl(94)."
         ::= { adslMibObjects 7 }

         adslAturPerfDataEntry       OBJECT-TYPE
             SYNTAX          AdslAturPerfDataEntry
             MAX-ACCESS      not-accessible
             STATUS          current
             DESCRIPTION     "An entry in adslAturPerfDataTable."
             INDEX           { ifIndex }
         ::= { adslAturPerfDataTable 1 }

         AdslAturPerfDataEntry ::=
             SEQUENCE {
             adslAturPerfLofs                 Counter32,
             adslAturPerfLoss                 Counter32,
             adslAturPerfLprs                 Counter32,
             adslAturPerfESs                  Counter32,
             adslAturPerfValidIntervals       INTEGER,
             adslAturPerfInvalidIntervals     INTEGER,
             adslAturPerfCurr15MinTimeElapsed AdslPerfTimeElapsed,
             adslAturPerfCurr15MinLofs        PerfCurrentCount,
             adslAturPerfCurr15MinLoss        PerfCurrentCount,
             adslAturPerfCurr15MinLprs        PerfCurrentCount,
             adslAturPerfCurr15MinESs         PerfCurrentCount,
             adslAturPerfCurr1DayTimeElapsed  AdslPerfTimeElapsed,
             adslAturPerfCurr1DayLofs         AdslPerfCurrDayCount,
             adslAturPerfCurr1DayLoss         AdslPerfCurrDayCount,
             adslAturPerfCurr1DayLprs         AdslPerfCurrDayCount,
             adslAturPerfCurr1DayESs          AdslPerfCurrDayCount,
             adslAturPerfPrev1DayMoniSecs     INTEGER,
             adslAturPerfPrev1DayLofs         AdslPerfPrevDayCount,
             adslAturPerfPrev1DayLoss         AdslPerfPrevDayCount,
             adslAturPerfPrev1DayLprs         AdslPerfPrevDayCount,
             adslAturPerfPrev1DayESs          AdslPerfPrevDayCount
             }

         -- Event (Raw) Counters
         --
         -- Also see adslAturIntervalTable for 15 minute interval
         -- elapsed counters.
         --
         adslAturPerfLofs OBJECT-TYPE
             SYNTAX      Counter32
             UNITS       "seconds"
             MAX-ACCESS  read-only
             STATUS      current
             DESCRIPTION
                 "Count of the number of Loss of Framing failures since
                 agent reset."
         ::= { adslAturPerfDataEntry 1 }

         adslAturPerfLoss  OBJECT-TYPE
             SYNTAX      Counter32
             UNITS       "seconds"
             MAX-ACCESS  read-only
             STATUS      current
             DESCRIPTION
                 "Count of the number of Loss of Signal failures since
                 agent reset."
         ::= { adslAturPerfDataEntry 2 }

        adslAturPerfLprs  OBJECT-TYPE
             SYNTAX      Counter32
             UNITS       "seconds"
             MAX-ACCESS  read-only
             STATUS      current
             DESCRIPTION
                 "Count of the number of Loss of Power failures since
                 agent reset."
         ::= { adslAturPerfDataEntry 3 }

         adslAturPerfESs  OBJECT-TYPE
             SYNTAX      Counter32
             UNITS       "seconds"
             MAX-ACCESS  read-only
             STATUS      current
             DESCRIPTION
                 "Count of the number of Errored Seconds since agent
                 reset.  The errored second parameter is a count of
                 one-second intervals containing one or more crc
                 anomalies, or one or more los or sef defects."
         ::= { adslAturPerfDataEntry 4 }

         -- general 15 min interval information
         --
         adslAturPerfValidIntervals OBJECT-TYPE
             SYNTAX      INTEGER(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adslAturPerfDataEntry 5 }

         adslAturPerfInvalidIntervals OBJECT-TYPE
             SYNTAX      INTEGER(0..96)
             MAX-ACCESS  read-only
             STATUS      current
             DESCRIPTION
                 "The number of intervals in the range from
                 0 to the value of adslAturPerfValidIntervals
                 for which no data is available. This object
                 will typically be zero except in cases where
                 the data for some intervals are not available
                 (e.g., in proxy situations)."
         ::= { adslAturPerfDataEntry 6 }

         -- 15 min current performance group
         --
         adslAturPerfCurr15MinTimeElapsed OBJECT-TYPE
             SYNTAX      AdslPerfTimeElapsed(0..899)
             UNITS       "seconds"
             MAX-ACCESS  read-only
             STATUS      current
             DESCRIPTION
                 "Total elapsed seconds in this interval."
         ::= { adslAturPerfDataEntry 7 }

         adslAturPerfCurr15MinLofs OBJECT-TYPE
             SYNTAX      PerfCurrentCount
             UNITS       "seconds"
             MAX-ACCESS  read-only
             STATUS      current
             DESCRIPTION
                 "Count of seconds in the current 15 minute interval
                 when there was Loss of Framing."
         ::= { adslAturPerfDataEntry 8 }

         adslAturPerfCurr15MinLoss  OBJECT-TYPE
             SYNTAX      PerfCurrentCount
             UNITS       "seconds"
             MAX-ACCESS  read-only
             STATUS      current
             DESCRIPTION
                 "Count of seconds in the current 15 minute interval
                 when there was Loss of Signal."
         ::= { adslAturPerfDataEntry 9 }

         adslAturPerfCurr15MinLprs  OBJECT-TYPE
             SYNTAX      PerfCurrentCount
             UNITS       "seconds"
             MAX-ACCESS  read-only
             STATUS      current
             DESCRIPTION
                 "Count of seconds in the current 15 minute interval
                 when there was Loss of Power."
         ::= { adslAturPerfDataEntry 10 }

         adslAturPerfCurr15MinESs OBJECT-TYPE
             SYNTAX      PerfCurrentCount
             UNITS       "seconds"
             MAX-ACCESS  read-only
             STATUS      current
             DESCRIPTION
                "Count of Errored Seconds in the current 15 minute
                interval.  The errored second parameter is a count of
                one-second intervals containing one or more crc
                anomalies, or one or more los or sef defects."

         ::= { adslAturPerfDataEntry 11 }

         -- 1-day current and previous performance group
         --
         adslAturPerfCurr1DayTimeElapsed OBJECT-TYPE
             SYNTAX      AdslPerfTimeElapsed(0..86399)
             UNITS       "seconds"
             MAX-ACCESS  read-only
             STATUS      current
             DESCRIPTION
                 "Number of seconds that have elapsed since the
                 beginning of the current 1-day interval."
         ::= { adslAturPerfDataEntry 12 }

         adslAturPerfCurr1DayLofs  OBJECT-TYPE
             SYNTAX      AdslPerfCurrDayCount
             UNITS       "seconds"
             MAX-ACCESS  read-only
             STATUS      current
             DESCRIPTION
                 "Count of the number of seconds when there was Loss
                 of Framing during the current day as measured by
                 adslAturPerfCurr1DayTimeElapsed."
         ::= { adslAturPerfDataEntry 13 }

         adslAturPerfCurr1DayLoss  OBJECT-TYPE
             SYNTAX      AdslPerfCurrDayCount
             UNITS       "seconds"
             MAX-ACCESS  read-only
             STATUS      current
             DESCRIPTION
                 "Count of the number of seconds when there was Loss
                 of Signal during the current day as measured by
                 adslAturPerfCurr1DayTimeElapsed."
         ::= { adslAturPerfDataEntry 14 }

         adslAturPerfCurr1DayLprs  OBJECT-TYPE
             SYNTAX      AdslPerfCurrDayCount
             UNITS       "seconds"
             MAX-ACCESS  read-only
             STATUS      current
             DESCRIPTION
                 "Count of the number of seconds when there was Loss
                 of Power during the current day as measured by
                 adslAturPerfCurr1DayTimeElapsed."
         ::= { adslAturPerfDataEntry 15 }

    adslAturPerfCurr1DayESs OBJECT-TYPE
             SYNTAX      AdslPerfCurrDayCount
             UNITS       "seconds"
             MAX-ACCESS  read-only
             STATUS      current
             DESCRIPTION
                 "Count of Errored Seconds during the current day as
                 measured by adslAturPerfCurr1DayTimeElapsed.
                 The errored second parameter is a count of
                 one-second intervals containing one or more crc
                 anomalies, or one or more los or sef defects."
         ::= { adslAturPerfDataEntry 16 }

         adslAturPerfPrev1DayMoniSecs OBJECT-TYPE
             SYNTAX      INTEGER(0..86400)
             UNITS       "seconds"
             MAX-ACCESS  read-only
             STATUS      current
             DESCRIPTION
                 "The amount of time in the previous 1-day interval
                 over which the performance monitoring information
                 is actually counted. This value will be the same as
                 the interval duration except in a situation where
                 performance monitoring data could not be collected
                 for any reason."
         ::= { adslAturPerfDataEntry 17 }

         adslAturPerfPrev1DayLofs  OBJECT-TYPE
             SYNTAX      AdslPerfPrevDayCount
             UNITS       "seconds"
             MAX-ACCESS  read-only
             STATUS      current
             DESCRIPTION
                 "Count of seconds in the interval when there was
                 Loss of Framing within the most recent previous
                 1-day period."
         ::= { adslAturPerfDataEntry 18 }

         adslAturPerfPrev1DayLoss  OBJECT-TYPE
             SYNTAX      AdslPerfPrevDayCount
             UNITS       "seconds"
             MAX-ACCESS  read-only
             STATUS      current
             DESCRIPTION
                 "Count of seconds in the interval when there was
                 Loss of Signal within the most recent previous
                 1-day period."
         ::= { adslAturPerfDataEntry 19 }

         adslAturPerfPrev1DayLprs  OBJECT-TYPE
             SYNTAX      AdslPerfPrevDayCount
             UNITS       "seconds"
             MAX-ACCESS  read-only
             STATUS      current
             DESCRIPTION
                 "Count of seconds in the interval when there was
                 Loss of Power within the most recent previous
                 1-day period."
         ::= { adslAturPerfDataEntry 20 }

         adslAturPerfPrev1DayESs OBJECT-TYPE
             SYNTAX      AdslPerfPrevDayCount
             UNITS       "seconds"
             MAX-ACCESS  read-only
             STATUS      current
             DESCRIPTION
                 "Count of Errored Seconds within the most recent
                 previous 1-day period. The errored second parameter is
                 a count of one-second intervals containing one or more
                 crc anomalies, or one or more los or sef defects."
         ::= { adslAturPerfDataEntry 21 }

         adslAtucIntervalTable   OBJECT-TYPE
             SYNTAX          SEQUENCE OF AdslAtucIntervalEntry
             MAX-ACCESS      not-accessible
             STATUS          current
             DESCRIPTION
                 "This table provides one row for each ATUC
                 performance data collection interval.
                 ADSL physical interfaces are
                 those ifEntries where ifType is equal to adsl(94)."
         ::= { adslMibObjects 8 }

         adslAtucIntervalEntry   OBJECT-TYPE
             SYNTAX          AdslAtucIntervalEntry
             MAX-ACCESS      not-accessible
             STATUS          current
             DESCRIPTION     "An entry in the adslAtucIntervalTable."
             INDEX           { ifIndex, adslAtucIntervalNumber }
         ::= { adslAtucIntervalTable 1 }

         AdslAtucIntervalEntry ::=
             SEQUENCE {
             adslAtucIntervalNumber          INTEGER,
             adslAtucIntervalLofs            PerfIntervalCount,
             adslAtucIntervalLoss            PerfIntervalCount,
             adslAtucIntervalLols            PerfIntervalCount,
             adslAtucIntervalLprs            PerfIntervalCount,
             adslAtucIntervalESs             PerfIntervalCount,
             adslAtucIntervalInits           PerfIntervalCount,
             adslAtucIntervalValidData       TruthValue
             }

         adslAtucIntervalNumber OBJECT-TYPE
             SYNTAX      INTEGER(1..96)
             MAX-ACCESS  not-accessible
             STATUS      current
             DESCRIPTION
                 "Performance Data Interval number 1 is the
                 the most recent previous interval; interval
                 96 is 24 hours ago.  Intervals 2..96 are
                 optional."
         ::= { adslAtucIntervalEntry 1 }

         adslAtucIntervalLofs OBJECT-TYPE
             SYNTAX      PerfIntervalCount
             UNITS       "seconds"
             MAX-ACCESS  read-only
             STATUS      current
             DESCRIPTION
                 "Count of seconds in the interval when there was Loss
                 of Framing."
         ::= { adslAtucIntervalEntry 2 }

         adslAtucIntervalLoss  OBJECT-TYPE
             SYNTAX      PerfIntervalCount
             UNITS       "seconds"
             MAX-ACCESS  read-only
             STATUS      current
             DESCRIPTION
                 "Count of seconds in the interval when there was Loss
                 of Signal."
         ::= { adslAtucIntervalEntry 3 }

         adslAtucIntervalLols  OBJECT-TYPE
             SYNTAX      PerfIntervalCount
             UNITS       "seconds"
             MAX-ACCESS  read-only
             STATUS      current
             DESCRIPTION
                 "Count of seconds in the interval when there was Loss
                 of Link."
         ::= { adslAtucIntervalEntry 4 }

         adslAtucIntervalLprs  OBJECT-TYPE
             SYNTAX      PerfIntervalCount
             UNITS       "seconds"
             MAX-ACCESS  read-only
             STATUS      current
             DESCRIPTION
                 "Count of seconds in the interval when there was Loss
                 of Power."
         ::= { adslAtucIntervalEntry 5 }

         adslAtucIntervalESs OBJECT-TYPE
             SYNTAX      PerfIntervalCount
             UNITS       "seconds"
             MAX-ACCESS  read-only
             STATUS      current
             DESCRIPTION
                 "Count of Errored Seconds in the interval.
                 The errored second parameter is a count of
                 one-second intervals containing one or more crc
                 anomalies, or one or more los or sef defects."
         ::= { adslAtucIntervalEntry 6 }

         adslAtucIntervalInits  OBJECT-TYPE
             SYNTAX      PerfIntervalCount
             MAX-ACCESS  read-only
             STATUS      current
             DESCRIPTION
                 "Count of the line initialization attempts
                 during the interval. Includes both successful
                 and failed attempts."
         ::= { adslAtucIntervalEntry 7 }

         adslAtucIntervalValidData OBJECT-TYPE
             SYNTAX TruthValue
             MAX-ACCESS read-only
             STATUS current
             DESCRIPTION
                 "This variable indicates if the data for this
                 interval is valid."
         ::= { adslAtucIntervalEntry 8 }

         adslAturIntervalTable   OBJECT-TYPE
             SYNTAX          SEQUENCE OF AdslAturIntervalEntry
             MAX-ACCESS      not-accessible
             STATUS          current
             DESCRIPTION
                 "This table provides one row for each ATUR
                 performance data collection interval.
                 ADSL physical interfaces are those
                 ifEntries where ifType is equal to adsl(94)."
         ::= { adslMibObjects 9 }

         adslAturIntervalEntry   OBJECT-TYPE
             SYNTAX          AdslAturIntervalEntry
             MAX-ACCESS      not-accessible
             STATUS          current
             DESCRIPTION     "An entry in the adslAturIntervalTable."
             INDEX           { ifIndex, adslAturIntervalNumber }
         ::= { adslAturIntervalTable 1 }

         AdslAturIntervalEntry ::=
             SEQUENCE {
             adslAturIntervalNumber          INTEGER,
             adslAturIntervalLofs            PerfIntervalCount,
             adslAturIntervalLoss            PerfIntervalCount,
             adslAturIntervalLprs            PerfIntervalCount,
             adslAturIntervalESs             PerfIntervalCount,
             adslAturIntervalValidData       TruthValue
             }

         adslAturIntervalNumber OBJECT-TYPE
             SYNTAX      INTEGER(1..96)
             MAX-ACCESS  not-accessible
             STATUS      current
             DESCRIPTION
                 "Performance Data Interval number 1 is the
                 the most recent previous interval; interval
                 96 is 24 hours ago.  Intervals 2..96 are
                 optional."
         ::= { adslAturIntervalEntry 1 }

         adslAturIntervalLofs OBJECT-TYPE
             SYNTAX      PerfIntervalCount
             UNITS       "seconds"
             MAX-ACCESS  read-only
             STATUS      current
             DESCRIPTION
                 "Count of seconds in the interval when there was
                 Loss of Framing."
         ::= { adslAturIntervalEntry 2 }

         adslAturIntervalLoss  OBJECT-TYPE
             SYNTAX      PerfIntervalCount
             UNITS       "seconds"
             MAX-ACCESS  read-only
             STATUS      current
             DESCRIPTION
                 "Count of seconds in the interval when there was
                 Loss of Signal."
         ::= { adslAturIntervalEntry 3 }

         adslAturIntervalLprs  OBJECT-TYPE
             SYNTAX      PerfIntervalCount
             UNITS       "seconds"
             MAX-ACCESS  read-only
             STATUS      current
             DESCRIPTION
                 "Count of seconds in the interval when there was
                 Loss of Power."
         ::= { adslAturIntervalEntry 4 }

         adslAturIntervalESs OBJECT-TYPE
             SYNTAX      PerfIntervalCount
             UNITS       "seconds"
             MAX-ACCESS  read-only
             STATUS      current
             DESCRIPTION
                 "Count of Errored Seconds in the interval.
                 The errored second parameter is a count of
                 one-second intervals containing one or more crc
                 anomalies, or one or more los or sef defects."
         ::= { adslAturIntervalEntry 5 }

         adslAturIntervalValidData OBJECT-TYPE
             SYNTAX TruthValue
             MAX-ACCESS read-only
             STATUS current
             DESCRIPTION
                 "This variable indicates if the data for this
                 interval is valid."
         ::= { adslAturIntervalEntry 6 }

         adslAtucChanPerfDataTable       OBJECT-TYPE
             SYNTAX          SEQUENCE OF AdslAtucChanPerfDataEntry
             MAX-ACCESS      not-accessible
             STATUS          current
             DESCRIPTION
                 "This table provides one row for each ATUC channel.
                 ADSL channel interfaces are those ifEntries
                 where ifType is equal to adslInterleave(124)
                 or adslFast(125)."
         ::= { adslMibObjects 10 }

         adslAtucChanPerfDataEntry       OBJECT-TYPE

             SYNTAX          AdslAtucChanPerfDataEntry
             MAX-ACCESS      not-accessible
             STATUS          current
             DESCRIPTION     "An entry in adslAtucChanPerfDataTable."
             INDEX           { ifIndex }
         ::= { adslAtucChanPerfDataTable 1 }

         AdslAtucChanPerfDataEntry ::=
          SEQUENCE {
          adslAtucChanReceivedBlks                 Counter32,
          adslAtucChanTransmittedBlks              Counter32,
          adslAtucChanCorrectedBlks                Counter32,
          adslAtucChanUncorrectBlks                Counter32,
          adslAtucChanPerfValidIntervals           INTEGER,
          adslAtucChanPerfInvalidIntervals         INTEGER,
          adslAtucChanPerfCurr15MinTimeElapsed     AdslPerfTimeElapsed,
          adslAtucChanPerfCurr15MinReceivedBlks    PerfCurrentCount,
          adslAtucChanPerfCurr15MinTransmittedBlks PerfCurrentCount,
          adslAtucChanPerfCurr15MinCorrectedBlks   PerfCurrentCount,
          adslAtucChanPerfCurr15MinUncorrectBlks   PerfCurrentCount,
          adslAtucChanPerfCurr1DayTimeElapsed      AdslPerfTimeElapsed,
          adslAtucChanPerfCurr1DayReceivedBlks     AdslPerfCurrDayCount,
          adslAtucChanPerfCurr1DayTransmittedBlks  AdslPerfCurrDayCount,
          adslAtucChanPerfCurr1DayCorrectedBlks    AdslPerfCurrDayCount,
          adslAtucChanPerfCurr1DayUncorrectBlks    AdslPerfCurrDayCount,
          adslAtucChanPerfPrev1DayMoniSecs         INTEGER,
          adslAtucChanPerfPrev1DayReceivedBlks     AdslPerfPrevDayCount,
          adslAtucChanPerfPrev1DayTransmittedBlks  AdslPerfPrevDayCount,
          adslAtucChanPerfPrev1DayCorrectedBlks    AdslPerfPrevDayCount,
          adslAtucChanPerfPrev1DayUncorrectBlks    AdslPerfPrevDayCount
         }
         -- performance group

         --
         -- Note: block is intended to be the length of the channel
         --       data-block on which the CRC operates. See
         --       adslAtucChanCrcBlockLength for more information.
         --
         adslAtucChanReceivedBlks OBJECT-TYPE
             SYNTAX      Counter32
             MAX-ACCESS  read-only
             STATUS      current
             DESCRIPTION
                 "Count of all encoded blocks received on this channel
                 since agent reset."
         ::= { adslAtucChanPerfDataEntry 1 }

         adslAtucChanTransmittedBlks  OBJECT-TYPE
             SYNTAX      Counter32
             MAX-ACCESS  read-only
             STATUS      current
             DESCRIPTION
                 "Count of all encoded blocks transmitted on this
                 channel since agent reset."
         ::= { adslAtucChanPerfDataEntry 2 }

         adslAtucChanCorrectedBlks  OBJECT-TYPE
             SYNTAX      Counter32
             MAX-ACCESS  read-only
             STATUS      current
             DESCRIPTION
                 "Count of all blocks received with errors that were
                 corrected since agent reset.  These blocks are passed
                 on as good data."
         ::= { adslAtucChanPerfDataEntry 3 }

         adslAtucChanUncorrectBlks  OBJECT-TYPE
             SYNTAX      Counter32
             MAX-ACCESS  read-only
             STATUS      current
             DESCRIPTION
                 "Count of all blocks received with uncorrectable
                 errors since agent reset."
         ::= { adslAtucChanPerfDataEntry 4 }

         -- general 15 min interval information
         --
         adslAtucChanPerfValidIntervals OBJECT-TYPE
             SYNTAX      INTEGER(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adslAtucChanPerfDataEntry 5 }

         adslAtucChanPerfInvalidIntervals OBJECT-TYPE
             SYNTAX      INTEGER(0..96)
             MAX-ACCESS  read-only
             STATUS      current
             DESCRIPTION
                 "The number of intervals in the range from
                 0 to the value of adslAtucChanPerfValidIntervals
                 for which no data is available. This object
                 will typically be zero except in cases where
                 the data for some intervals are not available
                 (e.g., in proxy situations)."
         ::= { adslAtucChanPerfDataEntry 6 }

         -- 15 min current performance group
         --
         adslAtucChanPerfCurr15MinTimeElapsed OBJECT-TYPE
             SYNTAX      AdslPerfTimeElapsed(0..899)
             UNITS       "seconds"
             MAX-ACCESS  read-only
             STATUS      current
             DESCRIPTION
                 "Total elapsed seconds in this interval."
         ::= { adslAtucChanPerfDataEntry 7 }

         adslAtucChanPerfCurr15MinReceivedBlks OBJECT-TYPE
             SYNTAX      PerfCurrentCount
             MAX-ACCESS  read-only
             STATUS      current
             DESCRIPTION
                 "Count of all encoded blocks received on this channel
                 within the current 15 minute interval."
         ::= { adslAtucChanPerfDataEntry 8 }

         adslAtucChanPerfCurr15MinTransmittedBlks OBJECT-TYPE
             SYNTAX      PerfCurrentCount
             MAX-ACCESS  read-only
             STATUS      current
             DESCRIPTION
                 "Count of all encoded blocks transmitted on this
                 channel within the current 15 minute interval."
         ::= { adslAtucChanPerfDataEntry 9 }

         adslAtucChanPerfCurr15MinCorrectedBlks  OBJECT-TYPE
             SYNTAX      PerfCurrentCount
             MAX-ACCESS  read-only
             STATUS      current
             DESCRIPTION
                 "Count of all blocks received with errors that were
                 corrected on this channel within the current 15 minute
                 interval."
         ::= { adslAtucChanPerfDataEntry 10 }

         adslAtucChanPerfCurr15MinUncorrectBlks  OBJECT-TYPE
             SYNTAX      PerfCurrentCount
             MAX-ACCESS  read-only
             STATUS      current
             DESCRIPTION
                 "Count of all blocks received with uncorrectable
                 errors on this channel within the current 15 minute
                 interval."
         ::= { adslAtucChanPerfDataEntry 11 }

         -- 1-day current and previous performance group
         --
         adslAtucChanPerfCurr1DayTimeElapsed OBJECT-TYPE
             SYNTAX      AdslPerfTimeElapsed(0..86399)
             UNITS       "seconds"
             MAX-ACCESS  read-only
             STATUS      current
             DESCRIPTION
                 "Number of seconds that have elapsed since the
                 beginning of the current 1-day interval."
         ::= { adslAtucChanPerfDataEntry 12 }

         adslAtucChanPerfCurr1DayReceivedBlks  OBJECT-TYPE
             SYNTAX      AdslPerfCurrDayCount
             MAX-ACCESS  read-only
             STATUS      current
             DESCRIPTION
                 "Count of all encoded blocks received on this
                 channel during the current day as measured by
                 adslAtucChanPerfCurr1DayTimeElapsed."
         ::= { adslAtucChanPerfDataEntry 13 }

         adslAtucChanPerfCurr1DayTransmittedBlks  OBJECT-TYPE
             SYNTAX      AdslPerfCurrDayCount
             MAX-ACCESS  read-only
             STATUS      current
             DESCRIPTION
                 "Count of all encoded blocks transmitted on this
                 channel during the current day as measured by
                 adslAtucChanPerfCurr1DayTimeElapsed."
         ::= { adslAtucChanPerfDataEntry 14 }

         adslAtucChanPerfCurr1DayCorrectedBlks  OBJECT-TYPE
             SYNTAX      AdslPerfCurrDayCount
             MAX-ACCESS  read-only
             STATUS      current
             DESCRIPTION
                 "Count of all blocks received with errors that were
                 corrected on this channel during the current day as
                 measured by adslAtucChanPerfCurr1DayTimeElapsed."
         ::= { adslAtucChanPerfDataEntry 15 }

         adslAtucChanPerfCurr1DayUncorrectBlks  OBJECT-TYPE
             SYNTAX      AdslPerfCurrDayCount
             MAX-ACCESS  read-only
             STATUS      current
             DESCRIPTION
                 "Count of all blocks received with uncorrectable
                 errors on this channel during the current day as
                 measured by adslAtucChanPerfCurr1DayTimeElapsed."
         ::= { adslAtucChanPerfDataEntry 16 }

         adslAtucChanPerfPrev1DayMoniSecs OBJECT-TYPE
             SYNTAX      INTEGER(0..86400)
             UNITS       "seconds"
             MAX-ACCESS  read-only
             STATUS      current
             DESCRIPTION
                 "The amount of time in the previous 1-day interval
                 over which the performance monitoring information
                 is actually counted. This value will be the same as
                 the interval duration except in a situation where
                 performance monitoring data could not be collected
                 for any reason."
         ::= { adslAtucChanPerfDataEntry 17 }

         adslAtucChanPerfPrev1DayReceivedBlks  OBJECT-TYPE
             SYNTAX      AdslPerfPrevDayCount
             MAX-ACCESS  read-only
             STATUS      current
             DESCRIPTION
                 "Count of all encoded blocks received on this
                 channel within the most recent previous 1-day
                 period."
         ::= { adslAtucChanPerfDataEntry 18 }

         adslAtucChanPerfPrev1DayTransmittedBlks  OBJECT-TYPE
             SYNTAX      AdslPerfPrevDayCount
             MAX-ACCESS  read-only
             STATUS      current
             DESCRIPTION
                 "Count of all encoded blocks transmitted on this
                 channel within the most recent previous 1-day
                 period."
         ::= { adslAtucChanPerfDataEntry 19 }

         adslAtucChanPerfPrev1DayCorrectedBlks  OBJECT-TYPE
             SYNTAX      AdslPerfPrevDayCount
             MAX-ACCESS  read-only
             STATUS      current
             DESCRIPTION
                 "Count of all blocks received with errors that were
                 corrected on this channel within the most recent
                 previous 1-day period."
         ::= { adslAtucChanPerfDataEntry 20 }

         adslAtucChanPerfPrev1DayUncorrectBlks  OBJECT-TYPE
             SYNTAX      AdslPerfPrevDayCount
             MAX-ACCESS  read-only
             STATUS      current
             DESCRIPTION
                 "Count of all blocks received with uncorrectable
                 errors on this channel within the most recent previous
                 1-day period."
         ::= { adslAtucChanPerfDataEntry 21 }

         adslAturChanPerfDataTable       OBJECT-TYPE
             SYNTAX          SEQUENCE OF AdslAturChanPerfDataEntry
             MAX-ACCESS      not-accessible
             STATUS          current
             DESCRIPTION
                 "This table provides one row for each ATUR channel.
                 ADSL channel interfaces are those ifEntries
                 where ifType is equal to adslInterleave(124)
                 or adslFast(125)."
         ::= { adslMibObjects 11 }

         adslAturChanPerfDataEntry       OBJECT-TYPE
             SYNTAX          AdslAturChanPerfDataEntry
             MAX-ACCESS      not-accessible
             STATUS          current
             DESCRIPTION     "An entry in adslAturChanPerfDataTable."
             INDEX           { ifIndex }
         ::= { adslAturChanPerfDataTable 1 }

         AdslAturChanPerfDataEntry ::=
          SEQUENCE {
          adslAturChanReceivedBlks                 Counter32,
          adslAturChanTransmittedBlks              Counter32,
          adslAturChanCorrectedBlks                Counter32,
          adslAturChanUncorrectBlks                Counter32,
          adslAturChanPerfValidIntervals           INTEGER,
          adslAturChanPerfInvalidIntervals         INTEGER,
          adslAturChanPerfCurr15MinTimeElapsed     AdslPerfTimeElapsed,
          adslAturChanPerfCurr15MinReceivedBlks    PerfCurrentCount,
          adslAturChanPerfCurr15MinTransmittedBlks PerfCurrentCount,
          adslAturChanPerfCurr15MinCorrectedBlks   PerfCurrentCount,
          adslAturChanPerfCurr15MinUncorrectBlks   PerfCurrentCount,
          adslAturChanPerfCurr1DayTimeElapsed      AdslPerfTimeElapsed,
          adslAturChanPerfCurr1DayReceivedBlks     AdslPerfCurrDayCount,
          adslAturChanPerfCurr1DayTransmittedBlks  AdslPerfCurrDayCount,
          adslAturChanPerfCurr1DayCorrectedBlks    AdslPerfCurrDayCount,
          adslAturChanPerfCurr1DayUncorrectBlks    AdslPerfCurrDayCount,
          adslAturChanPerfPrev1DayMoniSecs         INTEGER,
          adslAturChanPerfPrev1DayReceivedBlks     AdslPerfPrevDayCount,
          adslAturChanPerfPrev1DayTransmittedBlks  AdslPerfPrevDayCount,
          adslAturChanPerfPrev1DayCorrectedBlks    AdslPerfPrevDayCount,
          adslAturChanPerfPrev1DayUncorrectBlks    AdslPerfPrevDayCount
          }
         -- performance group
         --
         -- Note: block is intended to be the length of the channel
         --       data-block on which the CRC operates. See
         --       adslAturChanCrcBlockLength for more information.
         --
         adslAturChanReceivedBlks OBJECT-TYPE
             SYNTAX      Counter32
             MAX-ACCESS  read-only
             STATUS      current
             DESCRIPTION
                 "Count of all encoded blocks received on this channel
                 since agent reset."
         ::= { adslAturChanPerfDataEntry 1 }

         adslAturChanTransmittedBlks  OBJECT-TYPE
             SYNTAX      Counter32
             MAX-ACCESS  read-only
             STATUS      current
             DESCRIPTION
                 "Count of all encoded blocks transmitted on this
                 channel since agent reset."
         ::= { adslAturChanPerfDataEntry 2 }

         adslAturChanCorrectedBlks  OBJECT-TYPE
             SYNTAX      Counter32
             MAX-ACCESS  read-only
             STATUS      current
             DESCRIPTION
                 "Count of all blocks received with errors that were
                 corrected since agent reset.  These blocks are passed
                 on as good data."
         ::= { adslAturChanPerfDataEntry 3 }

         adslAturChanUncorrectBlks  OBJECT-TYPE
             SYNTAX      Counter32
             MAX-ACCESS  read-only
             STATUS      current
             DESCRIPTION
                 "Count of all blocks received with uncorrectable
                 errors since agent reset."
         ::= { adslAturChanPerfDataEntry 4 }

         -- general 15 min interval information
         --
         adslAturChanPerfValidIntervals OBJECT-TYPE
             SYNTAX      INTEGER(0..96)
             MAX-ACCESS  read-only
             STATUS      current
             DESCRIPTION
                 "The number of previous 15-minute intervals in the
                 interval table for which data was collected.  Given
                 that <n> is the maximum # of intervals supported.
                 The value will be <n> unless the measurement was
                 (re-)started within the last (<n>*15) minutes, in which
                 case the value will be the number of complete 15
                 minute intervals for which the agent has at least
                 some data. In certain cases (e.g., in the case
                 where the agent is a proxy) it is possible that some
                 intervals are unavailable.  In this case, this
                 interval is the maximum interval number for
                 which data is available."
         ::= { adslAturChanPerfDataEntry 5 }

         adslAturChanPerfInvalidIntervals OBJECT-TYPE
             SYNTAX      INTEGER(0..96)
             MAX-ACCESS  read-only
             STATUS      current
             DESCRIPTION
                 "The number of intervals in the range from
                 0 to the value of adslAturChanPerfValidIntervals
                 for which no data is available. This object
                 will typically be zero except in cases where
                 the data for some intervals are not available
                 (e.g., in proxy situations)."
         ::= { adslAturChanPerfDataEntry 6 }

         -- 15 min current performance group
         --
         adslAturChanPerfCurr15MinTimeElapsed OBJECT-TYPE
             SYNTAX      AdslPerfTimeElapsed(0..899)
             UNITS       "seconds"
             MAX-ACCESS  read-only
             STATUS      current
             DESCRIPTION
                 "Total elapsed seconds in this interval.
                 A full interval is 900 seconds."
         ::= { adslAturChanPerfDataEntry 7 }

         adslAturChanPerfCurr15MinReceivedBlks OBJECT-TYPE
             SYNTAX      PerfCurrentCount
             MAX-ACCESS  read-only
             STATUS      current
             DESCRIPTION
                 "Count of all encoded blocks received on this
                 channel within the current 15 minute interval."
         ::= { adslAturChanPerfDataEntry 8 }

         adslAturChanPerfCurr15MinTransmittedBlks OBJECT-TYPE
             SYNTAX      PerfCurrentCount
             MAX-ACCESS  read-only
             STATUS      current
             DESCRIPTION
                 "Count of all encoded blocks transmitted on this
                 channel within the current 15 minute interval."
         ::= { adslAturChanPerfDataEntry 9 }

         adslAturChanPerfCurr15MinCorrectedBlks  OBJECT-TYPE
             SYNTAX      PerfCurrentCount
             MAX-ACCESS  read-only
             STATUS      current
             DESCRIPTION
                 "Count of all blocks received with errors that were
                 corrected on this channel within the current 15 minute
                 interval."
         ::= { adslAturChanPerfDataEntry 10 }

         adslAturChanPerfCurr15MinUncorrectBlks  OBJECT-TYPE
             SYNTAX      PerfCurrentCount
             MAX-ACCESS  read-only
             STATUS      current
             DESCRIPTION
                 "Count of all blocks received with uncorrectable
                 errors on this channel within the current 15 minute
                 interval."
         ::= { adslAturChanPerfDataEntry 11 }

         -- 1-day current and previous performance group
         --
         adslAturChanPerfCurr1DayTimeElapsed OBJECT-TYPE
             SYNTAX      AdslPerfTimeElapsed(0..86399)
             UNITS       "seconds"
             MAX-ACCESS  read-only
             STATUS      current
             DESCRIPTION
                 "Number of seconds that have elapsed since the
                 beginning of the current 1-day interval."
         ::= { adslAturChanPerfDataEntry 12 }

         adslAturChanPerfCurr1DayReceivedBlks  OBJECT-TYPE
             SYNTAX      AdslPerfCurrDayCount
             MAX-ACCESS  read-only
             STATUS      current
             DESCRIPTION
                 "Count of all encoded blocks received on this
                 channel during the current day as measured by
                 adslAturChanPerfCurr1DayTimeElapsed."
         ::= { adslAturChanPerfDataEntry 13 }

         adslAturChanPerfCurr1DayTransmittedBlks  OBJECT-TYPE
             SYNTAX      AdslPerfCurrDayCount
             MAX-ACCESS  read-only
             STATUS      current
             DESCRIPTION
                 "Count of all encoded blocks transmitted on this
                 channel during the current day as measured by
                 adslAturChanPerfCurr1DayTimeElapsed."

         ::= { adslAturChanPerfDataEntry 14 }

         adslAturChanPerfCurr1DayCorrectedBlks  OBJECT-TYPE
             SYNTAX      AdslPerfCurrDayCount
             MAX-ACCESS  read-only
             STATUS      current
             DESCRIPTION
                 "Count of all blocks received with errors that were
                 corrected on this channel during the current day as
                 measured by adslAturChanPerfCurr1DayTimeElapsed."
         ::= { adslAturChanPerfDataEntry 15 }

         adslAturChanPerfCurr1DayUncorrectBlks  OBJECT-TYPE
             SYNTAX      AdslPerfCurrDayCount
             MAX-ACCESS  read-only
             STATUS      current
             DESCRIPTION
                 "Count of all blocks received with uncorrectable
                 errors on this channel during the current day as
                 measured by adslAturChanPerfCurr1DayTimeElapsed."
         ::= { adslAturChanPerfDataEntry 16 }

         adslAturChanPerfPrev1DayMoniSecs OBJECT-TYPE
             SYNTAX      INTEGER(0..86400)
             UNITS       "seconds"
             MAX-ACCESS  read-only
             STATUS      current
             DESCRIPTION
                 "The amount of time in the previous 1-day interval
                 over which the performance monitoring information
                 is actually counted. This value will be the same as
                 the interval duration except in a situation where
                 performance monitoring data could not be collected
                 for any reason."
         ::= { adslAturChanPerfDataEntry 17 }

         adslAturChanPerfPrev1DayReceivedBlks  OBJECT-TYPE
             SYNTAX      AdslPerfPrevDayCount
             MAX-ACCESS  read-only
             STATUS      current
             DESCRIPTION
                 "Count of all encoded blocks received on this
                 channel within the most recent previous 1-day
                 period."
         ::= { adslAturChanPerfDataEntry 18 }

         adslAturChanPerfPrev1DayTransmittedBlks  OBJECT-TYPE
             SYNTAX      AdslPerfPrevDayCount
             MAX-ACCESS  read-only
             STATUS      current
             DESCRIPTION
                 "Count of all encoded blocks transmitted on this
                 channel within the most recent previous 1-day
                 period."
         ::= { adslAturChanPerfDataEntry 19 }

         adslAturChanPerfPrev1DayCorrectedBlks  OBJECT-TYPE
             SYNTAX      AdslPerfPrevDayCount
             MAX-ACCESS  read-only
             STATUS      current
             DESCRIPTION
                 "Count of all blocks received with errors that were
                 corrected on this channel within the most recent
                 previous 1-day period."
         ::= { adslAturChanPerfDataEntry 20 }

         adslAturChanPerfPrev1DayUncorrectBlks  OBJECT-TYPE
             SYNTAX      AdslPerfPrevDayCount
             MAX-ACCESS  read-only
             STATUS      current
             DESCRIPTION
                 "Count of all blocks received with uncorrectable
                 errors on this channel within the most recent previous
                 1-day period."
         ::= { adslAturChanPerfDataEntry 21 }

         adslAtucChanIntervalTable   OBJECT-TYPE
             SYNTAX          SEQUENCE OF AdslAtucChanIntervalEntry
             MAX-ACCESS      not-accessible
             STATUS          current
             DESCRIPTION
                 "This table provides one row for each ATUC channel's
                 performance data collection interval.
                 ADSL channel interfaces are those ifEntries
                 where ifType is equal to adslInterleave(124)
                 or adslFast(125)."
         ::= { adslMibObjects 12 }

         adslAtucChanIntervalEntry   OBJECT-TYPE
             SYNTAX          AdslAtucChanIntervalEntry
             MAX-ACCESS      not-accessible
             STATUS          current
             DESCRIPTION     "An entry in the adslAtucIntervalTable."
             INDEX           { ifIndex, adslAtucChanIntervalNumber }
         ::= { adslAtucChanIntervalTable 1 }

         AdslAtucChanIntervalEntry ::=
             SEQUENCE {
             adslAtucChanIntervalNumber          INTEGER,
             adslAtucChanIntervalReceivedBlks    PerfIntervalCount,
             adslAtucChanIntervalTransmittedBlks PerfIntervalCount,
             adslAtucChanIntervalCorrectedBlks   PerfIntervalCount,
             adslAtucChanIntervalUncorrectBlks   PerfIntervalCount,
             adslAtucChanIntervalValidData       TruthValue
             }
         adslAtucChanIntervalNumber OBJECT-TYPE
             SYNTAX      INTEGER(1..96)
             MAX-ACCESS  not-accessible
             STATUS      current
             DESCRIPTION
                 "Performance Data Interval number 1 is the
                 the most recent previous interval; interval
                 96 is 24 hours ago.  Intervals 2..96 are
                 optional."
         ::= { adslAtucChanIntervalEntry 1 }

         adslAtucChanIntervalReceivedBlks OBJECT-TYPE
             SYNTAX      PerfIntervalCount
             MAX-ACCESS  read-only
             STATUS      current
             DESCRIPTION
                 "Count of all encoded blocks received on this channel
                 during this interval."
         ::= { adslAtucChanIntervalEntry 2 }

         adslAtucChanIntervalTransmittedBlks  OBJECT-TYPE
             SYNTAX      PerfIntervalCount
             MAX-ACCESS  read-only
             STATUS      current
             DESCRIPTION
                 "Count of all encoded blocks transmitted on this
                 channel during this interval."
         ::= { adslAtucChanIntervalEntry 3 }

         adslAtucChanIntervalCorrectedBlks  OBJECT-TYPE
             SYNTAX      PerfIntervalCount
             MAX-ACCESS  read-only
             STATUS      current
             DESCRIPTION
                 "Count of all blocks received with errors that were
                 corrected on this channel during this interval."
         ::= { adslAtucChanIntervalEntry 4 }

         adslAtucChanIntervalUncorrectBlks  OBJECT-TYPE
             SYNTAX      PerfIntervalCount
             MAX-ACCESS  read-only
             STATUS      current
             DESCRIPTION
                 "Count of all blocks received with uncorrectable
                 errors on this channel during this interval."
         ::= { adslAtucChanIntervalEntry 5 }

         adslAtucChanIntervalValidData OBJECT-TYPE
             SYNTAX TruthValue
             MAX-ACCESS read-only
             STATUS current
             DESCRIPTION
                 "This variable indicates if the data for this
                 interval is valid."
         ::= { adslAtucChanIntervalEntry 6 }

         adslAturChanIntervalTable   OBJECT-TYPE
             SYNTAX          SEQUENCE OF AdslAturChanIntervalEntry
             MAX-ACCESS      not-accessible
             STATUS          current
             DESCRIPTION
                 "This table provides one row for each ATUR channel's
                 performance data collection interval.
                 ADSL channel interfaces are those ifEntries
                 where ifType is equal to adslInterleave(124)
                 or adslFast(125)."
         ::= { adslMibObjects 13 }

         adslAturChanIntervalEntry   OBJECT-TYPE
             SYNTAX          AdslAturChanIntervalEntry
             MAX-ACCESS      not-accessible
             STATUS          current
             DESCRIPTION     "An entry in the adslAturIntervalTable."
             INDEX           { ifIndex, adslAturChanIntervalNumber }
         ::= { adslAturChanIntervalTable 1 }

         AdslAturChanIntervalEntry ::=
             SEQUENCE {
             adslAturChanIntervalNumber               INTEGER,
             adslAturChanIntervalReceivedBlks         PerfIntervalCount,
             adslAturChanIntervalTransmittedBlks      PerfIntervalCount,
             adslAturChanIntervalCorrectedBlks        PerfIntervalCount,
             adslAturChanIntervalUncorrectBlks        PerfIntervalCount,
             adslAturChanIntervalValidData            TruthValue
             }
         adslAturChanIntervalNumber OBJECT-TYPE
             SYNTAX      INTEGER(1..96)
             MAX-ACCESS  not-accessible
             STATUS      current
             DESCRIPTION
                 "Performance Data Interval number 1 is the
                 the most recent previous interval; interval
                 96 is 24 hours ago.  Intervals 2..96 are
                 optional."
         ::= { adslAturChanIntervalEntry 1 }

         adslAturChanIntervalReceivedBlks OBJECT-TYPE
             SYNTAX      PerfIntervalCount
             MAX-ACCESS  read-only
             STATUS      current
             DESCRIPTION
                 "Count of all encoded blocks received on this channel
                 during this interval."
         ::= { adslAturChanIntervalEntry 2 }

         adslAturChanIntervalTransmittedBlks  OBJECT-TYPE
             SYNTAX      PerfIntervalCount
             MAX-ACCESS  read-only
             STATUS      current
             DESCRIPTION
                 "Count of all encoded blocks transmitted on this
                 channel during this interval."
         ::= { adslAturChanIntervalEntry 3 }

         adslAturChanIntervalCorrectedBlks  OBJECT-TYPE
             SYNTAX      PerfIntervalCount
             MAX-ACCESS  read-only
             STATUS      current
             DESCRIPTION
                 "Count of all blocks received with errors that were
                 corrected on this channel during this interval."
         ::= { adslAturChanIntervalEntry 4 }

         adslAturChanIntervalUncorrectBlks  OBJECT-TYPE
             SYNTAX      PerfIntervalCount
             MAX-ACCESS  read-only
             STATUS      current
             DESCRIPTION
                 "Count of all blocks received with uncorrectable
                 errors on this channel during this interval."
         ::= { adslAturChanIntervalEntry 5 }

         adslAturChanIntervalValidData OBJECT-TYPE
             SYNTAX TruthValue
             MAX-ACCESS read-only
             STATUS current
             DESCRIPTION
                 "This variable indicates if the data for this
                 interval is valid."
         ::= { adslAturChanIntervalEntry 6 }

         -- Profile Group
         --

         adslLineConfProfileTable    OBJECT-TYPE
             SYNTAX          SEQUENCE OF AdslLineConfProfileEntry
             MAX-ACCESS      not-accessible
             STATUS          current
             DESCRIPTION
                 "This table contains information on the ADSL line
                 configuration.  One entry in this table reflects a
                 profile defined by a manager which can be used to
                 configure the ADSL line."
         ::= { adslMibObjects 14}

         adslLineConfProfileEntry    OBJECT-TYPE
             SYNTAX          AdslLineConfProfileEntry
             MAX-ACCESS      not-accessible
             STATUS          current
             DESCRIPTION
                 "Each entry consists of a list of parameters that
                 represents the configuration of an ADSL modem.

                 When `dynamic' profiles are implemented, a default
                 profile will always exist.  This profile's name will
                 be set to `DEFVAL' and its parameters will be set
                 to vendor specific values, unless otherwise specified
                 in this document.

                 When `static' profiles are implemented, profiles
                 are automaticly created or destroyed as ADSL
                 physical lines are discovered and removed by
                 the system.  The name of the profile will be
                 equivalent to the decimal value of the line's
                 interface index.
                 "
             INDEX { IMPLIED adslLineConfProfileName}
         ::= { adslLineConfProfileTable 1}

         AdslLineConfProfileEntry ::=
             SEQUENCE {
             adslLineConfProfileName               SnmpAdminString,
             adslAtucConfRateMode                  INTEGER,
             adslAtucConfRateChanRatio             INTEGER,
             adslAtucConfTargetSnrMgn              INTEGER,
             adslAtucConfMaxSnrMgn                 INTEGER,
             adslAtucConfMinSnrMgn                 INTEGER,
--             adslAtucConfDownshiftSnrMgn           INTEGER,
--             adslAtucConfUpshiftSnrMgn             INTEGER,
--             adslAtucConfMinUpshiftTime            INTEGER,
--             adslAtucConfMinDownshiftTime          INTEGER,
             adslAtucChanConfFastMinTxRate         Unsigned32,
             adslAtucChanConfInterleaveMinTxRate   Unsigned32,
             adslAtucChanConfFastMaxTxRate         Unsigned32,
             adslAtucChanConfInterleaveMaxTxRate   Unsigned32,
             adslAtucChanConfMaxInterleaveDelay    INTEGER,
             adslAturConfRateMode                  INTEGER,
             adslAturConfRateChanRatio             INTEGER,
             adslAturConfTargetSnrMgn              INTEGER,
             adslAturConfMaxSnrMgn                 INTEGER,
             adslAturConfMinSnrMgn                 INTEGER,
--             adslAturConfDownshiftSnrMgn           INTEGER,
--             adslAturConfUpshiftSnrMgn             INTEGER,
--             adslAturConfMinUpshiftTime            INTEGER,
--             adslAturConfMinDownshiftTime          INTEGER,
             adslAturChanConfFastMinTxRate         Unsigned32,
             adslAturChanConfInterleaveMinTxRate   Unsigned32,
             adslAturChanConfFastMaxTxRate         Unsigned32,
             adslAturChanConfInterleaveMaxTxRate   Unsigned32,
             adslAturChanConfMaxInterleaveDelay    INTEGER,
             adslLineConfProfileRowStatus          RowStatus
         }

         adslLineConfProfileName    OBJECT-TYPE
                 SYNTAX          SnmpAdminString (SIZE (1..32))
                 MAX-ACCESS      not-accessible
                 STATUS          current
                 DESCRIPTION
                 "This object is used by the line configuration table
                 in order to identify a row of this table.

                 When `dynamic' profiles are implemented, the profile
                 name is user specified.  Also, the system will always
                 provide a default profile whose name is `DEFVAL'.

                 When `static' profiles are implemented, there is an
                 one-to-one relationship between each line and its
                 profile.  In which case, the profile name will
                 need to algorithmicly represent the Line's ifIndex.
                 Therefore, the profile's name is a decimalized string
                 of the ifIndex that is fixed-length (i.e., 10) with
                 leading zero(s).  For example, the profile name for
                 ifIndex which equals '15' will be '0000000015'."
         ::= { adslLineConfProfileEntry 1 }

         adslAtucConfRateMode OBJECT-TYPE
             SYNTAX      INTEGER {
                 fixed (1),              -- no rate adaptation
                 adaptAtStartup (2),     -- perform rate adaptation
                                         -- only at initialization
                 adaptAtRuntime (3)      -- perform rate adaptation at
                                         -- any time
             }
             MAX-ACCESS  read-create
             STATUS      current
             DESCRIPTION
                 "Defines what form of transmit rate adaptation is
                 configured on this modem.  See ADSL Forum TR-005 [3]
                 for more information."
         ::= { adslLineConfProfileEntry 2 }

         adslAtucConfRateChanRatio OBJECT-TYPE
             SYNTAX      INTEGER(0..100)
             UNITS        "%"
             MAX-ACCESS  read-create
             STATUS      current
             DESCRIPTION
                 "Configured allocation ratio of excess transmit
                 bandwidth between fast and interleaved channels.  Only
                 applies when two channel mode and RADSL are supported.
                 Distribute bandwidth on each channel in excess of the
                 corresponding ChanConfMinTxRate so that:
                 adslAtucConfRateChanRatio =

                         [Fast / (Fast + Interleaved)] * 100

                 In other words this value is the fast channel
                 percentage."
         ::= { adslLineConfProfileEntry 3 }

       adslAtucConfTargetSnrMgn OBJECT-TYPE
             SYNTAX      INTEGER (0..310)
             UNITS       "tenth dB"
             MAX-ACCESS  read-create
             STATUS      current
             DESCRIPTION
                 "Configured Target Signal/Noise Margin.
                 This is the Noise Margin the modem must achieve
                 with a BER of 10-7 or better to successfully complete
                 initialization."
         ::= { adslLineConfProfileEntry 4 }

       adslAtucConfMaxSnrMgn OBJECT-TYPE
             SYNTAX      INTEGER (0..310)
             UNITS       "tenth dB"
             MAX-ACCESS  read-create
             STATUS      current
             DESCRIPTION
                 "Configured Maximum acceptable Signal/Noise Margin.
                 If the Noise Margin is above this the modem should
                 attempt to reduce its power output to optimize its
                 operation."
         ::= { adslLineConfProfileEntry 5 }

         adslAtucConfMinSnrMgn  OBJECT-TYPE
             SYNTAX      INTEGER (0..310)
             UNITS       "tenth dB"
             MAX-ACCESS  read-create
             STATUS      current
             DESCRIPTION
                 "Configured Minimum acceptable Signal/Noise Margin.
                 If the noise margin falls below this level, the modem
                 should attempt to increase its power output.  If that
                 is not possible the modem will attempt to
                 re-initialize or shut down."
         ::= { adslLineConfProfileEntry 6 }

--         adslAtucConfDownshiftSnrMgn  OBJECT-TYPE
--             SYNTAX      INTEGER (0..310)
--             UNITS       "tenth dB"
--             MAX-ACCESS  read-create
--             STATUS      current
--             DESCRIPTION
--                 "Configured Signal/Noise Margin for rate downshift.
--                If the noise margin falls below this level, the modem
--                 should attempt to decrease its transmit rate.  In
--               the case that RADSL mode is not present,
--                 the value will be `0'."
--         ::= { adslLineConfProfileEntry 7 }

--         adslAtucConfUpshiftSnrMgn  OBJECT-TYPE
--             SYNTAX      INTEGER (0..310)
--            UNITS       "tenth dB"
--             MAX-ACCESS  read-create
--             STATUS      current
--             DESCRIPTION
--                 "Configured Signal/Noise Margin for rate upshift.
--                If the noise margin rises above this level, the modem
--                 should attempt to increase its transmit rate.    In
--                 the case that RADSL is not present, the value will
--                 be `0'."
--         ::= { adslLineConfProfileEntry 8 }

--         adslAtucConfMinUpshiftTime OBJECT-TYPE
--             SYNTAX      INTEGER(0..16383)
--             UNITS       "seconds"
--             MAX-ACCESS  read-create
--             STATUS      current
--             DESCRIPTION
--                 "Minimum time that the current margin is above
--                 UpshiftSnrMgn before an upshift occurs.
--                 In the case that RADSL is not present, the value will
--                 be `0'."
--         ::= { adslLineConfProfileEntry 9 }
--        adslAtucConfMinDownshiftTime OBJECT-TYPE
--             SYNTAX      INTEGER(0..16383)
--             UNITS       "seconds"
--             MAX-ACCESS  read-create
--             STATUS      current
--             DESCRIPTION
--                 "Minimum time that the current margin is below
--                 DownshiftSnrMgn before a downshift occurs.
--                 In the case that RADSL mode is not present,
--                 the value will be `0'."
--        ::= { adslLineConfProfileEntry 10 }

         adslAtucChanConfFastMinTxRate  OBJECT-TYPE
             SYNTAX      Unsigned32
             UNITS       "bps"
             MAX-ACCESS  read-create
             STATUS      current
             DESCRIPTION
                 "Configured Minimum Transmit rate for `Fast' channels,
                 in bps.  See adslAtucConfRateChanRatio for information
                 regarding RADSL mode and ATUR transmit rate for
                 ATUC receive rates."
         ::= { adslLineConfProfileEntry 11 }

         adslAtucChanConfInterleaveMinTxRate OBJECT-TYPE
             SYNTAX      Unsigned32
             UNITS       "bps"
             MAX-ACCESS  read-create
             STATUS      current
             DESCRIPTION
                 "Configured Minimum Transmit rate for `Interleave'
                 channels, in bps.  See adslAtucConfRateChanRatio for
                 information regarding RADSL mode and see
                 ATUR transmit rate for receive rates."
         ::= { adslLineConfProfileEntry 12 }

         adslAtucChanConfFastMaxTxRate  OBJECT-TYPE
             SYNTAX      Unsigned32
             UNITS       "bps"
             MAX-ACCESS  read-create
             STATUS      current
             DESCRIPTION
                 "Configured Maximum Transmit rate for `Fast' channels,
                 in bps.  See adslAtucConfRateChanRatio for information
                 regarding RADSL mode and see ATUR transmit rate for
                 ATUC receive rates."
         ::= { adslLineConfProfileEntry 13 }

         adslAtucChanConfInterleaveMaxTxRate OBJECT-TYPE
             SYNTAX      Unsigned32
             UNITS       "bps"
             MAX-ACCESS  read-create
             STATUS      current
             DESCRIPTION
                 "Configured Maximum Transmit rate for `Interleave'
                 channels, in bps.  See adslAtucConfRateChanRatio for
                 information regarding RADSL mode and ATUR transmit
                 rate for ATUC receive rates."
         ::= { adslLineConfProfileEntry 14 }

         adslAtucChanConfMaxInterleaveDelay OBJECT-TYPE
             SYNTAX      INTEGER(0..255)
             UNITS        "milli-seconds"
             MAX-ACCESS  read-create
             STATUS      current
             DESCRIPTION
                 "Configured maximum Interleave Delay for this channel.

                 Interleave delay applies only to the interleave channel
                 and defines the mapping (relative spacing) between
                 subsequent input bytes at the interleaver input and
                 their placement in the bit stream at the interleaver
                 output.  Larger numbers provide greater separation
                 between consecutive input bytes in the output bit
                 stream allowing for improved impulse noise immunity
                 at the expense of payload latency."
         ::= { adslLineConfProfileEntry 15 }

         adslAturConfRateMode OBJECT-TYPE
             SYNTAX      INTEGER {
                 fixed (1),              -- no rate adaptation
                 adaptAtStartup (2),     -- perform rate adaptation
                                         -- only at initialization
                 adaptAtRuntime (3)      -- perform rate adaptation at
                                         -- any time
             }
             MAX-ACCESS  read-create
             STATUS      current
             DESCRIPTION
                 "Defines what form of transmit rate adaptation is
                 configured on this modem.  See ADSL Forum TR-005 [3]
                 for more information."
         ::= { adslLineConfProfileEntry 16 }

         adslAturConfRateChanRatio OBJECT-TYPE
             SYNTAX      INTEGER(0..100)
             UNITS        "%"
             MAX-ACCESS  read-create
             STATUS      current
             DESCRIPTION
                 "Configured allocation ratio of excess transmit
                 bandwidth between fast and interleaved channels.  Only
                 applies when two channel mode and RADSL are supported.
                 Distribute bandwidth on each channel in excess of the
                 corresponding ChanConfMinTxRate so that:
                 adslAturConfRateChanRatio =

                         [Fast / (Fast + Interleaved)] * 100

                 In other words this value is the fast channel
                 percentage."
         ::= { adslLineConfProfileEntry 17 }

       adslAturConfTargetSnrMgn OBJECT-TYPE
             SYNTAX      INTEGER (0..310)
             UNITS       "tenth dB"
             MAX-ACCESS  read-create
             STATUS      current
             DESCRIPTION
                 "Configured Target Signal/Noise Margin.
                 This is the Noise Margin the modem must achieve
                 with a BER of 10-7 or better to successfully complete
                 initialization."
         ::= { adslLineConfProfileEntry 18 }

       adslAturConfMaxSnrMgn OBJECT-TYPE
             SYNTAX      INTEGER (0..310)
             UNITS       "tenth dB"
             MAX-ACCESS  read-create
             STATUS      current
             DESCRIPTION
                 "Configured Maximum acceptable Signal/Noise Margin.
                 If the Noise Margin is above this the modem should
                 attempt to reduce its power output to optimize its
                 operation."
         ::= { adslLineConfProfileEntry 19 }

        adslAturConfMinSnrMgn  OBJECT-TYPE
             SYNTAX      INTEGER (0..310)
             UNITS       "tenth dB"
             MAX-ACCESS  read-create
             STATUS      current
             DESCRIPTION
                 "Configured Minimum acceptable Signal/Noise Margin.
                 If the noise margin falls below this level, the modem
                 should attempt to increase its power output.  If that
                 is not possible the modem will attempt to
                 re-initialize or shut down."
         ::= { adslLineConfProfileEntry 20 }

--         adslAturConfDownshiftSnrMgn  OBJECT-TYPE
--             SYNTAX      INTEGER (0..310)
--             UNITS       "tenth dB"
--             MAX-ACCESS  read-create
--             STATUS      current
--             DESCRIPTION
--                 "Configured Signal/Noise Margin for rate downshift.
--                 If the noise margin falls below this level, the modem
--                 should attempt to decrease its transmit rate.
--                 In the case that RADSL mode is not present,
--                 the value will be `0'."
--        ::= { adslLineConfProfileEntry 21 }

--         adslAturConfUpshiftSnrMgn  OBJECT-TYPE
--             SYNTAX      INTEGER (0..310)
--             UNITS       "tenth dB"
--             MAX-ACCESS  read-create
--             STATUS      current
--             DESCRIPTION
--                 "Configured Signal/Noise Margin for rate upshift.
--                 If the noise margin rises above this level, the modem
--                 should attempt to increase its transmit rate.
--                 In the case that RADSL is not present,
--                 the value will be `0'."
--         ::= { adslLineConfProfileEntry 22 }

--         adslAturConfMinUpshiftTime OBJECT-TYPE
--             SYNTAX      INTEGER(0..16383)
--             UNITS       "seconds"
--             MAX-ACCESS  read-create
--             STATUS      current
--             DESCRIPTION
--                 "Minimum time that the current margin is above
--                 UpshiftSnrMgn before an upshift occurs.
--                 In the case that RADSL is not present, the value will
--                 be `0'."
--         ::= { adslLineConfProfileEntry 23 }

--        adslAturConfMinDownshiftTime OBJECT-TYPE
--             SYNTAX      INTEGER(0..16383)
--             UNITS       "seconds"
--             MAX-ACCESS  read-create
--             STATUS      current
--             DESCRIPTION
--                 "Minimum time that the current margin is below
--                 DownshiftSnrMgn before a downshift occurs.
--                 In the case that RADSL mode is not present,
--                 the value will be `0'."
--         ::= { adslLineConfProfileEntry 24 }

         adslAturChanConfFastMinTxRate  OBJECT-TYPE
             SYNTAX      Unsigned32
             UNITS       "bps"
             MAX-ACCESS  read-create
             STATUS      current
             DESCRIPTION
                 "Configured Minimum Transmit rate for `Fast' channels,
                 in bps.  See adslAturConfRateChanRatio for information
                 regarding RADSL mode and ATUC transmit rate
                 for ATUR receive rates."
         ::= { adslLineConfProfileEntry 25 }

         adslAturChanConfInterleaveMinTxRate OBJECT-TYPE
             SYNTAX      Unsigned32
             UNITS       "bps"
             MAX-ACCESS  read-create
             STATUS      current
             DESCRIPTION
                 "Configured Minimum Transmit rate for `Interleave'
                 channels, in bps.  See adslAturConfRateChanRatio for
                 information regarding RADSL mode and ATUC transmit rate
                 for ATUR receive rates."
         ::= { adslLineConfProfileEntry 26 }

         adslAturChanConfFastMaxTxRate  OBJECT-TYPE
             SYNTAX      Unsigned32
             UNITS       "bps"
             MAX-ACCESS  read-create
             STATUS      current
             DESCRIPTION
                 "Configured Maximum Transmit rate for `Fast' channels,
                 in bps.  See adslAturConfRateChanRatio for information
                 regarding RADSL mode and ATUC transmit rate
                 for ATUR receive rates."
         ::= { adslLineConfProfileEntry 27 }

         adslAturChanConfInterleaveMaxTxRate OBJECT-TYPE
             SYNTAX      Unsigned32
             UNITS       "bps"
             MAX-ACCESS  read-create
             STATUS      current
             DESCRIPTION
                 "Configured Maximum Transmit rate for `Interleave'
                 channels, in bps.  See adslAturConfRateChanRatio for
                 information regarding RADSL mode and see
                 ATUC transmit rate for ATUR receive rates."
         ::= { adslLineConfProfileEntry 28 }

         adslAturChanConfMaxInterleaveDelay OBJECT-TYPE
             SYNTAX      INTEGER(0..255)
             UNITS        "milli-seconds"
             MAX-ACCESS  read-create
             STATUS      current
             DESCRIPTION
                 "Configured maximum Interleave Delay for this channel.

                 Interleave delay applies only to the interleave channel
                 and defines the mapping (relative spacing) between
                 subsequent input bytes at the interleaver input and
                 their placement in the bit stream at the interleaver
                 output.  Larger numbers provide greater separation
                 between consecutive input bytes in the output bit
                 stream allowing for improved impulse noise immunity
                 at the expense of payload latency."
         ::= { adslLineConfProfileEntry 29 }

         adslLineConfProfileRowStatus OBJECT-TYPE
             SYNTAX          RowStatus
             MAX-ACCESS      read-create
             STATUS          current
             DESCRIPTION
                 "This object is used to create a new row or modify or
                 delete an existing row in this table.
                 A profile activated by setting this object to
                 `active'.  When `active' is set, the system
                 will validate the profile.

                 Before a profile can be deleted or taken out of
                 service, (by setting this object to `destroy' or
                 `outOfService') it must be first unreferenced
                 from all associated lines.

                 If the implementator of this MIB has chosen not
                 to implement `dynamic assignment' of profiles, this
                 object's MIN-ACCESS is read-only and its value
                 is always to be `active'."
         ::= { adslLineConfProfileEntry 30 }

         adslLineAlarmConfProfileTable    OBJECT-TYPE
             SYNTAX          SEQUENCE OF AdslLineAlarmConfProfileEntry
             MAX-ACCESS      not-accessible
             STATUS          current
             DESCRIPTION
                 "This table contains information on the ADSL line
                 configuration.  One entry in this table reflects a
                 profile defined by a manager which can be used to
                 configure the modem for a physical line"
         ::= { adslMibObjects 15}

         adslLineAlarmConfProfileEntry    OBJECT-TYPE
             SYNTAX          AdslLineAlarmConfProfileEntry
             MAX-ACCESS      not-accessible
             STATUS          current
             DESCRIPTION
                 "Each entry consists of a list of parameters that
                 represents the configuration of an ADSL modem.

                 When `dynamic' profiles are implemented, a default
                 profile will always exist.  This profile's name will
                 be set to `DEFVAL' and its parameters will be set to
                 vendor specific values, unless otherwise specified
                 in this document.

                 When `static' profiles are implemented, profiles
                 are automaticly created or destroyed as ADSL
                 physical lines are discovered and removed by
                 the system.  The name of the profile will be
                 equivalent to the decimal value of the line's
                 interface index.
                 "
             INDEX { IMPLIED adslLineAlarmConfProfileName}
         ::= { adslLineAlarmConfProfileTable 1}

         AdslLineAlarmConfProfileEntry ::=
             SEQUENCE {
             adslLineAlarmConfProfileName          SnmpAdminString,
             adslAtucThresh15MinLofs               INTEGER,
             adslAtucThresh15MinLoss               INTEGER,
             adslAtucThresh15MinLols               INTEGER,
             adslAtucThresh15MinLprs               INTEGER,
             adslAtucThresh15MinESs                INTEGER,
--             adslAtucThreshFastRateUp              Unsigned32,
--             adslAtucThreshInterleaveRateUp        Unsigned32,
--             adslAtucThreshFastRateDown            Unsigned32,
--             adslAtucThreshInterleaveRateDown      Unsigned32,
             adslAtucInitFailureTrapEnable         INTEGER,
             adslAturThresh15MinLofs               INTEGER,
             adslAturThresh15MinLoss               INTEGER,
             adslAturThresh15MinLprs               INTEGER,
             adslAturThresh15MinESs                INTEGER,
--             adslAturThreshFastRateUp              Unsigned32,
--             adslAturThreshInterleaveRateUp        Unsigned32,
--             adslAturThreshFastRateDown            Unsigned32,
--             adslAturThreshInterleaveRateDown      Unsigned32,
             adslLineAlarmConfProfileRowStatus     RowStatus
             }

         adslLineAlarmConfProfileName    OBJECT-TYPE
             SYNTAX          SnmpAdminString (SIZE (1..32))
             MAX-ACCESS      not-accessible
             STATUS          current
             DESCRIPTION
                 "This object is used by the line alarm configuration
                 table in order to identify a row of this table.

                 When `dynamic' profiles are implemented, the profile
                 name is user specified.  Also, the system will always
                 provide a default profile whose name is `DEFVAL'.

                 When `static' profiles are implemented, there is an
                 one-to-one relationship between each line and its
                 profile.  In which case, the profile name will
                 need to algorithmicly represent the Line's ifIndex.
                 Therefore, the profile's name is a decimalized string
                 of the ifIndex that is fixed-length (i.e., 10) with
                 leading zero(s).  For example, the profile name for
                 ifIndex which equals '15' will be '0000000015'."
         ::= { adslLineAlarmConfProfileEntry 1}

         adslAtucThresh15MinLofs OBJECT-TYPE
             SYNTAX      INTEGER(0..900)
             UNITS       "seconds"
             MAX-ACCESS  read-create
             STATUS      current
             DESCRIPTION
                 "The number of Loss of Frame Seconds
                 encountered by an ADSL interface within any given 15
                 minutes performance data collection period, which
                 causes the SNMP agent to send an
                 adslAtucPerfLofsThreshTrap.
                 One trap will be sent per interval per interface.
                 A value of `0' will disable the trap."
         ::= { adslLineAlarmConfProfileEntry 2}

         adslAtucThresh15MinLoss  OBJECT-TYPE
             SYNTAX      INTEGER(0..900)
             UNITS       "seconds"
             MAX-ACCESS  read-create
             STATUS      current
             DESCRIPTION
                 "The number of Loss of Signal Seconds
                 encountered by an ADSL interface within any given 15
                 minutes performance data collection period, which
                 causes the SNMP agent to send an
                 adslAtucPerfLossThreshTrap.
                 One trap will be sent per interval per interface.
                 A value of `0' will disable the trap."
         ::= { adslLineAlarmConfProfileEntry 3}

         adslAtucThresh15MinLols  OBJECT-TYPE
             SYNTAX      INTEGER(0..900)
             UNITS       "seconds"
             MAX-ACCESS  read-create
             STATUS      current
             DESCRIPTION
                 "The number of Loss of Link Seconds
                 encountered by an ADSL interface within any given 15
                 minutes performance data collection period, which
                 causes the SNMP agent to send an
                 adslAtucPerfLolsThreshTrap.
                 One trap will be sent per interval per interface.
                 A value of `0' will disable the trap."
         ::= { adslLineAlarmConfProfileEntry 4}

         adslAtucThresh15MinLprs  OBJECT-TYPE
             SYNTAX      INTEGER(0..900)
             UNITS       "seconds"
             MAX-ACCESS  read-create
             STATUS      current
             DESCRIPTION
                 "The number of Loss of Power Seconds
                 encountered by an ADSL interface within any given 15
                 minutes performance data collection period, which
                 causes the SNMP agent to send an
                 adslAtucPerfLprsThreshTrap.
                 One trap will be sent per interval per interface.
                 A value of `0' will disable the trap."
         ::= { adslLineAlarmConfProfileEntry 5}

         adslAtucThresh15MinESs  OBJECT-TYPE
             SYNTAX      INTEGER(0..900)
             UNITS       "seconds"
             MAX-ACCESS  read-create
             STATUS      current
             DESCRIPTION
                 "The number of Errored Seconds
                 encountered by an ADSL interface within any given 15
                 minutes performance data collection period, which
                 causes the SNMP agent to send an
                 adslAtucPerfESsThreshTrap.
                 One trap will be sent per interval per interface.
                 A value of `0' will disable the trap."
         ::= { adslLineAlarmConfProfileEntry 6}

--         adslAtucThreshFastRateUp OBJECT-TYPE
--             SYNTAX      Unsigned32
--             UNITS       "bps"
--             MAX-ACCESS  read-create
--             STATUS      current
--             DESCRIPTION
--                 "Applies to `Fast' channels only.
--                 Configured change in rate causing an
--                 adslAtucRateChangeTrap. A trap is produced when:
--                 ChanCurrTxRate >= ChanPrevTxRate plus the value of
--                 this object. A value of `0' will disable the trap."
--         ::= { adslLineAlarmConfProfileEntry 7}
--
--         adslAtucThreshInterleaveRateUp OBJECT-TYPE
--             SYNTAX      Unsigned32
--             UNITS       "bps"
--             MAX-ACCESS  read-create
--             STATUS      current
--             DESCRIPTION
--                 "Applies to `Interleave' channels only.
--                 Configured change in rate causing an
--                 adslAtucRateChangeTrap.  A trap is produced when:
--                 ChanCurrTxRate >= ChanPrevTxRate plus the value of
--                 this object. A value of `0' will disable the trap."
--         ::= { adslLineAlarmConfProfileEntry 8}
--
--         adslAtucThreshFastRateDown OBJECT-TYPE
--             SYNTAX      Unsigned32
--             UNITS       "bps"
--             MAX-ACCESS  read-create
--             STATUS      current
--             DESCRIPTION
--                 "Applies to `Fast' channels only.
--                 Configured change in rate causing an
--                 adslAtucRateChangeTrap.  A trap is produced when:
--                 ChanCurrTxRate <= ChanPrevTxRate minus the value of
--                 this object. A value of `0' will disable the trap."
--         ::= { adslLineAlarmConfProfileEntry 9 }
--
--         adslAtucThreshInterleaveRateDown OBJECT-TYPE
--             SYNTAX      Unsigned32
--             UNITS       "bps"
--             MAX-ACCESS  read-create
--             STATUS      current
--             DESCRIPTION
--                 "Applies to `Interleave' channels only.
--                 Configured change in rate causing an
--                 adslAtucRateChangeTrap.  A trap is produced when:
--                 ChanCurrTxRate <= ChanPrevTxRate minus the value of
--                 this object. A value of `0' will disable the trap."
--         ::= { adslLineAlarmConfProfileEntry 10 }

         adslAtucInitFailureTrapEnable OBJECT-TYPE
             SYNTAX      INTEGER {
                 enable (1),
                 disable (2)
             }
             MAX-ACCESS  read-create
             STATUS      current
             DESCRIPTION
                 "Enables and disables the InitFailureTrap.  This
                 object is defaulted disable(2)."
         DEFVAL { disable }
         ::= { adslLineAlarmConfProfileEntry 11 }

         adslAturThresh15MinLofs OBJECT-TYPE
             SYNTAX      INTEGER(0..900)
             UNITS       "seconds"
             MAX-ACCESS  read-create
             STATUS      current
             DESCRIPTION
                 "The number of Loss of Frame Seconds
                 encountered by an ADSL interface within any given 15
                 minutes performance data collection period, which
                 causes the SNMP agent to send an
                 adslAturPerfLofsThreshTrap.
                 One trap will be sent per interval per interface.
                 A value of `0' will disable the trap."
         ::= { adslLineAlarmConfProfileEntry 12 }

         adslAturThresh15MinLoss  OBJECT-TYPE
             SYNTAX      INTEGER(0..900)
             UNITS       "seconds"
             MAX-ACCESS  read-create
             STATUS      current
             DESCRIPTION
                 "The number of Loss of Signal Seconds
                 encountered by an ADSL interface within any given 15
                 minutes performance data collection period, which
                 causes the SNMP agent to send an
                 adslAturPerfLossThreshTrap.
                 One trap will be sent per interval per interface.
                 A value of `0' will disable the trap."
         ::= { adslLineAlarmConfProfileEntry 13 }

         adslAturThresh15MinLprs  OBJECT-TYPE
             SYNTAX      INTEGER(0..900)
             UNITS       "seconds"
             MAX-ACCESS  read-create
             STATUS      current
             DESCRIPTION
                 "The number of Loss of Power Seconds
                 encountered by an ADSL interface within any given 15
                 minutes performance data collection period, which
                 causes the SNMP agent to send an
                 adslAturPerfLprsThreshTrap.
                 One trap will be sent per interval per interface.
                 A value of `0' will disable the trap."
         ::= { adslLineAlarmConfProfileEntry 14 }

         adslAturThresh15MinESs  OBJECT-TYPE
             SYNTAX      INTEGER(0..900)
             UNITS       "seconds"
             MAX-ACCESS  read-create
             STATUS      current
             DESCRIPTION
                 "The number of Errored Seconds
                 encountered by an ADSL interface within any given 15
                 minutes performance data collection period, which
                 causes the SNMP agent to send an
                 adslAturPerfESsThreshTrap.
                 One trap will be sent per interval per interface.
                 A value of `0' will disable the trap."
         ::= { adslLineAlarmConfProfileEntry 15 }

--         adslAturThreshFastRateUp OBJECT-TYPE
--             SYNTAX      Unsigned32
--             UNITS       "bps"
--             MAX-ACCESS  read-create
--             STATUS      current
--             DESCRIPTION
--                 "Applies to `Fast' channels only.
--                 Configured change in rate causing an
--                 adslAturRateChangeTrap.  A trap is produced when:
--                 ChanCurrTxRate >= ChanPrevTxRate plus the value of
--                 this object. A value of `0' will disable the trap."
--         ::= { adslLineAlarmConfProfileEntry 16 }
--
--         adslAturThreshInterleaveRateUp OBJECT-TYPE
--             SYNTAX      Unsigned32
--             UNITS       "bps"
--             MAX-ACCESS  read-create
--             STATUS      current
--             DESCRIPTION
--                 "Applies to `Interleave' channels only.
--                 configured change in rate causing an
--                 adslAturRateChangeTrap.  A trap is produced when:
--                 ChanCurrTxRate >= ChanPrevTxRate plus the value of
--                 this object. A value of `0' will disable the trap."
--         ::= { adslLineAlarmConfProfileEntry 17 }
--
--         adslAturThreshFastRateDown OBJECT-TYPE
--             SYNTAX      Unsigned32
--             UNITS       "bps"
--             MAX-ACCESS  read-create
--             STATUS      current
--             DESCRIPTION
--                 "Applies to `Fast' channels only.
--                 Configured change in rate causing an
--                 adslAturRateChangeTrap.  A trap is produced when:
--                 ChanCurrTxRate <= ChanPrevTxRate minus the value of
--                 this object. A value of `0' will disable the trap."
--         ::= { adslLineAlarmConfProfileEntry 18 }
--
--         adslAturThreshInterleaveRateDown OBJECT-TYPE
--             SYNTAX      Unsigned32
--             UNITS       "bps"
--             MAX-ACCESS  read-create
--             STATUS      current
--             DESCRIPTION
--                 "Applies to `Interleave' channels only.
--                 Configured change in rate causing an
--                 adslAturRateChangeTrap.  A trap is produced when:
--                 ChanCurrTxRate <= ChanPrevTxRate minus the value of
--                 this object. A value of `0' will disable the trap."
--         ::= { adslLineAlarmConfProfileEntry 19 }

         adslLineAlarmConfProfileRowStatus OBJECT-TYPE
             SYNTAX          RowStatus
             MAX-ACCESS      read-create
             STATUS          current
             DESCRIPTION
                 "This object is used to create a new row or modify or
                 delete an existing row in this table.

                 A profile activated by setting this object to
                 `active'.  When `active' is set, the system
                 will validate the profile.

                 Before a profile can be deleted or taken out of
                 service, (by setting this object to `destroy' or
                 `outOfService') it must be first unreferenced
                 from all associated lines.

                 If the implementator of this MIB has chosen not
                 to implement `dynamic assignment' of profiles, this
                 object's MIN-ACCESS is read-only and its value
                 is always to be `active'."
         ::= { adslLineAlarmConfProfileEntry 20 }

         -- Line Code Specific Tables

         -- These are place holders for the Line Code Specific MIBs
         -- once they become available.

--         adslLCSMib  OBJECT IDENTIFIER ::= { adslMibObjects 16 }

   -- trap definitions

   adslTraps OBJECT IDENTIFIER ::= { adslLineMib 2 }

   adslAtucTraps OBJECT IDENTIFIER ::= { adslTraps 1 }

         adslAtucPerfLofsThreshTrap      NOTIFICATION-TYPE
             OBJECTS { adslAtucPerfCurr15MinLofs,
                       adslAtucThresh15MinLofs }
             STATUS  current
             DESCRIPTION
                 "Loss of Framing 15-minute interval threshold reached."
         ::= { adslAtucTraps 0 1 }

         adslAtucPerfLossThreshTrap      NOTIFICATION-TYPE
             OBJECTS { adslAtucPerfCurr15MinLoss,
                       adslAtucThresh15MinLoss }
             STATUS  current
             DESCRIPTION
                 "Loss of Signal 15-minute interval threshold reached."
         ::= { adslAtucTraps 0 2 }

         adslAtucPerfLprsThreshTrap      NOTIFICATION-TYPE
             OBJECTS { adslAtucPerfCurr15MinLprs,
                       adslAtucThresh15MinLprs }
             STATUS  current
             DESCRIPTION
                 "Loss of Power 15-minute interval threshold reached."
         ::= { adslAtucTraps 0 3 }

         adslAtucPerfESsThreshTrap       NOTIFICATION-TYPE
             OBJECTS { adslAtucPerfCurr15MinESs,
                       adslAtucThresh15MinESs }
             STATUS  current
             DESCRIPTION
                 "Errored Second 15-minute interval threshold reached."
         ::= { adslAtucTraps 0 4 }

         adslAtucRateChangeTrap  NOTIFICATION-TYPE
             OBJECTS { adslAtucChanCurrTxRate,
                       adslAtucChanPrevTxRate }
             STATUS  current
             DESCRIPTION
                 "The ATUCs transmit rate has changed (RADSL mode only)"
         ::= { adslAtucTraps 0 5 }

         adslAtucPerfLolsThreshTrap      NOTIFICATION-TYPE
             OBJECTS { adslAtucPerfCurr15MinLols,
                       adslAtucThresh15MinLols }
             STATUS  current
             DESCRIPTION
                 "Loss of Link 15-minute interval threshold reached."
         ::= { adslAtucTraps 0 6 }

         adslAtucInitFailureTrap NOTIFICATION-TYPE
             OBJECTS { adslAtucCurrStatus }
             STATUS  current
             DESCRIPTION
                 "ATUC initialization failed. See adslAtucCurrStatus
                 for potential reasons."
         ::= { adslAtucTraps 0 7 }

   adslAturTraps OBJECT IDENTIFIER ::= { adslTraps 2 }

         adslAturPerfLofsThreshTrap      NOTIFICATION-TYPE
             OBJECTS { adslAturPerfCurr15MinLofs,
                       adslAturThresh15MinLofs }
             STATUS  current
             DESCRIPTION
                 "Loss of Framing 15-minute interval threshold reached."
         ::= { adslAturTraps 0 1 }

         adslAturPerfLossThreshTrap      NOTIFICATION-TYPE
             OBJECTS { adslAturPerfCurr15MinLoss,
                       adslAturThresh15MinLoss }
             STATUS  current
             DESCRIPTION
                 "Loss of Signal 15-minute interval threshold reached."
         ::= { adslAturTraps 0 2 }

         adslAturPerfLprsThreshTrap      NOTIFICATION-TYPE
             OBJECTS { adslAturPerfCurr15MinLprs,
                       adslAturThresh15MinLprs }
             STATUS  current
             DESCRIPTION
                 "Loss of Power 15-minute interval threshold reached."
         ::= { adslAturTraps 0 3 }

         adslAturPerfESsThreshTrap       NOTIFICATION-TYPE
             OBJECTS { adslAturPerfCurr15MinESs,
                       adslAturThresh15MinESs }
             STATUS  current
             DESCRIPTION
                 "Errored Second 15-minute interval threshold reached."
         ::= { adslAturTraps 0 4 }

         adslAturRateChangeTrap  NOTIFICATION-TYPE
             OBJECTS { adslAturChanCurrTxRate,
                       adslAturChanPrevTxRate }
             STATUS  current
             DESCRIPTION
                 "The ATURs transmit rate has changed (RADSL mode only)"
         ::= { adslAturTraps 0 5 }

         -- no adslAturPerfLolsThreshTrap possible { 0 6 }

         -- no adslAturInitFailureTrap possible { 0 7 }

   -- conformance information


   END
   
   
ZXDSLAM-MIB DEFINITIONS ::= BEGIN
IMPORTS
        MODULE-IDENTITY, TimeTicks,	OBJECT-TYPE,
		NOTIFICATION-TYPE, enterprises,IpAddress FROM SNMPv2-SMI
        DateAndTime  	FROM SNMPv2-TC
		atmVcCrossConnectIndex FROM ATM-MIB
		InterfaceIndex,ifEntry,ifIndex					FROM IF-MIB;
-- 		PhysicalIndex                  		  		FROM ENTITY-MIB;

zte MODULE-IDENTITY
LAST-UPDATED "2703200000Z"
ORGANIZATION ""
CONTACT-INFO ""
DESCRIPTION  "Initial Version"
::= { enterprises 5000 } 


zxDslam	    OBJECT IDENTIFIER ::= { zte 29 }
zxDslamAim  OBJECT IDENTIFIER ::= { zxDslam 1 }
zxDslamTrap OBJECT IDENTIFIER ::= { zxDslam 2 }
zxDslamCommon OBJECT IDENTIFIER ::= { zxDslam 3 }
zxDslamCommonLoad OBJECT IDENTIFIER ::= { zxDslamCommon 1 }
zxDslamCommonVer  OBJECT IDENTIFIER ::= { zxDslamCommon 2 }
zxDslamCommonData  OBJECT IDENTIFIER ::= { zxDslamCommon 3 }
zxDslamGroup	OBJECT IDENTIFIER ::= { zxDslam 4 }

zxCsv          OBJECT IDENTIFIER ::= { zte               1009  }                         
-- csv product
zxAccessProduct     OBJECT IDENTIFIER ::= { zxCsv        3     } 
-- access product

selfMake       OBJECT IDENTIFIER ::= { zxAccessProduct   1     }                        
-- self develop

zxCsvObj       OBJECT IDENTIFIER ::= { selfMake     1     }
-- csv product

zxCsvCmd       OBJECT IDENTIFIER ::= { zxCsvObj     1     }
-- csv command

zxCsvTrap      OBJECT IDENTIFIER ::= { zxCsvObj     2     }
-- csv trap
                      
DisplayString ::= OCTET STRING

-- the card table

zxDslamCardTable OBJECT-TYPE
	SYNTAX		SEQUENCE OF ZxDslamCardEntry
	MAX-ACCESS	not-accessible
	STATUS		current
	DESCRIPTION	"A list of card entries."
	::= { zxDslamAim 1 }

zxDslamCardEntry OBJECT-TYPE
	SYNTAX		ZxDslamCardEntry
	MAX-ACCESS	not-accessible
	STATUS		current
	DESCRIPTION	
        "An card entry containing objects describing the card in some slot."
	INDEX	{ zxDslamCardIndex }
	::= { zxDslamCardTable 1 }

ZxDslamCardEntry ::= SEQUENCE {
    zxDslamCardIndex				INTEGER,
    zxDslamCardType				INTEGER,
    zxDslamCardFrame       INTEGER,
    zxDslamCardShelf       INTEGER,
    zxDslamCardSlot				INTEGER,
    zxDslamCardPortNum       INTEGER,
    zxDslamCardstandbyStatus         INTEGER,
   	zxDslamCardDescr				DisplayString,
    zxDslamCardAdminStatus		INTEGER,
    zxDslamCardOperStatus		INTEGER,
  	zxDslamCardLastChange		TimeTicks,
    zxDslamHardwareVersion             		DisplayString, 	
    zxDslamSoftwareVersion             		DisplayString 
--  zxDslamCardEntPhysicalIndex	PhysicalIndex            
--    zxDslamBuildtimeVersion	           		DisplayString, 	
--    zxDslamBackupSoftwareVersion            DisplayString, 
--    zxDslamBackupBuildtimeVersion          	DisplayString, 	
--    zxDslamVersionNum				INTEGER,
--    zxDslamCardChipsOperStatus		INTEGER
	}

zxDslamCardIndex OBJECT-TYPE
	  SYNTAX		INTEGER
    MAX-ACCESS  not-accessible
    STATUS      current
    DESCRIPTION
          "The index for this entry."
	::= { zxDslamCardEntry 1 }

zxDslamCardType 	OBJECT-TYPE
	SYNTAX	INTEGER {
                unknown(0),  
                core(1),
                wan-ds3(2),
                wan-sdh(3),
                power(4),
	        atuc-ti(5),  -- ATUC card
        	atuc-al(6),  -- ATUC card
        	other(7) ,
        	corea (8),
                corec(9),
                wana1(10),
                wanad(11),
                wane(12),
                esu(13),
                atucd(14),
                atuce(15),
                atucf(16),
                atucg(17),
                atuch(18),
                atuci(19),
				ima(20),
				coreA2(21),
                coreB2(22),
                coreC2(23),
                coreA3(24),
                coreB3(25),
                coreC3(26),
                imab(27),
                lanaa(28),
                lanab(29),
                lanac(30),
                lanad(31),
                lanba(32),
                lanbb(33),
                lanca(34),
                lancb(35),
                lancc(36),
                lancd(37),
                landa(38),
                landb(39),
                stuca(40),
                atugi(41)
            }
	MAX-ACCESS	read-only
	STATUS		current
	DESCRIPTION	
   		"The type of card, distinguished according to 
		service type carried or function."
	::= { zxDslamCardEntry 2 }

zxDslamCardFrame   OBJECT-TYPE   
  SYNTAX  INTEGER
  MAX-ACCESS  read-only
  STATUS current
  DESCRIPTION	
		"The number of frame which contained this card."
	::= { zxDslamCardEntry 3 }
	
zxDslamCardShelf   OBJECT-TYPE   
  SYNTAX  INTEGER
  MAX-ACCESS read-only
  STATUS current
  DESCRIPTION	
		"The number of shelf which contained this card."
	::= { zxDslamCardEntry 4 }
	
zxDslamCardSlot	OBJECT-TYPE
 	SYNTAX		INTEGER
 	MAX-ACCESS	read-only
 	STATUS		current
 	DESCRIPTION	
		"The number of slot which contained this card."
 	::= { zxDslamCardEntry 5 }

zxDslamCardPortNum   OBJECT-TYPE
    SYNTAX   INTEGER
	MAX-ACCESS read-only
	STATUS    current
	DESCRIPTION	
		"The number of port which contained in this card."
 	::= { zxDslamCardEntry 6 }

zxDslamCardstandbyStatus   OBJECT-TYPE
	SYNTAX	INTEGER {
	            unknown(0),
	            single(1),
                    standby(2), 
                    master(3)                    
                }
	MAX-ACCESS	read-write
	STATUS		current
	DESCRIPTION	
		"The type of card, distinguished according to 
		service type carried  or function."
	::= { zxDslamCardEntry 7 }

zxDslamCardDescr OBJECT-TYPE
	SYNTAX		DisplayString (SIZE (0..255))
	MAX-ACCESS	read-only
	STATUS		current
    	DESCRIPTION	
		"A textual string containing information about the card.
		This string should include the manufacturer, 
		the product name, type, function and version of the hardware."
	::= { zxDslamCardEntry 8 }

zxDslamCardAdminStatus	OBJECT-TYPE
	SYNTAX	INTEGER {
				up(1),		-- ready
				down(2),	-- deactiivate
				testing(3)	-- in some test mode
			}
	MAX-ACCESS	read-write
	STATUS		current
	DESCRIPTION	
		"The desired state of the card. 
		The down (2) and testing (3) state indicate	
		the card doesn't present service currently."
	::= { zxDslamCardEntry 9 }
	
zxDslamCardOperStatus	OBJECT-TYPE
	SYNTAX	INTEGER {
				up(1),		-- ready
				down(2),	-- fault occur or pulled out from the slot
				testing(3)	-- in some test mode
			}
	MAX-ACCESS	read-only
	STATUS		current
	DESCRIPTION	
		"The current operational state of the card. 
		The down (2) and testing (3) mode indicate that 
		no service can be presented by the card."
	::= { zxDslamCardEntry 10 }

zxDslamCardLastChange	OBJECT-TYPE
	SYNTAX		TimeTicks
	MAX-ACCESS	read-only
	STATUS		current
	DESCRIPTION	
			"The value of sysUpTime at the time 
			the card entered its current operational state. 
			If the current state was entered prior to the last 
			reinitialization of the	local network management subsystem, 
			then this object contains a zero value."
	::= { zxDslamCardEntry 11 }
	
zxDslamHardwareVersion  OBJECT-TYPE
	SYNTAX		DisplayString (SIZE (0..32))
	MAX-ACCESS	read-only
	STATUS		current
        DESCRIPTION	"hardware Version of this card"
	::= { zxDslamCardEntry 12 } 
	
--zxDslamVersionNum	OBJECT-TYPE
--	SYNTAX      INTEGER (1..2)
--	MAX-ACCESS	read-only
--	STATUS		current
--	DESCRIPTION	
--		"version number."
--	::= { zxDslamCardEntry 13 }
	
zxDslamSoftwareVersion  OBJECT-TYPE
	SYNTAX		DisplayString (SIZE (0..32))
	MAX-ACCESS	read-only
	STATUS		current
        DESCRIPTION	"running software Version of this card"
	::= { zxDslamCardEntry 14 } 
	
--zxDslamBuildtimeVersion	OBJECT-TYPE
--	SYNTAX      DisplayString (SIZE (0..32))
--	MAX-ACCESS	read-only
--	STATUS		current
--	DESCRIPTION	
--		"running Version buildtime of this card."
--	::= { zxDslamCardEntry 15 }
--zxDslamBackupSoftwareVersion	OBJECT-TYPE
--	SYNTAX      DisplayString (SIZE (0..32))
--	MAX-ACCESS	read-only
--	STATUS		current
--	DESCRIPTION	
--		"backup software version."
--	::= { zxDslamCardEntry 16 }
--
--zxDslamBackupBuildtimeVersion	OBJECT-TYPE
--	SYNTAX      DisplayString (SIZE (0..32))
--	MAX-ACCESS	read-only
--	STATUS		current
--	DESCRIPTION	
--		"backup version buildtime."
--	::= { zxDslamCardEntry 17 }
	

--zxDslamCardChipsOperStatus	OBJECT-TYPE
--	SYNTAX      INTEGER (0..63)
--	MAX-ACCESS	read-only
--	STATUS		current
--	DESCRIPTION	
--		"The current operational state of the card chips. 
--		!!!!!!!!!!!!!!!!!The down (2) and testing (3) mode indicate that 
--		no service can be presented by the card."
--	::= { zxDslamCardEntry 18 }
	

-- definition of 
-- definition of zxDslamPortIfIndexMappingTable

zxDslamPortIfIndexMappingTable OBJECT-TYPE
	SYNTAX		SEQUENCE OF ZxDslamPortIfIndexMappingEntry
	MAX-ACCESS		not-accessible
	STATUS		current
	DESCRIPTION
		"zxDslamPortIfIndexMappingTable  is used to show the mapping from 
		Port	to ifIndex."
	::= {zxDslamAim 2 }

zxDslamPortIfIndexMappingEntry	OBJECT-TYPE
	SYNTAX		ZxDslamPortIfIndexMappingEntry
	MAX-ACCESS		not-accessible
	STATUS		current
	DESCRIPTION
		"An entry in the zxDslamPortIfIndexMappingTable. There is one 
		 entry  in the table corresponding to each active row in the
		 ifTable for which there is a non-zero cpn and ifindex."
	INDEX	{ zxDslamMappingFrame,zxDslamMappingShelf,
	zxDslamMappingSlot,zxDslamMappingPort,zxDslamPortMappingifIndex}
	::= {zxDslamPortIfIndexMappingTable 1 }

ZxDslamPortIfIndexMappingEntry	::= SEQUENCE {
	zxDslamMappingFrame INTEGER,
	zxDslamMappingShelf INTEGER,
	zxDslamMappingSlot  INTEGER,
    zxDslamMappingPort  INTEGER,
    zxDslamPortMappingifIndex       InterfaceIndex
}

zxDslamMappingFrame    OBJECT-TYPE
    SYNTAX  INTEGER
    MAX-ACCESS  not-accessible
    STATUS      current
    DESCRIPTION
            "The sub-index for this entry."
  ::= {zxDslamPortIfIndexMappingEntry 1 } 
zxDslamMappingShelf    OBJECT-TYPE
    SYNTAX  INTEGER
    MAX-ACCESS  not-accessible
    STATUS      current
    DESCRIPTION
            "The sub-index for this entry."
  ::= {zxDslamPortIfIndexMappingEntry 2 } 
zxDslamMappingSlot     OBJECT-TYPE
    SYNTAX  INTEGER
    MAX-ACCESS  not-accessible
    STATUS      current
    DESCRIPTION
            "The sub-index for this entry."
  ::= {zxDslamPortIfIndexMappingEntry 3 } 
zxDslamMappingPort     OBJECT-TYPE
    SYNTAX  INTEGER
    MAX-ACCESS  not-accessible
    STATUS      current
    DESCRIPTION
            "The sub-index for this entry."
  ::= {zxDslamPortIfIndexMappingEntry 4 }             
  
zxDslamPortMappingifIndex	OBJECT-TYPE
	SYNTAX			InterfaceIndex
	MAX-ACCESS		read-only
	STATUS			current
	DESCRIPTION
		 "The value of InterfaceIndex of the same circuitnum."
	::= {zxDslamPortIfIndexMappingEntry 5 } 
--		
-- zxDslamSysDateAndTime	OBJECT-TYPE
--	SYNTAX		DateAndTime
--	MAX-ACCESS	read-write
--	STATUS		current
--	DESCRIPTION	"The system time of ZX Dslam "
--	::= { zxDslamAim 3 }
 
zxDslamCardNumber  OBJECT-TYPE
  SYNTAX		INTEGER
  MAX-ACCESS read-only
  STATUS  current
  DESCRIPTION	"The  Cards number of ZX Dslam "
  ::= {zxDslamAim 4 }

zxDslamVcxSubscriberMappingTable OBJECT-TYPE
  SYNTAX		SEQUENCE OF ZxDslamVcxSubscriberMappingEntry
  MAX-ACCESS		not-accessible
  STATUS		current
  DESCRIPTION
	"zxDslamSubscriberVcxIndexMappingTab  is used to show the mapping from 
	Vcx	to subscriber name."
  ::= {zxDslamAim 5 }

zxDslamVcxSubscriberMappingEntry OBJECT-TYPE
    SYNTAX		ZxDslamVcxSubscriberMappingEntry
	MAX-ACCESS		not-accessible
	STATUS		current
	DESCRIPTION
		"An entry in the zxDslamVcxSubscriberMappingTable. There is one 
		 entry  in the table corresponding to each active row in the
		 AtmVcCrossConnectTable, there is subscriber name."
	INDEX	{atmVcCrossConnectIndex }
	::= {zxDslamVcxSubscriberMappingTable 1 } 

ZxDslamVcxSubscriberMappingEntry ::= SEQUENCE {
	zxDslamVcxSubscribeName DisplayString	
}

zxDslamVcxSubscribeName OBJECT-TYPE
  SYNTAX	DisplayString(SIZE(0..32))
  MAX-ACCESS read-write
  STATUS  current
  DESCRIPTION	"The  subscriber name of vcx "
  ::= {zxDslamVcxSubscriberMappingEntry 1 }   

zxDslamCommandTable        OBJECT-TYPE
     SYNTAX         SEQUENCE OF ZxDslamCommandEntry
     MAX-ACCESS     not-accessible
     STATUS         current
     DESCRIPTION
        	"The ZXDslam command Execute table. "
     ::= {zxDslamAim 6 }

zxDslamCommandEntry		OBJECT-TYPE
     SYNTAX         ZxDslamCommandEntry
     MAX-ACCESS     not-accessible
     STATUS         current
     DESCRIPTION
		"An entry in the ZXDslam command Execute table  "
     INDEX  {  zxDslamCommandType }	
     ::= { zxDslamCommandTable  1}

ZxDslamCommandEntry  ::= SEQUENCE  {
     zxDslamCommandType			INTEGER ,
     zxDslamCommandLastChange	TimeTicks ,
     zxDslamCommandStatus	    INTEGER
  }
	
	
zxDslamCommandType			OBJECT-TYPE
     SYNTAX          INTEGER 	{	
                saveAdslFlash(1),
		saveAtmFlash(2),
		saveSysFlash(3),
		initAdslFlash(4),
		initAtmFlash(5),
		initSysFlash(6),
		swich(7),
		sysReboot(8),
		download(9),
		switchVer(10),
		creatPvcGroup(11),
		deletePvcAll(12),
		disablePvcGroup(13),
		enablePvcGroup(14),
		setLinGroup(15),
        enableLinGroup(16),
        disableLinGroup(17),
		setAlamGroup(18),
		resetDslGroup(19),
		resetCardGroup(20)
	        }
	MAX-ACCESS     read-only
	STATUS         current
	DESCRIPTION
			" The operation type of the commands."
	::= { zxDslamCommandEntry	1}
	

zxDslamCommandLastChange	OBJECT-TYPE
	SYNTAX         TimeTicks
	MAX-ACCESS     read-only
	STATUS         current
	DESCRIPTION
		  "The value of MIB-II's sysUpTime at the time this
                   Command is excuted.	When the command hasn't been excuted,
	           the value is always  zero. " 
          ::= { zxDslamCommandEntry	2 }

zxDslamCommandStatus		OBJECT-TYPE
        SYNTAX    INTEGER 	{	
         			cmdNeverExecuted(0),
 				lastCmdSuccessfulExecuted(1),
				lastCmdFailed(2),
				executing(3),
				execute(4)
				}
	MAX-ACCESS     read-write
	STATUS         current
	DESCRIPTION
		" Indicates the status of this type of command
			When the command hasn't been excuted,
		        the value is always  zero. 	
		        If want to execute the command , the manager should 
			        set the value to Execute(3)	."
	DEFVAL { 0 }
	::= {zxDslamCommandEntry 3}
zxDslamSystemVersion OBJECT-TYPE
	SYNTAX		DisplayString (SIZE (0..64))
	MAX-ACCESS	read-only
	STATUS		current
        DESCRIPTION	"the Dslam System Version of this card."
::= {zxDslamAim 7 }

zxDslamSnmpManagerServerIpAddress OBJECT-TYPE
	SYNTAX		IpAddress
	MAX-ACCESS	read-write
	STATUS		current
        DESCRIPTION	"The IpAddress of the Snmp Manager Server for Trap."
::= {zxDslamAim 8 }

--Fan Table
zxDslamFanTable  OBJECT-TYPE
     SYNTAX         SEQUENCE OF ZxDslamFanEntry
     MAX-ACCESS     not-accessible
     STATUS         current
     DESCRIPTION
        	"The ZXDslam fan table. "
     ::= {zxDslamAim 9 }

zxDslamFanEntry	    OBJECT-TYPE
     SYNTAX         ZxDslamFanEntry   
     MAX-ACCESS     not-accessible
     STATUS         current
     DESCRIPTION
		"An entry in the ZXDslam fan table  "
     INDEX  {  zxDslamFanIndex }	
     ::= { zxDslamFanTable  1}

ZxDslamFanEntry  ::= SEQUENCE  {
     zxDslamFanIndex		INTEGER ,
     zxDslamFanLastChange	TimeTicks ,
     zxDslamFanOperStatus	    INTEGER
  }
	
zxDslamFanIndex		OBJECT-TYPE
        SYNTAX          INTEGER
        MAX-ACCESS     not-accessible
	STATUS         current
	DESCRIPTION
		" The Identifier of the fan."
	::= { zxDslamFanEntry	1}
	

zxDslamFanLastChange	OBJECT-TYPE
	SYNTAX         TimeTicks
	MAX-ACCESS     read-only
	STATUS         current
	DESCRIPTION
		  "The value of MIB-II's sysUpTime at the time this
                   entry changes.	When the fan hasn't been changed,
	           the value is always  zero. " 
          ::= { zxDslamFanEntry	2 }

zxDslamFanOperStatus	    OBJECT-TYPE
        SYNTAX    INTEGER 	{	
         	               up(1),
         	               down(2)
				}
	MAX-ACCESS     read-only
	STATUS         current
	DESCRIPTION
		" Indicates the status of this fan."
	DEFVAL { 2 }
	::= {zxDslamFanEntry 3}
zxDslamFanNumber OBJECT-TYPE
        SYNTAX	INTEGER
        MAX-ACCESS read-only
        STATUS  current
        DESCRIPTION	"The  fan number of ZX Dslam "
        DEFVAL {6}
  ::= {zxDslamAim  10}
  
zxDslamPowerTable OBJECT-TYPE
     SYNTAX         SEQUENCE OF ZxDslamPowerEntry  
     MAX-ACCESS     not-accessible
     STATUS         current
     DESCRIPTION
        	"The ZXDslam power table. "
     ::= {zxDslamAim 11 }

zxDslamPowerEntry   OBJECT-TYPE
     SYNTAX         ZxDslamPowerEntry   
     MAX-ACCESS     not-accessible
     STATUS         current
     DESCRIPTION
		"An entry in the ZXDslam Power table  "
     INDEX  {  zxDslamPowerIndex }  
     ::= { zxDslamPowerTable  1}

ZxDslamPowerEntry  ::= SEQUENCE  {    
     zxDslamPowerIndex		INTEGER ,
     zxDslamPowerLastChange	TimeTicks ,
     zxDslamPowerOperStatus	INTEGER
  }
	
zxDslamPowerIndex	OBJECT-TYPE
        SYNTAX          INTEGER
        MAX-ACCESS      not-accessible
	STATUS          current
	DESCRIPTION
		" The Identifier of the power."
	::= { zxDslamPowerEntry	1}
	

zxDslamPowerLastChange	OBJECT-TYPE
	SYNTAX         TimeTicks
	MAX-ACCESS     read-only
	STATUS         current
	DESCRIPTION
		  "The value of MIB-II's sysUpTime at the time this
                   power changes. When the power hasn't been changed,
	           the value is always  zero. " 
          ::= { zxDslamPowerEntry 2 }

  zxDslamPowerOperStatus		OBJECT-TYPE 
	SYNTAX    INTEGER  {	
				up(1), 
	 			down(2) 
			   } 
	MAX-ACCESS     read-only 
	STATUS         current 
	DESCRIPTION 
		"Indicates the status of this power." 
	DEFVAL { down } 
	::= {zxDslamPowerEntry 3}
	
    zxDslamPowerNumber OBJECT-TYPE         
	SYNTAX		INTEGER 
	MAX-ACCESS 	read-only
  	STATUS  	current 
	DESCRIPTION	
		"The  Power number of ZX Dslam " 
	DEFVAL {2} 
	::={zxDslamAim  12}
  

    zxDslamifTable        OBJECT-TYPE
       SYNTAX      SEQUENCE OF ZxDslamIfEntry
       MAX-ACCESS  not-accessible
       STATUS      current
       DESCRIPTION
               "A list of interface entries for sdh interface(ifType = ifType = VAL_ifType_sonet ,
                VAL_ifType_sonetPath).  This table contains additional objects for the interface table of sdh interface."
       ::= { zxDslamAim 13 }

     zxDslamifEntry        OBJECT-TYPE
       SYNTAX      ZxDslamIfEntry
       MAX-ACCESS  not-accessible
       STATUS      current
       DESCRIPTION
               "An entry containing additional management information
               applicable to a sdh 155M interface."
       AUGMENTS    { ifEntry }
       ::= { zxDslamifTable 1 }
       
      ZxDslamIfEntry  ::= SEQUENCE  {    
        zxDslamIfTxOperStatus	INTEGER,
        zxDslamIfRxOperStatus	INTEGER
      }
     
      zxDslamIfTxOperStatus OBJECT-TYPE
         SYNTAX  INTEGER {
                   up(1),        -- ready to pass packets
                   down(2),
                   testing(3)   -- in some test mode
               }
        MAX-ACCESS  read-only
        STATUS      current
        DESCRIPTION
               "The current Tx direction operational state of the sdh  interface.
               If sdh interface recieve LRDI or PRDI signal ,it will change to be down"
        ::= { zxDslamifEntry 1 }
       
      zxDslamIfRxOperStatus OBJECT-TYPE
        SYNTAX  INTEGER {
                   up(1),        -- ready to pass packets
                   down(2),
                   testing(3)   -- in some test mode
               }
       MAX-ACCESS  read-only
       STATUS      current
       DESCRIPTION
               "The current rx direction operational state of the sdh  interface.
               if sdh interface can't receive the signal from its peer(LOS) , it will 
               change to be down "
       ::= { zxDslamifEntry 2 }
       
    zxDslamConfigureDataSynStatus     OBJECT-TYPE
       SYNTAX      INTEGER{
                    outOfSyn(1),
                    synchronizing(2),
                    inSyn(3)
       }
       MAX-ACCESS  read-only
       STATUS      current
       DESCRIPTION
       "1 sigle core running,it's value is outOfSyn(1)
        2 when tow core running ,synchronizing(2) means starting syn
        3 when syn completed ,the value changes to be inSyn(3)"
        
       ::= { zxDslamAim 14 }     

      zxDslamNetWorkUserNum     OBJECT-TYPE
       SYNTAX      INTEGER
       MAX-ACCESS  read-only
       STATUS      current
       DESCRIPTION
       "stat the networks usr number "      
       ::= { zxDslamAim 15 }  
       

      zxDslamLinkupNumTable     OBJECT-TYPE
       SYNTAX      SEQUENCE OF ZxDslamLinkupNumEntry
       MAX-ACCESS  not-accessible
       STATUS      current
       DESCRIPTION
       "The linkup-num of adsl users "      
       ::= { zxDslamAim 16 }      
       
       zxDslamLinkupNumEntry        OBJECT-TYPE
       SYNTAX      ZxDslamLinkupNumEntry
       MAX-ACCESS  not-accessible
       STATUS      current
       DESCRIPTION
               "An Entry of linkup-num of adsl users "    
       INDEX  { ifIndex }  
       ::= { zxDslamLinkupNumTable 1 }
       
      ZxDslamLinkupNumEntry  ::= SEQUENCE  {    
        zxDslamLinkupNum	INTEGER
      }
     
      zxDslamLinkupNum OBJECT-TYPE
         SYNTAX  INTEGER 
        MAX-ACCESS  read-write
        STATUS      current
        DESCRIPTION
               "linkup num of a port"
        ::= { zxDslamLinkupNumEntry 1 }
       

 

  zxDslamCommonLoadTftpAddress OBJECT-TYPE
        SYNTAX IpAddress
        MAX-ACCESS read-write
        STATUS current
        DESCRIPTION
            "DURABLE:
             The IP Address for the TFTP server used for downloading
             and/or uploading files." 
        ::= { zxDslamCommonLoad 1 }

    zxDslamCommonLoadTftpFileName OBJECT-TYPE
        SYNTAX DisplayString (SIZE (1..64))
        MAX-ACCESS read-write
        STATUS current
        DESCRIPTION
            "DURABLE:
             The TFTP file path and name."
        ::= { zxDslamCommonLoad 2 }
        
    
    zxDslamCommonLoadExecuteStatus OBJECT-TYPE
        SYNTAX INTEGER {
               notStarted(1),       -- download has not yet started
               inProgress(2),       -- download has not yet finished
               success(3),          -- download has finished successfully
               errorConnection(4),  -- download cannot connect
               errorFilename(5),    -- download has bad image path/filename
               errorFault(6)        -- download has fault condition on device
        }
        MAX-ACCESS read-only 
        STATUS current
        DESCRIPTION
            "Provides status on the execute file load progress."
        ::= { zxDslamCommonLoad 3 }
      
   zxDslamCommonVerInforTable   OBJECT-TYPE
        SYNTAX SEQUENCE OF ZxDslamCommonVerInforEntry
        MAX-ACCESS not-accessible
        STATUS current
        DESCRIPTION
            "A table of version information in flash."
        ::= { zxDslamCommonVer 1 }

    zxDslamCommonVerInforEntry OBJECT-TYPE
        SYNTAX ZxDslamCommonVerInforEntry
        MAX-ACCESS not-accessible
        STATUS current
        DESCRIPTION
            "A list of version in flash."
        INDEX { zxDslamCommonVerIndex }
        ::= { zxDslamCommonVerInforTable 1 }

    ZxDslamCommonVerInforEntry ::= SEQUENCE {
        zxDslamCommonVerIndex           INTEGER,
        zxDslamCommonVersion            DisplayString,
        zxDslamCommonVerFileName        DisplayString,
        zxDslamCommonVerReleaseDate     DisplayString,
        zxDslamCommonVerCurrStatus      INTEGER
    }
    zxDslamCommonVerIndex  OBJECT-TYPE
        SYNTAX         INTEGER
        MAX-ACCESS  not-accessible
        STATUS current
        DESCRIPTION 
             "The index of version in flash"  
        ::= { zxDslamCommonVerInforEntry 1 }     
        
    zxDslamCommonVersion  OBJECT-TYPE
        SYNTAX         DisplayString(SIZE(1..32))
        MAX-ACCESS     read-only
        STATUS current
        DESCRIPTION 
             "The number of version in flash"  
        ::= { zxDslamCommonVerInforEntry 2 }                  
    zxDslamCommonVerFileName  OBJECT-TYPE
        SYNTAX         DisplayString(SIZE(1..32))
        MAX-ACCESS     read-only
        STATUS current
        DESCRIPTION 
             "The  file name of version in flash"  
        ::= { zxDslamCommonVerInforEntry 3 }
        
   zxDslamCommonVerReleaseDate   OBJECT-TYPE
        SYNTAX         DisplayString(SIZE(1..32))
        MAX-ACCESS     read-only
        STATUS current
        DESCRIPTION 
             "The release date of version in flash"  
        ::= { zxDslamCommonVerInforEntry 4 }                  
        
   zxDslamCommonVerCurrStatus  OBJECT-TYPE
        SYNTAX         INTEGER
                       {
                          notAvailable(0), 
                          running(1),
                          backup(2)
                       }
        MAX-ACCESS     read-only
        STATUS current
        DESCRIPTION 
             "The current status of version in flash"  
        ::= { zxDslamCommonVerInforEntry 5 }   


zxDslamCommonDataFtpAddress OBJECT-TYPE
        SYNTAX IpAddress
        MAX-ACCESS read-write
        STATUS current
        DESCRIPTION
            "DURABLE:
             The IP Address for the TFTP server used for downloading
             and/or uploading files." 
        ::= { zxDslamCommonData 1 }

   zxDslamCommonDataTableIndex OBJECT-TYPE
        SYNTAX INTEGER { 
		ifTable(1),
		adslLineTable (2),
		adslLineConfProfileTable(3),
		adslLineAlarmConfProfileTable(4),
		adslAtucChanTable(5),
		adslAturChanTable(6),
		adslAtucPhysTable(7),
		adslAturPhysTable(8),
		atmTrafficDescrParamTable(9),
		atmVclTable(10),
		atmVcCrossConnectTable(11),
		zxDslamVcxSubscriberMappingTable(12),
		zxDslamCardTable(13),
		zxDslamPortIfIndexMappingTable(14),
		hdsl2ShdslSpanConfTable(15),
		hdsl2ShdslSpanConfProfileTable(16),
        hdsl2ShdslEndpointAlarmConfProfileTable(17),
        hdsl2ShdslEndpointConfTable(18),

		adslflash(19),
		systemflash(20),
		atmflash(21),
		shdslflash(22),
		wanbflash(23),

        wanedata(24),
        waneconfig(25),

        imaadata(26),
        imaaconfig(27),

        imabdata(28),
        imabconfig(29),

        lanadata(30),
        lanaconfig(31),

        wanddata(32),
        wandconfig(33),

        wandbdata(34),
        wandbconfig(35)
        
               }
        MAX-ACCESS read-write
        STATUS current
        DESCRIPTION
            " Table Index."
    ::= { zxDslamCommonData 2 }


    zxDslamCommonDataFtpFilePath OBJECT-TYPE
        SYNTAX DisplayString (SIZE (1..64))
        MAX-ACCESS read-write
        STATUS current
        DESCRIPTION
            "
             The FTP File Path."
        ::= { zxDslamCommonData 3 }

    zxDslamCommonDataFtpUserName OBJECT-TYPE
        SYNTAX DisplayString (SIZE (1..64))
        MAX-ACCESS read-write
        STATUS current
        DESCRIPTION
            "The FTP username."
    ::= { zxDslamCommonData 4 }
    
    zxDslamCommonDataFtpUserPassword OBJECT-TYPE
        SYNTAX DisplayString (SIZE (1..64))
        MAX-ACCESS read-write
        STATUS current
        DESCRIPTION
            "
             The FTP User Password."
    ::= { zxDslamCommonData 5 }

    zxDslamCommonDataFtpFileName OBJECT-TYPE
        SYNTAX DisplayString (SIZE (1..64))
        MAX-ACCESS read-write
        STATUS current
        DESCRIPTION
            "
             The FTP file path and name."
    ::= { zxDslamCommonData 6 }

   zxDslamCommonDataExecuteStatus OBJECT-TYPE
        SYNTAX INTEGER { 
               notStarted(1),       -- download has not yet started
               inProgress(2),       -- download has not yet finished
               success(3),          -- download has finished successfully
               errorConnection(4),  -- download cannot connect
               errorFilename(5),    -- download has bad image path/filename
               errorFault(6) ,       -- download has fault condition on device
               errorUsername(7),    -- 
               errorUserPassword(8) --
               }
        MAX-ACCESS read-only
        STATUS current
        DESCRIPTION
            "  operatioanl status."
    ::= { zxDslamCommonData 7 }
               
-- zxDslamGroup subtree 
--This sub tree is for group operation. operations is: 
	--creatPvcGroup(9)
	--deletePvcAll(10)
	--disablePvcGroup(11)
	--enablePvcGroup(12)
	--setLinGroup(13)
	--enableLinGroup(14)
	--disableLinGroup(15)
	--setAlamGroup(16)

	zxDslamFromAtucCard	OBJECT-TYPE
		SYNTAX		INTEGER (1..34)
		MAX-ACCESS	read-write
		STATUS		current
		DESCRIPTION	"The number of ATUC card to config from"
		::= { zxDslamGroup 1 }

	zxDslamToAtucCard	OBJECT-TYPE
		SYNTAX		INTEGER (1..34)
		MAX-ACCESS	read-write
		STATUS		current
		DESCRIPTION	"The number of ATUC card to config last"
		::= { zxDslamGroup 2 }


	zxDslamAtucVpi	OBJECT-TYPE
		SYNTAX		INTEGER (0..255)
		MAX-ACCESS	read-write
		STATUS		current
		DESCRIPTION	"The vpi created for ATUC card"
		::= { zxDslamGroup 3 }


	zxDslamFromAtucVci	OBJECT-TYPE
		SYNTAX		INTEGER (32..65535)
		MAX-ACCESS	read-write
		STATUS		current
		DESCRIPTION	"The vci created from for ATUC card"
		::= { zxDslamGroup 4 }

	zxDslamAtucVcxNum	OBJECT-TYPE
		SYNTAX		INTEGER (1..65535)
		MAX-ACCESS	read-write
		STATUS		current
		DESCRIPTION	"The number of VCXs of every port "
		::= { zxDslamGroup 5 }

	zxDslamVclTrafficIndex	OBJECT-TYPE
		SYNTAX		INTEGER (1..20)
		MAX-ACCESS	read-write
		STATUS		current
		DESCRIPTION	"The vcl traffic index "
		::= { zxDslamGroup 6 }

	zxDslamWanPort	OBJECT-TYPE
		SYNTAX		INTEGER (1..2)
		MAX-ACCESS	read-write
		STATUS		current
		DESCRIPTION	"port numer for WANE/WANA card "
		::= { zxDslamGroup 7 }


	zxDslamFromWanVpi	OBJECT-TYPE
		SYNTAX		INTEGER (0..255)
		MAX-ACCESS	read-write
		STATUS		current
		DESCRIPTION	"The vpi created from for WANE/WANA card"
		::= { zxDslamGroup 8 }

	zxDslamToWanVpi	OBJECT-TYPE
		SYNTAX		INTEGER (0..255)
		MAX-ACCESS	read-write
		STATUS		current
		DESCRIPTION	"The vpi created last for WANE/WANA card"
		::= { zxDslamGroup 9 }

	zxDslamFromWanVci	OBJECT-TYPE
		SYNTAX		INTEGER (0..65535)
		MAX-ACCESS	read-write
		STATUS		current
		DESCRIPTION	"The vci created from for WANE/WANA card"
		::= { zxDslamGroup 10 }

	zxDslamToWanVci	OBJECT-TYPE
		SYNTAX		INTEGER (0..65535)
		MAX-ACCESS	read-write
		STATUS		current
		DESCRIPTION	"The vci created last for WANE/WANA card"
		::= { zxDslamGroup 11 }

	zxDslamAtucVcxName	OBJECT-TYPE
		SYNTAX		DisplayString (SIZE (0..100))
		MAX-ACCESS	read-write
		STATUS		current
		DESCRIPTION	"The name head of VCX "
		::= { zxDslamGroup 12 }

	zxDslamLineCoding	OBJECT-TYPE
		SYNTAX		INTEGER {
					gdmt (2),
					glite(5)
					}
		MAX-ACCESS	read-write
		STATUS		current
		DESCRIPTION	"The type of linecode"
		::= { zxDslamGroup 13 }

	zxDslamLineType	OBJECT-TYPE
		SYNTAX		INTEGER {
					fastOnly(2), 
					interleaveOnly(3)
					}
		MAX-ACCESS	read-write
		STATUS		current
		DESCRIPTION	"The type of linetype"
		::= { zxDslamGroup 14 }


	 	zxDslamAdslLineProfile	OBJECT-TYPE
		SYNTAX		DisplayString (SIZE (0..32))
		MAX-ACCESS	read-write
		STATUS		current
		DESCRIPTION	"A textual string containing profile filename,
		             the file should include the information about
					 ADSL line configration."
		::= { zxDslamGroup 15 }

	 	zxDslamAdslLineAlarmProfile	OBJECT-TYPE
		SYNTAX		DisplayString (SIZE (0..32))
		MAX-ACCESS	read-write
		STATUS		current
		DESCRIPTION	"A textual string containing profile filename,
		             the file should include the information about
					 ADSL line alarm configration."
		::= { zxDslamGroup 16 }
		
		zxDslamLocalCard  OBJECT-TYPE
		SYNTAX		INTEGER (1..2)
		MAX-ACCESS	read-write
		STATUS		current
		DESCRIPTION	"The slot which the WANE card on"
		::= { zxDslamGroup 17 }

--end define zxDslamGroup
         
-- zxDslamTrap 
zxDslamCardUp	NOTIFICATION-TYPE
    OBJECTS   {  zxDslamCardOperStatus }
    STATUS    current
    DESCRIPTION 
		"A cardUp trap signifies that the SNMP agent has detectd 
		that the cardOperStatus object for the card has transitioned 
		out of the down state.This trap indicates that some card has 
		recovered from fault or been inserted into one switch slot"
     ::= { zxDslamTrap 0 1 }

zxDslamCardDown 	NOTIFICATION-TYPE
    OBJECTS   { zxDslamCardOperStatus }
    STATUS    current
    DESCRIPTION	
		"A cardDown trap signifies that the SNMP agent has deected that 
		the cardOperStatus object for the card has transitioned into 
		the down state. This trap indicates that some card has occured 
		fault or been pulled out from one switch slot."
     ::= { zxDslamTrap 0 2 }
     
zxDslamCommandTabStatusLastChange NOTIFICATION-TYPE
    OBJECTS   { zxDslamCommandStatus }
    STATUS    current
    DESCRIPTION	
		"This trap signifies that the SNMP agent has detected that 
		the zxDslamCommandStatus object for the command has been changed."
     ::= { zxDslamTrap 0 3 }

zxDslamCoreStandbyStatusChange NOTIFICATION-TYPE
    OBJECTS   { zxDslamCardstandbyStatus }
    STATUS    current
    DESCRIPTION	
		"This trap signifies that the SNMP agent has detected that the	
		zxDslamCardstandbyStatus object for the core card has been changed."
     ::= { zxDslamTrap 0 4 }
     
zxDslamFanOperStatusChange NOTIFICATION-TYPE
    OBJECTS   { zxDslamFanOperStatus}
    STATUS    current
    DESCRIPTION	
		"This trap signifies that the SNMP agent has detected that the	
		zxDslamFanOperStatus object for the fan has been changed."
     ::= { zxDslamTrap 0 5 }
     
zxDslamPowerOperStatusChange NOTIFICATION-TYPE
    OBJECTS   { zxDslamPowerOperStatus }
    STATUS    current
    DESCRIPTION	
		"This trap signifies that the SNMP agent has detected that the	
		zxDslamPowerOperStatus object for the power has been changed."
     ::= { zxDslamTrap 0 6 }
     
zxDslamConfigureDataSynStatusChange NOTIFICATION-TYPE
    OBJECTS   { zxDslamConfigureDataSynStatus }
    STATUS    current
    DESCRIPTION	
		"This trap signifies that the SNMP agent has detected that the	
		zxDslamCofigureDataSynStatus object for the syn Status has been changed."
     ::= { zxDslamTrap 0 7 }

zxDslamChipDown 	NOTIFICATION-TYPE
    OBJECTS   { zxDslamCardChipsOperStatus }
    STATUS    current
    DESCRIPTION	
		"!A chipDown trap signifies that the SNMP agent has deected that 
		the cardChipsOperStatus object for the card chip has transitioned into 
		the down state. This trap indicates that some card chip has occured 
		fault."
     ::= { zxDslamTrap 0 8 }

zxCsvNmSendToCsvMessage OBJECT-TYPE
     SYNTAX      OCTET STRING (SIZE (1..64))
     MAX-ACCESS  read-write
     STATUS  current
     DESCRIPTION	"The message string which recv from manager and sent to csv"
   ::= {zxCsvCmd  1}
  
 zxCsvCsvSendToNmMessage OBJECT-TYPE
     SYNTAX      OCTET STRING (SIZE (1..64))
     MAX-ACCESS  read-only
     STATUS  current
     DESCRIPTION	"The message string which recv from csv and sent to manager"
   ::= {zxCsvCmd  2}
       
 zxCsvCsvSendToNmNotification  NOTIFICATION-TYPE
     OBJECTS   { zxCsvCsvSendToNmMessage }
     STATUS    current
     DESCRIPTION  "A  zxCsvCsvCommandResponseToNm trap signifies that 
		the SNMP agent has recieved a  msg from Csv and send to manager"
   ::= { zxCsvTrap 0 1 }

END

ZXWANE-MIB DEFINITIONS ::= BEGIN
IMPORTS
        MODULE-IDENTITY, TimeTicks,	OBJECT-TYPE,
		NOTIFICATION-TYPE, enterprises	FROM SNMPv2-SMI
        	InterfaceIndex							FROM IF-MIB;

zte MODULE-IDENTITY
LAST-UPDATED "2703200000Z"
ORGANIZATION ""
CONTACT-INFO ""
DESCRIPTION  "Initial Version"

::= { enterprises 3902 } 
zxDsl	OBJECT IDENTIFIER ::= { zte 1004 }
zxDslam OBJECT IDENTIFIER ::= { zxDsl 1 }
zxWane	OBJECT IDENTIFIER ::= { zxDslam 2 }
zxWaneTrap OBJECT IDENTIFIER ::= { zxWane 1}

-- definition of zxWaneVcl2PortMappingTable

zxWaneVcl2PortMappingTable OBJECT-TYPE
	SYNTAX		SEQUENCE OF ZxWaneVcl2PortMappingEntry
	MAX-ACCESS		not-accessible
	STATUS		current
	DESCRIPTION
		"zxWaneVcl2PortMappingTable  is used to show the mapping from 
		vcl to port."
	::= {zxWane 2 }

zxWaneVcl2PortMappingEntry	OBJECT-TYPE
	SYNTAX		ZxWaneVcl2PortMappingEntry
	MAX-ACCESS		not-accessible
	STATUS		current
	DESCRIPTION
--!!!
		""
	INDEX	{ zxWaneifIndex,zxWaneVclVpi,zxWaneVclVci}
	::= {zxWaneVcl2PortMappingTable 1 }

ZxWaneVcl2PortMappingEntry	::= SEQUENCE {

    	zxWaneifIndex			InterfaceIndex,
        zxWaneVclVpi 		INTEGER,
        zxWaneVclVci 		INTEGER,
        zxWaneBasePort		INTEGER

}


zxWaneifIndex    OBJECT-TYPE
    SYNTAX  InterfaceIndex
    MAX-ACCESS  not-accessible
    STATUS      current
    DESCRIPTION
--!!!
            ""
  ::= {zxWaneVcl2PortMappingEntry 1 } 


zxWaneVclVpi    OBJECT-TYPE
    SYNTAX  INTEGER
    MAX-ACCESS  not-accessible
    STATUS      current
    DESCRIPTION
--!!!
            ""
  ::= {zxWaneVcl2PortMappingEntry 2 } 


zxWaneVclVci    OBJECT-TYPE
    SYNTAX  INTEGER
    MAX-ACCESS  not-accessible
    STATUS      current
    DESCRIPTION
--!!!
            ""
  ::= {zxWaneVcl2PortMappingEntry 3 } 


zxWaneBasePort    OBJECT-TYPE
    SYNTAX  INTEGER
    MAX-ACCESS  read-only
    STATUS      current
    DESCRIPTION
--!!!
            ""
  ::= {zxWaneVcl2PortMappingEntry 4 } 

zxWaneBridgeFloodStatus OBJECT-TYPE
    SYNTAX      INTEGER {
                    noFlood(1),
                    floodAll(2),
                    floodOnlyUnicast(3)
                }
    MAX-ACCESS  read-write
    STATUS      current
    DESCRIPTION
        "When this is floodAll(2),the device will
        flood broadcast frame and unicast frames
        to pvc ports.  When floodOnlyUnicast(3), flood unicast frames
        to pvc ports.When noFlood(1),the device will not flood any frames."
        
    DEFVAL      { noFlood}
    ::= { zxWane 3 }
    
    
zxWaneCommandTable        OBJECT-TYPE
     SYNTAX         SEQUENCE OF ZxWaneCommandEntry
     MAX-ACCESS     not-accessible
     STATUS         current
     DESCRIPTION
        	"The ZXWane command Execute table. "
     ::= {zxWane 4}

zxWaneCommandEntry		OBJECT-TYPE
     SYNTAX         ZxWaneCommandEntry
     MAX-ACCESS     not-accessible
     STATUS         current
     DESCRIPTION
		"An entry in the ZXWane command Execute table  "
     INDEX  {  zxWaneCommandType }	
     ::= { zxWaneCommandTable  1}

ZxWaneCommandEntry  ::= SEQUENCE  {
     zxWaneCommandType		INTEGER ,
     zxWaneCommandLastChange	TimeTicks ,
     zxWaneCommandStatus	INTEGER
  }
	
zxWaneCommandType	OBJECT-TYPE
     SYNTAX      INTEGER {	
        saveWanedb(1)
	}
	MAX-ACCESS     read-only
	STATUS         current
	DESCRIPTION
			" The operation type of the commands."
	::= { zxWaneCommandEntry	1}
	

zxWaneCommandLastChange	OBJECT-TYPE
	SYNTAX         TimeTicks
	MAX-ACCESS     read-only
	STATUS         current
	DESCRIPTION
		  "The value of MIB-II's sysUpTime at the time this
                   Command is excuted.	When the command hasn't been excuted,
	           the value is always  zero. " 
          ::= { zxWaneCommandEntry	2 }

zxWaneCommandStatus		OBJECT-TYPE
        SYNTAX    INTEGER 	{	
         			cmdNeverExecuted(0),
 				lastCmdSuccessfulExecuted(1),
				lastCmdFailed(2),
				executing(3),
				execute(4)
				}
	MAX-ACCESS     read-write
	STATUS         current
	DESCRIPTION
		" Indicates the status of this type of command
			When the command hasn't been excuted,
		        the value is always  zero. 	
		        If want to execute the command , the manager should 
			        set the value to Execute(3)	."
	DEFVAL { 0 }
	::= {zxWaneCommandEntry 3}

zxWaneIGMPSnoopEnabled        OBJECT-TYPE
     SYNTAX         INTEGER {
			enabled(1),
			disabled(2)
			}
     MAX-ACCESS     read-write
     STATUS         current
     DESCRIPTION
        	"Setting this object to (1) enables IGMP Snooping.  Setting
                 it to (2) disables IGMP Snooping."
     ::= {zxWane 5}

zxWaneIgmpSnoopAging        OBJECT-TYPE
     SYNTAX         INTEGER (30..3600)
     MAX-ACCESS     read-write
     STATUS         current
     DESCRIPTION
        	"The timeout period in seconds for aging out Multicast Groups
                 dynamically learned with IGMP Snooping."
     ::= {zxWane 6}
     
zxWaneVersion       OBJECT-TYPE
     SYNTAX         INTEGER
     MAX-ACCESS     read-only
     STATUS         current
     DESCRIPTION
        	"The WANE Version Number"
     ::= {zxWane 7}

-- zxWaneTrap 
     
zxWaneCommandTabStatusLastChange NOTIFICATION-TYPE
    OBJECTS   { zxWaneCommandStatus }
    STATUS    current
    DESCRIPTION	"This trap signifies that the SNMP agent has detected that the	
			zxWaneCommandStatus object for the command has been changed."
     ::= { zxWaneTrap 0 1 }


END




-- Changes to rfc1493 (Bridge MIB):
--      No changes needed.
-- dperkins@scruznet.com


BRIDGE-MIB DEFINITIONS ::= BEGIN

          IMPORTS
                     Counter, TimeTicks
                             FROM RFC1155-SMI
                     mib-2
                             FROM RFC1213-MIB
                     OBJECT-TYPE
                             FROM RFC-1212
                     TRAP-TYPE
                             FROM RFC-1215;

          -- All representations of MAC addresses in this MIB Module
          -- use, as a textual convention (i.e. this convention does
          -- not affect their encoding), the data type:

          MacAddress ::= OCTET STRING (SIZE (6))    -- a 6 octet address
                                                    -- in the
                                                    -- "canonical"
                                                    -- order
          -- defined by IEEE 802.1a, i.e., as if it were transmitted
          -- least significant bit first, even though 802.5 (in
          -- contrast to other n802.x protocols) requires MAC
          -- addresses to be transmitted most significant bit first.
          --
          -- 16-bit addresses, if needed, are represented by setting
          -- their upper 4 octets to all 0's, i.e., AAFF would be
          -- represented as 00000000AAFF.

          -- Similarly, all representations of Bridge-Id in this MIB
          -- Module use, as a textual convention (i.e. this
          -- convention does not affect their encoding), the data
          -- type:

          BridgeId ::= OCTET STRING (SIZE (8))   -- the
                                                 -- Bridge-Identifier
                                                 -- as used in the
                                                 -- Spanning Tree

          -- Protocol to uniquely identify a bridge.  Its first two
          -- octets (in network byte order) contain a priority
          -- value and its last 6 octets contain the MAC address
          -- used to refer to a bridge in a unique fashion
          -- (typically, the numerically smallest MAC address
          -- of all ports on the bridge).


          -- Several objects in this MIB module represent values of
          -- timers used by the Spanning Tree Protocol.  In this
          -- MIB, these timers have values in units of hundreths of
          -- a second (i.e. 1/100 secs).
          -- These timers, when stored in a Spanning Tree Protocol's
          -- BPDU, are in units of 1/256 seconds.  Note, however,
          -- that 802.1D-1990 specifies a settable granularity of
          -- no more than 1 second for these timers.  To avoid
          -- ambiguity, a data type is defined here as a textual
          -- convention and all representation of these timers
          -- in this MIB module are defined using this data type.  An
          -- algorithm is also defined for converting between the
          -- different units, to ensure a timer's value is not
          -- distorted by multiple conversions.
          -- The data type is:

          Timeout ::= INTEGER -- a STP timer in units of 1/100 seconds

          -- To convert a Timeout value into a value in units of
          -- 1/256 seconds, the following algorithm should be used:
          --
          --      b  = floor( (n * 256) / 100)
          --
          -- where:
          --      floor   =  quotient [ignore remainder]
          --      n is the value in 1/100 second units
          --      b is the value in 1/256 second units
          --
          -- To convert the value from 1/256 second units back to
          -- 1/100 seconds, the following algorithm should be used:
          --
          --      n = ceiling( (b * 100) / 256)
          --
          -- where:
          --      ceiling =  quotient [if remainder is 0], or
          --                 quotient + 1 [if remainder is non-zero]
          --      n is the value in 1/100 second units
          --      b is the value in 1/256 second units
          --
          -- Note: it is important that the arithmetic operations are
          -- done in the order specified (i.e., multiply first, divide
          -- second).

             dot1dBridge   OBJECT IDENTIFIER ::= { mib-2 17 }


          -- groups in the Bridge MIB

          dot1dBase     OBJECT IDENTIFIER ::= { dot1dBridge 1 }

          dot1dStp      OBJECT IDENTIFIER ::= { dot1dBridge 2 }

          dot1dSr       OBJECT IDENTIFIER ::= { dot1dBridge 3 }
          -- separately documented

          dot1dTp       OBJECT IDENTIFIER ::= { dot1dBridge 4 }

          dot1dStatic   OBJECT IDENTIFIER ::= { dot1dBridge 5 }

          -- the dot1dBase group

          -- Implementation of the dot1dBase group is mandatory for all
          -- bridges.

          dot1dBaseBridgeAddress OBJECT-TYPE
              SYNTAX  MacAddress
              ACCESS  read-only
              STATUS  mandatory
              DESCRIPTION
                      "The MAC address used by this bridge when it must
                      be referred to in a unique fashion.   It is
                      recommended that this be the numerically smallest
                      MAC address of all ports that belong to this
                      bridge.  However it is only required to be unique.
                      When concatenated with dot1dStpPriority a unique
                      BridgeIdentifier is formed which is used in the
                      Spanning Tree Protocol."
              REFERENCE
                      "IEEE 802.1D-1990: Sections 6.4.1.1.3 and 3.12.5"
              ::= { dot1dBase 1 }

          dot1dBaseNumPorts OBJECT-TYPE
              SYNTAX  INTEGER
              ACCESS  read-only
              STATUS  mandatory
              DESCRIPTION
                      "The number of ports controlled by this bridging
                      entity."
              REFERENCE
                      "IEEE 802.1D-1990: Section 6.4.1.1.3"
              ::= { dot1dBase 2 }

          dot1dBaseType OBJECT-TYPE
              SYNTAX  INTEGER {
                          unknown(1),
                          transparent-only(2),
                          sourceroute-only(3),
                          srt(4)
                      }
              ACCESS  read-only
              STATUS  mandatory
              DESCRIPTION
                      "Indicates what type of bridging this bridge can
                      perform.  If a bridge is actually performing a
                      certain type of bridging this will be indicated by
                      entries in the port table for the given type."
              ::= { dot1dBase 3 }

          -- The Generic Bridge Port Table

          dot1dBasePortTable OBJECT-TYPE
              SYNTAX  SEQUENCE OF Dot1dBasePortEntry
              ACCESS  not-accessible
              STATUS  mandatory
              DESCRIPTION
                      "A table that contains generic information about
                      every port that is associated with this bridge.
                      Transparent, source-route, and srt ports are
                      included."
              ::= { dot1dBase 4 }

          dot1dBasePortEntry OBJECT-TYPE
              SYNTAX  Dot1dBasePortEntry
              ACCESS  not-accessible
              STATUS  mandatory
              DESCRIPTION
                      "A list of information for each port of the
                      bridge."
              REFERENCE
                      "IEEE 802.1D-1990: Section 6.4.2, 6.6.1"
              INDEX  { dot1dBasePort }
              ::= { dot1dBasePortTable 1 }

          Dot1dBasePortEntry ::=
              SEQUENCE {
                  dot1dBasePort
                      INTEGER,
                  dot1dBasePortIfIndex
                      INTEGER,
                  dot1dBasePortCircuit
                      OBJECT IDENTIFIER,
                  dot1dBasePortDelayExceededDiscards
                      Counter,
                  dot1dBasePortMtuExceededDiscards
                      Counter
              }

          dot1dBasePort OBJECT-TYPE
              SYNTAX  INTEGER (1..65535)
              ACCESS  read-only
              STATUS  mandatory
              DESCRIPTION
                      "The port number of the port for which this entry
                      contains bridge management information."
              ::= { dot1dBasePortEntry 1 }

          dot1dBasePortIfIndex OBJECT-TYPE
              SYNTAX  INTEGER
              ACCESS  read-only
              STATUS  mandatory
              DESCRIPTION
                      "The value of the instance of the ifIndex object,
                      defined in MIB-II, for the interface corresponding
                      to this port."
              ::= { dot1dBasePortEntry 2 }

          dot1dBasePortCircuit OBJECT-TYPE
              SYNTAX  OBJECT IDENTIFIER
              ACCESS  read-only
              STATUS  mandatory
              DESCRIPTION
                      "For a port which (potentially) has the same value
                      of dot1dBasePortIfIndex as another port on the
                      same bridge, this object contains the name of an
                      object instance unique to this port.  For example,
                      in the case where multiple ports correspond one-
                      to-one with multiple X.25 virtual circuits, this
                      value might identify an (e.g., the first) object
                      instance associated with the X.25 virtual circuit
                      corresponding to this port.

                      For a port which has a unique value of
                      dot1dBasePortIfIndex, this object can have the
                      value { 0 0 }."
              ::= { dot1dBasePortEntry 3 }

          dot1dBasePortDelayExceededDiscards OBJECT-TYPE
              SYNTAX  Counter
              ACCESS  read-only
              STATUS  mandatory
              DESCRIPTION
                      "The number of frames discarded by this port due
                      to excessive transit delay through the bridge.  It
                      is incremented by both transparent and source
                      route bridges."
              REFERENCE
                       "IEEE 802.1D-1990: Section 6.6.1.1.3"
              ::= { dot1dBasePortEntry 4 }

          dot1dBasePortMtuExceededDiscards OBJECT-TYPE
              SYNTAX  Counter
              ACCESS  read-only
              STATUS  mandatory
              DESCRIPTION
                      "The number of frames discarded by this port due
                      to an excessive size.  It is incremented by both
                      transparent and source route bridges."
              REFERENCE
                      "IEEE 802.1D-1990: Section 6.6.1.1.3"
              ::= { dot1dBasePortEntry 5 }

          -- the dot1dStp group

          -- Implementation of the dot1dStp group is optional.  It is
          -- implemented by those bridges that support the Spanning Tree
          -- Protocol.

          dot1dStpProtocolSpecification OBJECT-TYPE
              SYNTAX  INTEGER {
                          unknown(1),
                          decLb100(2),
                          ieee8021d(3)
                      }
              ACCESS  read-only
              STATUS  mandatory
              DESCRIPTION
                      "An indication of what version of the Spanning
                      Tree Protocol is being run.  The value
                      'decLb100(2)' indicates the DEC LANbridge 100
                      Spanning Tree protocol.  IEEE 802.1d
                      implementations will return 'ieee8021d(3)'.  If
                      future versions of the IEEE Spanning Tree Protocol
                      are released that are incompatible with the
                      current version a new value will be defined."
              ::= { dot1dStp 1 }

          dot1dStpPriority OBJECT-TYPE
              SYNTAX  INTEGER (0..65535)
              ACCESS  read-write
              STATUS  mandatory
              DESCRIPTION
                      "The value of the write-able portion of the Bridge
                      ID, i.e., the first two octets of the (8 octet
                      long) Bridge ID.  The other (last) 6 octets of the
                      Bridge ID are given by the value of
                      dot1dBaseBridgeAddress."
              REFERENCE
                      "IEEE 802.1D-1990: Section 4.5.3.7"
              ::= { dot1dStp 2 }

          dot1dStpTimeSinceTopologyChange OBJECT-TYPE
              SYNTAX  TimeTicks
              ACCESS  read-only
              STATUS  mandatory
              DESCRIPTION
                      "The time (in hundredths of a second) since the
                      last time a topology change was detected by the
                      bridge entity."
              REFERENCE
                      "IEEE 802.1D-1990: Section 6.8.1.1.3"
              ::= { dot1dStp 3 }

          dot1dStpTopChanges OBJECT-TYPE
              SYNTAX  Counter
              ACCESS  read-only
              STATUS  mandatory
              DESCRIPTION
                      "The total number of topology changes detected by
                      this bridge since the management entity was last
                      reset or initialized."
              REFERENCE
                      "IEEE 802.1D-1990: Section 6.8.1.1.3"
              ::= { dot1dStp 4 }

          dot1dStpDesignatedRoot OBJECT-TYPE
              SYNTAX  BridgeId
              ACCESS  read-only
              STATUS  mandatory
              DESCRIPTION
                      "The bridge identifier of the root of the spanning
                      tree as determined by the Spanning Tree Protocol
                      as executed by this node.  This value is used as
                      the Root Identifier parameter in all Configuration
                      Bridge PDUs originated by this node."
              REFERENCE
                      "IEEE 802.1D-1990: Section 4.5.3.1"
              ::= { dot1dStp 5 }

          dot1dStpRootCost OBJECT-TYPE
              SYNTAX  INTEGER
              ACCESS  read-only
              STATUS  mandatory
              DESCRIPTION
                      "The cost of the path to the root as seen from
                      this bridge."
              REFERENCE
                      "IEEE 802.1D-1990: Section 4.5.3.2"
              ::= { dot1dStp 6 }

          dot1dStpRootPort OBJECT-TYPE
              SYNTAX  INTEGER
              ACCESS  read-only
              STATUS  mandatory
              DESCRIPTION
                      "The port number of the port which offers the
                      lowest cost path from this bridge to the root
                      bridge."
              REFERENCE
                      "IEEE 802.1D-1990: Section 4.5.3.3"
              ::= { dot1dStp 7 }

          dot1dStpMaxAge OBJECT-TYPE
              SYNTAX  Timeout
              ACCESS  read-only
              STATUS  mandatory
              DESCRIPTION
                      "The maximum age of Spanning Tree Protocol
                      information learned from the network on any port
                      before it is discarded, in units of hundredths of
                      a second.  This is the actual value that this
                      bridge is currently using."
              REFERENCE
                      "IEEE 802.1D-1990: Section 4.5.3.4"
              ::= { dot1dStp 8 }

          dot1dStpHelloTime OBJECT-TYPE
              SYNTAX  Timeout
              ACCESS  read-only
              STATUS  mandatory
              DESCRIPTION
                      "The amount of time between the transmission of
                      Configuration bridge PDUs by this node on any port
                      when it is the root of the spanning tree or trying
                      to become so, in units of hundredths of a second.
                      This is the actual value that this bridge is
                      currently using."
              REFERENCE
                      "IEEE 802.1D-1990: Section 4.5.3.5"
              ::= { dot1dStp 9 }

          dot1dStpHoldTime OBJECT-TYPE
              SYNTAX  INTEGER
              ACCESS  read-only
              STATUS  mandatory
              DESCRIPTION
                      "This time value determines the interval length
                      during which no more than two Configuration bridge
                      PDUs shall be transmitted by this node, in units
                      of hundredths of a second."
              REFERENCE
                      "IEEE 802.1D-1990: Section 4.5.3.14"
              ::= { dot1dStp 10 }

          dot1dStpForwardDelay OBJECT-TYPE
              SYNTAX  Timeout
              ACCESS  read-only
              STATUS  mandatory
              DESCRIPTION
                      "This time value, measured in units of hundredths
                      of a second, controls how fast a port changes its
                      spanning state when moving towards the Forwarding
                      state.  The value determines how long the port
                      stays in each of the Listening and Learning
                      states, which precede the Forwarding state.  This
                      value is also used, when a topology change has
                      been detected and is underway, to age all dynamic
                      entries in the Forwarding Database.  [Note that
                      this value is the one that this bridge is
                      currently using, in contrast to
                      dot1dStpBridgeForwardDelay which is the value that
                      this bridge and all others would start using
                      if/when this bridge were to become the root.]"
              REFERENCE
                      "IEEE 802.1D-1990: Section 4.5.3.6"
              ::= { dot1dStp 11 }

          dot1dStpBridgeMaxAge OBJECT-TYPE
              SYNTAX  Timeout (600..4000)
              ACCESS  read-write
              STATUS  mandatory
              DESCRIPTION
                      "The value that all bridges use for MaxAge when
                      this bridge is acting as the root.  Note that
                      802.1D-1990 specifies that the range for this
                      parameter is related to the value of
                      dot1dStpBridgeHelloTime. The granularity of this
                      timer is specified by 802.1D-1990 to be 1 second.
                      An agent may return a badValue error if a set is
                      attempted to a value which is not a whole number
                      of seconds."
              REFERENCE
                      "IEEE 802.1D-1990: Section 4.5.3.8"
              ::= { dot1dStp 12 }

          dot1dStpBridgeHelloTime OBJECT-TYPE
              SYNTAX  Timeout (100..1000)
              ACCESS  read-write
              STATUS  mandatory
              DESCRIPTION
                      "The value that all bridges use for HelloTime when
                      this bridge is acting as the root.  The
                      granularity of this timer is specified by 802.1D-
                      1990 to be 1 second.  An agent may return a
                      badValue error if a set is attempted to a value
                      which is not a whole number of seconds."
              REFERENCE
                      "IEEE 802.1D-1990: Section 4.5.3.9"
              ::= { dot1dStp 13 }

          dot1dStpBridgeForwardDelay OBJECT-TYPE
              SYNTAX  Timeout (400..3000)
              ACCESS  read-write
              STATUS  mandatory
              DESCRIPTION
                      "The value that all bridges use for ForwardDelay
                      when this bridge is acting as the root.  Note that
                      802.1D-1990 specifies that the range for this
                      parameter is related to the value of
                      dot1dStpBridgeMaxAge.  The granularity of this
                      timer is specified by 802.1D-1990 to be 1 second.
                      An agent may return a badValue error if a set is
                      attempted to a value which is not a whole number
                      of seconds."
              REFERENCE
                      "IEEE 802.1D-1990: Section 4.5.3.10"
              ::= { dot1dStp 14 }


          -- The Spanning Tree Port Table

          dot1dStpPortTable OBJECT-TYPE
              SYNTAX  SEQUENCE OF Dot1dStpPortEntry
              ACCESS  not-accessible
              STATUS  mandatory
              DESCRIPTION
                      "A table that contains port-specific information
                      for the Spanning Tree Protocol."
              ::= { dot1dStp 15 }

          dot1dStpPortEntry OBJECT-TYPE
              SYNTAX  Dot1dStpPortEntry
              ACCESS  not-accessible
              STATUS  mandatory
              DESCRIPTION
                      "A list of information maintained by every port
                      about the Spanning Tree Protocol state for that
                      port."
              INDEX   { dot1dStpPort }
              ::= { dot1dStpPortTable 1 }

          Dot1dStpPortEntry ::=
              SEQUENCE {
                  dot1dStpPort
                      INTEGER,
                  dot1dStpPortPriority
                      INTEGER,
                  dot1dStpPortState
                      INTEGER,
                  dot1dStpPortEnable
                      INTEGER,
                  dot1dStpPortPathCost
                      INTEGER,
                  dot1dStpPortDesignatedRoot
                      BridgeId,
                  dot1dStpPortDesignatedCost
                      INTEGER,
                  dot1dStpPortDesignatedBridge
                      BridgeId,
                  dot1dStpPortDesignatedPort
                      OCTET STRING,
                  dot1dStpPortForwardTransitions
                      Counter
              }

          dot1dStpPort OBJECT-TYPE
              SYNTAX  INTEGER (1..65535)
              ACCESS  read-only
              STATUS  mandatory
              DESCRIPTION
                      "The port number of the port for which this entry
                      contains Spanning Tree Protocol management
                      information."
              REFERENCE
                      "IEEE 802.1D-1990: Section 6.8.2.1.2"
              ::= { dot1dStpPortEntry 1 }

          dot1dStpPortPriority OBJECT-TYPE
              SYNTAX  INTEGER (0..255)
              ACCESS  read-write
              STATUS  mandatory
              DESCRIPTION
                      "The value of the priority field which is
                      contained in the first (in network byte order)
                      octet of the (2 octet long) Port ID.  The other
                      octet of the Port ID is given by the value of
                      dot1dStpPort."
              REFERENCE
                      "IEEE 802.1D-1990: Section 4.5.5.1"
              ::= { dot1dStpPortEntry 2 }

          dot1dStpPortState OBJECT-TYPE
              SYNTAX  INTEGER {
                          disabled(1),
                          blocking(2),
                          listening(3),
                          learning(4),
                          forwarding(5),
                          broken(6)
                      }
              ACCESS  read-only
              STATUS  mandatory
              DESCRIPTION
                      "The port's current state as defined by
                      application of the Spanning Tree Protocol.  This
                      state controls what action a port takes on
                      reception of a frame.  If the bridge has detected
                      a port that is malfunctioning it will place that
                      port into the broken(6) state.  For ports which
                      are disabled (see dot1dStpPortEnable), this object
                      will have a value of disabled(1)."
              REFERENCE
                      "IEEE 802.1D-1990: Section 4.5.5.2"
              ::= { dot1dStpPortEntry 3 }

          dot1dStpPortEnable OBJECT-TYPE
              SYNTAX  INTEGER {
                          enabled(1),
                          disabled(2)
                      }
              ACCESS  read-write
              STATUS  mandatory
              DESCRIPTION
                      "The enabled/disabled status of the port."
              REFERENCE
                      "IEEE 802.1D-1990: Section 4.5.5.2"
              ::= { dot1dStpPortEntry 4 }

          dot1dStpPortPathCost OBJECT-TYPE
              SYNTAX  INTEGER (1..65535)
              ACCESS  read-write
              STATUS  mandatory
              DESCRIPTION
                      "The contribution of this port to the path cost of
                      paths towards the spanning tree root which include
                      this port.  802.1D-1990 recommends that the
                      default value of this parameter be in inverse
                      proportion to the speed of the attached LAN."
              REFERENCE
                      "IEEE 802.1D-1990: Section 4.5.5.3"
              ::= { dot1dStpPortEntry 5 }

          dot1dStpPortDesignatedRoot OBJECT-TYPE
              SYNTAX  BridgeId
              ACCESS  read-only
              STATUS  mandatory
              DESCRIPTION
                      "The unique Bridge Identifier of the Bridge
                      recorded as the Root in the Configuration BPDUs
                      transmitted by the Designated Bridge for the
                      segment to which the port is attached."
              REFERENCE
                      "IEEE 802.1D-1990: Section 4.5.5.4"
              ::= { dot1dStpPortEntry 6 }

          dot1dStpPortDesignatedCost OBJECT-TYPE
              SYNTAX  INTEGER
              ACCESS  read-only
              STATUS  mandatory
              DESCRIPTION
                      "The path cost of the Designated Port of the
                      segment connected to this port.  This value is
                      compared to the Root Path Cost field in received
                      bridge PDUs."
              REFERENCE
                      "IEEE 802.1D-1990: Section 4.5.5.5"
              ::= { dot1dStpPortEntry 7 }

          dot1dStpPortDesignatedBridge OBJECT-TYPE
              SYNTAX  BridgeId
              ACCESS  read-only
              STATUS  mandatory
              DESCRIPTION
                      "The Bridge Identifier of the bridge which this
                      port considers to be the Designated Bridge for
                      this port's segment."
              REFERENCE
                      "IEEE 802.1D-1990: Section 4.5.5.6"
              ::= { dot1dStpPortEntry 8 }

          dot1dStpPortDesignatedPort OBJECT-TYPE
              SYNTAX  OCTET STRING (SIZE (2))
              ACCESS  read-only
              STATUS  mandatory
              DESCRIPTION
                      "The Port Identifier of the port on the Designated
                      Bridge for this port's segment."
              REFERENCE
                      "IEEE 802.1D-1990: Section 4.5.5.7"
              ::= { dot1dStpPortEntry 9 }

          dot1dStpPortForwardTransitions OBJECT-TYPE
              SYNTAX  Counter
              ACCESS  read-only
              STATUS  mandatory
              DESCRIPTION
                      "The number of times this port has transitioned
                      from the Learning state to the Forwarding state."
              ::= { dot1dStpPortEntry 10 }

          -- the dot1dTp group

          -- Implementation of the dot1dTp group is optional.  It is
          -- implemented by those bridges that support the transparent
          -- bridging mode.  A transparent or SRT bridge will implement
          -- this group.

          dot1dTpLearnedEntryDiscards OBJECT-TYPE
              SYNTAX  Counter
              ACCESS  read-only
              STATUS  mandatory
              DESCRIPTION
                      "The total number of Forwarding Database entries,
                      which have been or would have been learnt, but
                      have been discarded due to a lack of space to
                      store them in the Forwarding Database.  If this
                      counter is increasing, it indicates that the
                      Forwarding Database is regularly becoming full (a
                      condition which has unpleasant performance effects
                      on the subnetwork).  If this counter has a
                      significant value but is not presently increasing,
                      it indicates that the problem has been occurring
                      but is not persistent."
              REFERENCE
                      "IEEE 802.1D-1990: Section 6.7.1.1.3"
              ::= { dot1dTp 1 }

          dot1dTpAgingTime OBJECT-TYPE
              SYNTAX   INTEGER (10..1000000)
              ACCESS   read-write
              STATUS   mandatory
              DESCRIPTION
                      "The timeout period in seconds for aging out
                      dynamically learned forwarding information.
                      802.1D-1990 recommends a default of 300 seconds."
              REFERENCE
                      "IEEE 802.1D-1990: Section 6.7.1.1.3"
              ::= { dot1dTp 2 }

          --  The Forwarding Database for Transparent Bridges

          dot1dTpFdbTable OBJECT-TYPE
              SYNTAX  SEQUENCE OF Dot1dTpFdbEntry
              ACCESS  not-accessible
              STATUS  mandatory
              DESCRIPTION
                      "A table that contains information about unicast
                      entries for which the bridge has forwarding and/or
                      filtering information.  This information is used
                      by the transparent bridging function in
                      determining how to propagate a received frame."
              ::= { dot1dTp 3 }

          dot1dTpFdbEntry OBJECT-TYPE
              SYNTAX  Dot1dTpFdbEntry
              ACCESS  not-accessible
              STATUS  mandatory
              DESCRIPTION
                      "Information about a specific unicast MAC address
                      for which the bridge has some forwarding and/or
                      filtering information."
              INDEX   { dot1dTpFdbAddress }
              ::= { dot1dTpFdbTable 1 }

          Dot1dTpFdbEntry ::=
              SEQUENCE {
                  dot1dTpFdbAddress
                      MacAddress,
                  dot1dTpFdbPort
                      INTEGER,
                  dot1dTpFdbStatus
                      INTEGER
              }

          dot1dTpFdbAddress OBJECT-TYPE
              SYNTAX  MacAddress
              ACCESS  read-only
              STATUS  mandatory
              DESCRIPTION
                      "A unicast MAC address for which the bridge has
                      forwarding and/or filtering information."
              REFERENCE
                      "IEEE 802.1D-1990: Section 3.9.1, 3.9.2"
              ::= { dot1dTpFdbEntry 1 }

          dot1dTpFdbPort OBJECT-TYPE
              SYNTAX  INTEGER
              ACCESS  read-only
              STATUS  mandatory
              DESCRIPTION
                      "Either the value '0', or the port number of the
                      port on which a frame having a source address
                      equal to the value of the corresponding instance
                      of dot1dTpFdbAddress has been seen.  A value of
                      '0' indicates that the port number has not been
                      learned but that the bridge does have some
                      forwarding/filtering information about this
                      address (e.g. in the dot1dStaticTable).
                      Implementors are encouraged to assign the port
                      value to this object whenever it is learned even
                      for addresses for which the corresponding value of
                      dot1dTpFdbStatus is not learned(3)."
              ::= { dot1dTpFdbEntry 2 }

          dot1dTpFdbStatus OBJECT-TYPE
              SYNTAX  INTEGER {
                          other(1),
                          invalid(2),
                          learned(3),
                          self(4),
                          mgmt(5)
                      }
              ACCESS  read-only
              STATUS  mandatory
              DESCRIPTION
                      "The status of this entry.  The meanings of the
                      values are:

                        other(1)   : none of the following.  This would
                                     include the case where some other
                                     MIB object (not the corresponding
                                     instance of dot1dTpFdbPort, nor an
                                     entry in the dot1dStaticTable) is
                                     being used to determine if and how
                                     frames addressed to the value of
                                     the corresponding instance of
                                     dot1dTpFdbAddress are being
                                     forwarded.

                        invalid(2) : this entry is not longer valid
                                     (e.g., it was learned but has since
                                     aged-out), but has not yet been
                                     flushed from the table.

                        learned(3) : the value of the corresponding
                                     instance of dot1dTpFdbPort was
                                     learned, and is being used.

                        self(4)    : the value of the corresponding
                                     instance of dot1dTpFdbAddress
                                     represents one of the bridge's
                                     addresses.  The corresponding
                                     instance of dot1dTpFdbPort
                                     indicates which of the bridge's
                                     ports has this address.

                        mgmt(5)    : the value of the corresponding
                                     instance of dot1dTpFdbAddress is
                                     also the value of an existing
                                     instance of dot1dStaticAddress."
              ::= { dot1dTpFdbEntry 3 }


          --  Port Table for Transparent Bridges

          dot1dTpPortTable OBJECT-TYPE
              SYNTAX  SEQUENCE OF Dot1dTpPortEntry
              ACCESS  not-accessible
              STATUS  mandatory
              DESCRIPTION
                      "A table that contains information about every
                      port that is associated with this transparent
                      bridge."
              ::= { dot1dTp 4 }

          dot1dTpPortEntry OBJECT-TYPE
              SYNTAX  Dot1dTpPortEntry
              ACCESS  not-accessible
              STATUS  mandatory
              DESCRIPTION
                      "A list of information for each port of a
                      transparent bridge."
              INDEX   { dot1dTpPort }
              ::= { dot1dTpPortTable 1 }

          Dot1dTpPortEntry ::=
              SEQUENCE {
                  dot1dTpPort
                      INTEGER,
                  dot1dTpPortMaxInfo
                      INTEGER,
                  dot1dTpPortInFrames
                      Counter,
                  dot1dTpPortOutFrames
                      Counter,
                  dot1dTpPortInDiscards
                      Counter
              }

          dot1dTpPort OBJECT-TYPE
              SYNTAX  INTEGER (1..65535)
              ACCESS  read-only
              STATUS  mandatory
              DESCRIPTION
                      "The port number of the port for which this entry
                      contains Transparent bridging management
                      information."
              ::= { dot1dTpPortEntry 1 }

          -- It would be nice if we could use ifMtu as the size of the
          -- largest INFO field, but we can't because ifMtu is defined
          -- to be the size that the (inter-)network layer can use which
          -- can differ from the MAC layer (especially if several layers
          -- of encapsulation are used).

          dot1dTpPortMaxInfo OBJECT-TYPE
              SYNTAX  INTEGER
              ACCESS  read-only
              STATUS  mandatory
              DESCRIPTION
                      "The maximum size of the INFO (non-MAC) field that
                      this port will receive or transmit."
              ::= { dot1dTpPortEntry 2 }

          dot1dTpPortInFrames OBJECT-TYPE
              SYNTAX  Counter
              ACCESS  read-only
              STATUS  mandatory
              DESCRIPTION
                      "The number of frames that have been received by
                      this port from its segment. Note that a frame
                      received on the interface corresponding to this
                      port is only counted by this object if and only if
                      it is for a protocol being processed by the local
                      bridging function, including bridge management
                      frames."
              REFERENCE
                      "IEEE 802.1D-1990: Section 6.6.1.1.3"
              ::= { dot1dTpPortEntry 3 }

          dot1dTpPortOutFrames OBJECT-TYPE
              SYNTAX  Counter
              ACCESS  read-only
              STATUS  mandatory
              DESCRIPTION
                      "The number of frames that have been transmitted
                      by this port to its segment.  Note that a frame
                      transmitted on the interface corresponding to this
                      port is only counted by this object if and only if
                      it is for a protocol being processed by the local
                      bridging function, including bridge management
                      frames."
              REFERENCE
                      "IEEE 802.1D-1990: Section 6.6.1.1.3"
              ::= { dot1dTpPortEntry 4 }

          dot1dTpPortInDiscards OBJECT-TYPE
              SYNTAX   Counter
              ACCESS   read-only
              STATUS   mandatory
              DESCRIPTION
                      "Count of valid frames received which were
                      discarded (i.e., filtered) by the Forwarding
                      Process."
              REFERENCE
                      "IEEE 802.1D-1990: Section 6.6.1.1.3"
              ::= { dot1dTpPortEntry 5 }

          -- The Static (Destination-Address Filtering) Database

          -- Implementation of this group is optional.

          dot1dStaticTable OBJECT-TYPE
              SYNTAX  SEQUENCE OF Dot1dStaticEntry
              ACCESS  not-accessible
              STATUS  mandatory
              DESCRIPTION
                      "A table containing filtering information
                      configured into the bridge by (local or network)
                      management specifying the set of ports to which
                      frames received from specific ports and containing
                      specific destination addresses are allowed to be
                      forwarded.  The value of zero in this table as the
                      port number from which frames with a specific
                      destination address are received, is used to
                      specify all ports for which there is no specific
                      entry in this table for that particular
                      destination address.  Entries are valid for
                      unicast and for group/broadcast addresses."
              REFERENCE
                      "IEEE 802.1D-1990: Section 6.7.2"
              ::= { dot1dStatic 1 }

          dot1dStaticEntry OBJECT-TYPE
              SYNTAX  Dot1dStaticEntry
              ACCESS  not-accessible
              STATUS  mandatory
              DESCRIPTION
                      "Filtering information configured into the bridge
                      by (local or network) management specifying the
                      set of ports to which frames received from a
                      specific port and containing a specific
                      destination address are allowed to be forwarded."
              REFERENCE
                      "IEEE 802.1D-1990: Section 6.7.2"


              INDEX   { dot1dStaticAddress, dot1dStaticReceivePort }
              ::= { dot1dStaticTable 1 }

          Dot1dStaticEntry ::=
              SEQUENCE {
                  dot1dStaticAddress
                      MacAddress,
                  dot1dStaticReceivePort
                      INTEGER,
                  dot1dStaticAllowedToGoTo
                      OCTET STRING,
                  dot1dStaticStatus
                      INTEGER
              }

          dot1dStaticAddress OBJECT-TYPE
              SYNTAX  MacAddress
              ACCESS  read-write
              STATUS  mandatory
              DESCRIPTION
                      "The destination MAC address in a frame to which
                      this entry's filtering information applies.  This
                      object can take the value of a unicast address, a
                      group address or the broadcast address."
              REFERENCE
                      "IEEE 802.1D-1990: Section 3.9.1, 3.9.2"
              ::= { dot1dStaticEntry 1 }

          dot1dStaticReceivePort OBJECT-TYPE
              SYNTAX  INTEGER
              ACCESS  read-write
              STATUS  mandatory
              DESCRIPTION
                      "Either the value '0', or the port number of the
                      port from which a frame must be received in order
                      for this entry's filtering information to apply.
                      A value of zero indicates that this entry applies
                      on all ports of the bridge for which there is no
                      other applicable entry."
              ::= { dot1dStaticEntry 2 }

          dot1dStaticAllowedToGoTo OBJECT-TYPE
              SYNTAX  OCTET STRING
              ACCESS  read-write
              STATUS  mandatory
              DESCRIPTION
                      "The set of ports to which frames received from a
                      specific port and destined for a specific MAC
                      address, are allowed to be forwarded.  Each octet
                      within the value of this object specifies a set of
                      eight ports, with the first octet specifying ports
                      1 through 8, the second octet specifying ports 9
                      through 16, etc.  Within each octet, the most
                      significant bit represents the lowest numbered
                      port, and the least significant bit represents the
                      highest numbered port.  Thus, each port of the
                      bridge is represented by a single bit within the
                      value of this object.  If that bit has a value of
                      '1' then that port is included in the set of
                      ports; the port is not included if its bit has a
                      value of '0'.  (Note that the setting of the bit
                      corresponding to the port from which a frame is
                      received is irrelevant.)  The default value of
                      this object is a string of ones of appropriate
                      length."
              ::= { dot1dStaticEntry 3 }

          dot1dStaticStatus OBJECT-TYPE
              SYNTAX  INTEGER {
                          other(1),
                          invalid(2),
                          permanent(3),
                          deleteOnReset(4),
                          deleteOnTimeout(5)
                      }
              ACCESS  read-write
              STATUS  mandatory
              DESCRIPTION
                      "This object indicates the status of this entry.
                      The default value is permanent(3).

                           other(1) - this entry is currently in use but
                                the conditions under which it will
                                remain so are different from each of the
                                following values.
                           invalid(2) - writing this value to the object
                                removes the corresponding entry.
                           permanent(3) - this entry is currently in use
                                and will remain so after the next reset
                                of the bridge.
                           deleteOnReset(4) - this entry is currently in
                                use and will remain so until the next
                                reset of the bridge.
                           deleteOnTimeout(5) - this entry is currently
                                in use and will remain so until it is
                                aged out."
              ::= { dot1dStaticEntry 4 }

          -- Traps for use by Bridges

          -- Traps for the Spanning Tree Protocol

          newRoot TRAP-TYPE
              ENTERPRISE  dot1dBridge
              DESCRIPTION
                      "The newRoot trap indicates that the sending agent
                      has become the new root of the Spanning Tree; the
                      trap is sent by a bridge soon after its election
                      as the new root, e.g., upon expiration of the
                      Topology Change Timer immediately subsequent to
                      its election.  Implementation of this trap is
                      optional."
              ::= 1

          topologyChange TRAP-TYPE
              ENTERPRISE  dot1dBridge
              DESCRIPTION
                      "A topologyChange trap is sent by a bridge when
                      any of its configured ports transitions from the
                      Learning state to the Forwarding state, or from
                      the Forwarding state to the Blocking state.  The
                      trap is not sent if a newRoot trap is sent for the
                      same transition.  Implementation of this trap is
                      optional."
              ::= 2

END


--------------------------------------------------------------------------
-- Rfc2674q
--------------------------------------------------------------------------
Q-BRIDGE-MIB DEFINITIONS ::= BEGIN

-- -------------------------------------------------------------
-- MIB for IEEE 802.1Q Devices
-- -------------------------------------------------------------

IMPORTS
    MODULE-IDENTITY, OBJECT-TYPE,
    Counter32, Counter64, Unsigned32, TimeTicks
        FROM SNMPv2-SMI
    RowStatus, TruthValue, TEXTUAL-CONVENTION, MacAddress
        FROM SNMPv2-TC
--    SnmpAdminString
--        FROM SNMP-FRAMEWORK-MIB
--    MODULE-COMPLIANCE, OBJECT-GROUP
--        FROM SNMPv2-CONF
    dot1dBridge, dot1dBasePortEntry, dot1dBasePort
        FROM BRIDGE-MIB;
--    EnabledStatus
--        FROM P-BRIDGE-MIB
--    TimeFilter
--        FROM RMON2-MIB;

qBridgeMIB MODULE-IDENTITY
    LAST-UPDATED "9908250000Z"
    ORGANIZATION "IETF Bridge MIB Working Group"
    CONTACT-INFO
        "       Les Bell
        Postal: 3Com Europe Ltd.
                3Com Centre, Boundary Way
                Hemel Hempstead, Herts. HP2 7YU
                UK
         Phone: +44 1442 438025
         Email: Les_Bell@3Com.com

                Andrew Smith
        Postal: Extreme Networks
                3585 Monroe St.
                Santa Clara CA 95051
                USA
         Phone: +1 408 579 2821
         Email: andrew@extremenetworks.com

                Paul Langille
        Postal: Newbridge Networks
                5 Corporate Drive
                Andover, MA 01810
                USA
         Phone: +1 978 691 4665
         Email: langille@newbridge.com

                Anil Rijhsinghani
        Postal: Cabletron Systems
                50 Minuteman Road
                Andover, MA 01810
                USA
         Phone: +1 978 684 1295
         Email: anil@cabletron.com

                Keith McCloghrie
        Postal: cisco Systems, Inc.
                170 West Tasman Drive
                San Jose, CA 95134-1706
                USA
         Phone: +1 408 526 5260
         Email: kzm@cisco.com"
    DESCRIPTION
        "The VLAN Bridge MIB module for managing Virtual Bridged
        Local Area Networks, as defined by IEEE 802.1Q-1998."

-- revision history

    REVISION     "9908250000Z"
    DESCRIPTION
         "Initial version, published as RFC 2674."

    ::= { dot1dBridge 7 }

qBridgeMIBObjects OBJECT IDENTIFIER ::= { qBridgeMIB 1 }

-- -------------------------------------------------------------
-- Textual Conventions
-- -------------------------------------------------------------
EnabledStatus ::= TEXTUAL-CONVENTION
    STATUS      current
    DESCRIPTION
        "A simple status value for the object."
    SYNTAX      INTEGER { enabled(1), disabled(2) }

TimeFilter ::= TEXTUAL-CONVENTION
    STATUS        current
    DESCRIPTION
        "To be used for the index to a table.  Allows an application
        to download only those rows changed since a particular time.
        A row is considered changed if the value of any object in the
        row changes or if the row is created or deleted.

        When sysUpTime is equal to zero, this table shall be empty.

        One entry exists for each past value of sysUpTime, except that
        the whole table is purged should sysUpTime wrap.

        As this basic row is updated new conceptual rows are created
        (which still share the now updated object values with all
        other instances).  The number of instances which are created
        is determined by the value of sysUpTime at which the basic row
        was last updated.  One instance will exist for each value of
        sysUpTime at the last update time for the row.  A new
        timeMark instance is created for each new sysUpTime value.
        Each new conceptual row will be associated with the timeMark
        instance which was created at the value of sysUpTime with
        which the conceptual row is to be associated.

        By definition all conceptual rows were updated at or after
        time zero and so at least one conceptual row (associated with
        timeMark.0) must exist for each underlying (basic) row.

        See the appendix for further discussion of this variable.

        Consider the following fooTable:

        fooTable ...
        INDEX { fooTimeMark, fooIndex }

        FooEntry {
           fooTimeMark  TimeFilter
           fooIndex     INTEGER,
           fooCounts    Counter
        }

        Should there be two basic rows in this table (fooIndex == 1,
        fooIndex == 2) and row 1 was updated most recently at time 6,
        while row 2 was updated most recently at time 8, and both rows
        had been updated on several earlier occasions such that the
        current values were 5 and 9 respectively then the following
        fooCounts instances would exist.

        fooCounts.0.1  5
        fooCounts.0.2  9
        fooCounts.1.1  5
        fooCounts.1.2  9
        fooCounts.2.1  5
        fooCounts.2.2  9
        fooCounts.3.1  5
        fooCounts.3.2  9
        fooCounts.4.1  5
        fooCounts.4.2  9
        fooCounts.5.1  5
        fooCounts.5.2  9
        fooCounts.6.1  5
        fooCounts.6.2  9
        fooCounts.7.2  9    -- note that row 1 doesn't exist for
        fooCounts.8.2  9    -- times 7 and 8"
    SYNTAX    TimeTicks

   SnmpAdminString ::= TEXTUAL-CONVENTION
       DISPLAY-HINT "255a"
       STATUS       current
       DESCRIPTION "An octet string containing administrative
                    information, preferably in human-readable form.

                    To facilitate internationalization, this
                    information is represented using the ISO/IEC
                    IS 10646-1 character set, encoded as an octet
                    string using the UTF-8 transformation format
                    described in [RFC2044].

                    Since additional code points are added by
                    amendments to the 10646 standard from time
                    to time, implementations must be prepared to
                    encounter any code point from 0x00000000 to
                    0x7fffffff.

                    The use of control codes should be avoided.

                    When it is necessary to represent a newline,
                    the control code sequence CR LF should be used.
                    The use of leading or trailing white space should
                    be avoided.

                    For code points not directly supported by user
                    interface hardware or software, an alternative
                    means of entry and display, such as hexadecimal,
                    may be provided.

                    For information encoded in 7-bit US-ASCII,
                    the UTF-8 encoding is identical to the
                    US-ASCII encoding.

                    Note that when this TC is used for an object that
                    is used or envisioned to be used as an index, then
                    a SIZE restriction must be specified so that the
                    number of sub-identifiers for any object instance
                    does not exceed the limit of 128, as defined by
                    [RFC1905].
                   "
       SYNTAX       OCTET STRING (SIZE (0..255))
       
PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING

VlanIndex ::= TEXTUAL-CONVENTION
    STATUS      current
    DESCRIPTION
        "A value used to index per-VLAN tables: values of 0 and
        4095 are not permitted; if the value is between 1 and
        4094 inclusive, it represents an IEEE 802.1Q VLAN-ID with
        global scope within a given bridged domain (see VlanId
        textual convention).  If the value is greater than 4095
        then it represents a VLAN with scope local to the
        particular agent, i.e. one without a global VLAN-ID
        assigned to it. Such VLANs are outside the scope of
        IEEE 802.1Q but it is convenient to be able to manage them
        in the same way using this MIB."
    SYNTAX      Unsigned32

VlanId ::= TEXTUAL-CONVENTION
    STATUS      current
    DESCRIPTION
        "A 12-bit VLAN ID used in the VLAN Tag header."
    SYNTAX      INTEGER (1..4094)

-- -------------------------------------------------------------
-- groups in the Q-BRIDGE MIB
-- -------------------------------------------------------------

dot1qBase       OBJECT IDENTIFIER ::= { qBridgeMIBObjects 1 }
dot1qTp         OBJECT IDENTIFIER ::= { qBridgeMIBObjects 2 }
dot1qStatic     OBJECT IDENTIFIER ::= { qBridgeMIBObjects 3 }
dot1qVlan       OBJECT IDENTIFIER ::= { qBridgeMIBObjects 4 }

-- -------------------------------------------------------------

-- -------------------------------------------------------------
-- dot1qBase group
-- -------------------------------------------------------------

dot1qVlanVersionNumber OBJECT-TYPE
    SYNTAX      INTEGER {
                    version1(1)
                }
    MAX-ACCESS  read-only
    STATUS      current
    DESCRIPTION
        "The version number of IEEE 802.1Q that this device
        supports."
    REFERENCE
        "IEEE 802.1Q/D11 Section 12.10.1.1"
    ::= { dot1qBase 1 }

dot1qMaxVlanId OBJECT-TYPE
    SYNTAX      VlanId
    MAX-ACCESS  read-only
    STATUS      current
    DESCRIPTION
        "The maximum IEEE 802.1Q VLAN ID that this device
        supports."
    REFERENCE
        "IEEE 802.1Q/D11 Section 9.3.2.3"
    ::= { dot1qBase 2 }

dot1qMaxSupportedVlans OBJECT-TYPE
    SYNTAX      Unsigned32
    MAX-ACCESS  read-only
    STATUS      current
    DESCRIPTION
        "The maximum number of IEEE 802.1Q VLANs that this
        device supports."
    REFERENCE
        "IEEE 802.1Q/D11 Section 12.10.1.1"
    ::= { dot1qBase 3 }

dot1qNumVlans OBJECT-TYPE
    SYNTAX      Unsigned32
    MAX-ACCESS  read-only
    STATUS      current
    DESCRIPTION
        "The current number of IEEE 802.1Q VLANs that are
        configured in this device."
    REFERENCE
        "IEEE 802.1Q/D11 Section 12.7.1.1"
    ::= { dot1qBase 4 }

dot1qGvrpStatus OBJECT-TYPE
    SYNTAX      EnabledStatus
    MAX-ACCESS  read-write
    STATUS      current
    DESCRIPTION
        "The administrative status requested by management for
        GVRP.  The value enabled(1) indicates that GVRP should
        be enabled on this device, on all ports for which it has
        not been specifically disabled.  When disabled(2), GVRP
        is disabled on all ports and all GVRP packets will be
        forwarded transparently.  This object affects all GVRP
        Applicant and Registrar state machines.  A transition
        from disabled(2) to enabled(1) will cause a reset of all
        GVRP state machines on all ports."
    DEFVAL      { enabled }
    ::= { dot1qBase 5 }

-- -------------------------------------------------------------
-- the dot1qTp group
-- -------------------------------------------------------------

-- -------------------------------------------------------------
-- the current Filtering Database Table
-- -------------------------------------------------------------

dot1qFdbTable OBJECT-TYPE
    SYNTAX      SEQUENCE OF Dot1qFdbEntry
    MAX-ACCESS  not-accessible
    STATUS      current
    DESCRIPTION
        "A table that contains configuration and control
        information for each Filtering Database currently
        operating on this device.  Entries in this table appear
        automatically when VLANs are assigned FDB IDs in the
        dot1qVlanCurrentTable."
    ::= { dot1qTp 1 }

dot1qFdbEntry OBJECT-TYPE
    SYNTAX      Dot1qFdbEntry
    MAX-ACCESS  not-accessible
    STATUS      current
    DESCRIPTION
        "Information about a specific Filtering Database."
    INDEX   { dot1qFdbId }
    ::= { dot1qFdbTable 1 }

Dot1qFdbEntry ::=
    SEQUENCE {
        dot1qFdbId
            Unsigned32,
        dot1qFdbDynamicCount
            Counter32
    }

dot1qFdbId OBJECT-TYPE
    SYNTAX       Unsigned32
    MAX-ACCESS   not-accessible
    STATUS       current
    DESCRIPTION
        "The identity of this Filtering Database."
    ::= { dot1qFdbEntry 1 }

dot1qFdbDynamicCount OBJECT-TYPE
    SYNTAX       Counter32
    MAX-ACCESS   read-only
    STATUS       current
    DESCRIPTION
        "The current number of dynamic entries in this
        Filtering Database."
    REFERENCE
        "IEEE 802.1Q/D11 Section 12.7.1.1.3"
    ::= { dot1qFdbEntry 2 }

-- -------------------------------------------------------------
-- Multiple Forwarding Databases for 802.1Q Transparent devices
-- This table is an alternative to the dot1dTpFdbTable,
-- previously defined for 802.1D devices which only support a
-- single Forwarding Database.
-- -------------------------------------------------------------

dot1qTpFdbTable OBJECT-TYPE
    SYNTAX      SEQUENCE OF Dot1qTpFdbEntry
    MAX-ACCESS  not-accessible
    STATUS      current
    DESCRIPTION
        "A table that contains information about unicast entries
        for which the device has forwarding and/or filtering
        information.  This information is used by the
        transparent bridging function in determining how to
        propagate a received frame."
    REFERENCE
        "IEEE 802.1Q/D11 Section 12.7.7"
    ::= { dot1qTp 2 }

dot1qTpFdbEntry OBJECT-TYPE
    SYNTAX      Dot1qTpFdbEntry
    MAX-ACCESS  not-accessible
    STATUS      current
    DESCRIPTION
        "Information about a specific unicast MAC address for
        which the device has some forwarding and/or filtering
        information."
    INDEX   { dot1qFdbId, dot1qTpFdbAddress }
    ::= { dot1qTpFdbTable 1 }

Dot1qTpFdbEntry ::=
    SEQUENCE {
        dot1qTpFdbAddress
            MacAddress,
        dot1qTpFdbPort
            INTEGER,
        dot1qTpFdbStatus
            INTEGER
    }

dot1qTpFdbAddress OBJECT-TYPE
    SYNTAX      MacAddress
    MAX-ACCESS  not-accessible
    STATUS      current
    DESCRIPTION
        "A unicast MAC address for which the device has
        forwarding and/or filtering information."
    ::= { dot1qTpFdbEntry 1 }

dot1qTpFdbPort OBJECT-TYPE
    SYNTAX      INTEGER (0..65535)
    MAX-ACCESS  read-only
    STATUS      current
    DESCRIPTION
        "Either the value '0', or the port number of the port on
        which a frame having a source address equal to the value
        of the corresponding instance of dot1qTpFdbAddress has
        been seen.  A value of '0' indicates that the port
        number has not been learned but that the device does
        have some forwarding/filtering information about this
        address (e.g. in the dot1qStaticUnicastTable).
        Implementors are encouraged to assign the port value to
        this object whenever it is learned even for addresses
        for which the corresponding value of dot1qTpFdbStatus is
        not learned(3)."
    ::= { dot1qTpFdbEntry 2 }

dot1qTpFdbStatus OBJECT-TYPE
    SYNTAX      INTEGER {
                    other(1),
                    invalid(2),
                    learned(3),
                    self(4),
                    mgmt(5)
                }
    MAX-ACCESS  read-only
    STATUS      current
    DESCRIPTION
        "The status of this entry.  The meanings of the values
        are:
            other(1) - none of the following.  This may include
                the case where some other MIB object (not the
                corresponding instance of dot1qTpFdbPort, nor an
                entry in the dot1qStaticUnicastTable) is being
                used to determine if and how frames addressed to
                the value of the corresponding instance of
                dot1qTpFdbAddress are being forwarded.
            invalid(2) - this entry is no longer valid (e.g., it
                was learned but has since aged out), but has not
                yet been flushed from the table.
            learned(3) - the value of the corresponding instance
                of dot1qTpFdbPort was learned and is being used.
            self(4) - the value of the corresponding instance of
                dot1qTpFdbAddress represents one of the device's
                addresses.  The corresponding instance of
                dot1qTpFdbPort indicates which of the device's
                ports has this address.
            mgmt(5) - the value of the corresponding instance of
                dot1qTpFdbAddress is also the value of an
                existing instance of dot1qStaticAddress."
    ::= { dot1qTpFdbEntry 3 }

-- -------------------------------------------------------------
-- Dynamic Group Registration Table
-- -------------------------------------------------------------

dot1qTpGroupTable OBJECT-TYPE
    SYNTAX      SEQUENCE OF Dot1qTpGroupEntry
    MAX-ACCESS  not-accessible
    STATUS      current
    DESCRIPTION
        "A table containing filtering information for VLANs
        configured into the bridge by (local or network)
        management, or learnt dynamically, specifying the set of
        ports to which frames received on a VLAN for this FDB
        and containing a specific Group destination address are
        allowed to be forwarded."
    ::= { dot1qTp 3 }

dot1qTpGroupEntry OBJECT-TYPE
    SYNTAX      Dot1qTpGroupEntry
    MAX-ACCESS  not-accessible
    STATUS      current
    DESCRIPTION
        "Filtering information configured into the bridge by
        management, or learnt dynamically, specifying the set of
        ports to which frames received on a VLAN and containing
        a specific Group destination address, are allowed to be
        forwarded.  The subset of these ports learnt dynamically
        is also provided."
    INDEX   { dot1qVlanIndex, dot1qTpGroupAddress }
    ::= { dot1qTpGroupTable 1 }

Dot1qTpGroupEntry ::=
    SEQUENCE {
        dot1qTpGroupAddress
            MacAddress,
        dot1qTpGroupEgressPorts
            PortList,
        dot1qTpGroupLearnt
            PortList
    }

dot1qTpGroupAddress OBJECT-TYPE
    SYNTAX      MacAddress
    MAX-ACCESS  not-accessible
    STATUS      current
    DESCRIPTION
        "The destination Group MAC address in a frame to which
        this entry's filtering information applies."
    ::= { dot1qTpGroupEntry 1 }

dot1qTpGroupEgressPorts OBJECT-TYPE
    SYNTAX      PortList
    MAX-ACCESS  read-only
    STATUS      current
    DESCRIPTION
        "The complete set of ports, in this VLAN, to which
        frames destined for this Group MAC address are currently
        being explicitly forwarded.  This does not include ports
        for which this address is only implicitly forwarded, in
        the dot1qForwardAllPorts list."
    ::= { dot1qTpGroupEntry 2 }

dot1qTpGroupLearnt OBJECT-TYPE
    SYNTAX      PortList
    MAX-ACCESS  read-only
    STATUS      current
    DESCRIPTION
        "The subset of ports in dot1qTpGroupEgressPorts which
        were learnt by GMRP or some other dynamic mechanism, in
        this Filtering database."
    ::= { dot1qTpGroupEntry 3 }

-- -------------------------------------------------------------
-- Service Requirements Group
-- -------------------------------------------------------------


-- -------------------------------------------------------------
-- The Static (Destination-Address Filtering) Database
-- -------------------------------------------------------------

dot1qStaticUnicastTable OBJECT-TYPE
    SYNTAX      SEQUENCE OF Dot1qStaticUnicastEntry
    MAX-ACCESS  not-accessible
    STATUS      current
    DESCRIPTION
        "A table containing filtering information for Unicast
        MAC addresses for each Filtering Database, configured
        into the device by (local or network) management
        specifying the set of ports to which frames received
        from specific ports and containing specific unicast
        destination addresses are allowed to be forwarded.  A
        value of zero in this table as the port number from
        which frames with a specific destination address are
        received, is used to specify all ports for which there
        is no specific entry in this table for that particular
        destination address.  Entries are valid for unicast
        addresses only."
    REFERENCE
        "IEEE 802.1Q/D11 Section 12.7.7,
        ISO/IEC 15802-3 Section 7.9.1"
    ::= { dot1qStatic 1 }

dot1qStaticUnicastEntry OBJECT-TYPE
    SYNTAX      Dot1qStaticUnicastEntry
    MAX-ACCESS  not-accessible
    STATUS      current
    DESCRIPTION
        "Filtering information configured into the device by
        (local or network) management specifying the set of
        ports to which frames received from a specific port and
        containing a specific unicast destination address are
        allowed to be forwarded."
    INDEX   {
        dot1qFdbId,
        dot1qStaticUnicastAddress,
        dot1qStaticUnicastReceivePort
    }
    ::= { dot1qStaticUnicastTable 1 }

Dot1qStaticUnicastEntry ::=
    SEQUENCE {
        dot1qStaticUnicastAddress
            MacAddress,
        dot1qStaticUnicastReceivePort
            INTEGER,
        dot1qStaticUnicastAllowedToGoTo
            PortList,
        dot1qStaticUnicastStatus
            INTEGER
    }

dot1qStaticUnicastAddress OBJECT-TYPE
    SYNTAX      MacAddress
    MAX-ACCESS  not-accessible
    STATUS      current
    DESCRIPTION
        "The destination MAC address in a frame to which this
        entry's filtering information applies.  This object must
        take the value of a unicast address."
    ::= { dot1qStaticUnicastEntry 1 }

dot1qStaticUnicastReceivePort OBJECT-TYPE
    SYNTAX      INTEGER (0..65535)
    MAX-ACCESS  not-accessible
    STATUS      current
    DESCRIPTION
        "Either the value '0', or the port number of the port
        from which a frame must be received in order for this
        entry's filtering information to apply.  A value of zero
        indicates that this entry applies on all ports of the
        device for which there is no other applicable entry."
    ::= { dot1qStaticUnicastEntry 2 }

dot1qStaticUnicastAllowedToGoTo OBJECT-TYPE
    SYNTAX      PortList
    MAX-ACCESS  read-write
    STATUS      current
    DESCRIPTION
        "The set of ports for which a frame with a specific
        unicast address will be flooded in the event that it
        has not been learned.  It also specifies the set of
        ports a specific unicast address may be dynamically
        learnt on.  The dot1qTpFdbTable will have an equivalent
        entry with a dot1qTpFdbPort value of '0' until this
        address has been learnt, when it will be updated with
        the port the address has been seen on.  This only
        applies to ports that are members of the VLAN, defined
        by dot1qVlanCurrentEgressPorts.  The default value of
        this object is a string of ones of appropriate length."
    REFERENCE
        "IEEE 802.1Q/D11 Table 8-5, ISO/IEC 15802-3 Table 7-5"
    ::= { dot1qStaticUnicastEntry 3 }

dot1qStaticUnicastStatus OBJECT-TYPE
    SYNTAX      INTEGER {
                    other(1),
                    invalid(2),
                    permanent(3),
                    deleteOnReset(4),
                    deleteOnTimeout(5)
                }
    MAX-ACCESS  read-write
    STATUS      current
    DESCRIPTION
        "This object indicates the status of this entry.
            other(1) - this entry is currently in use but
                the conditions under which it will remain
                so differ from the following values.
            invalid(2) - writing this value to the object
                removes the corresponding entry.
            permanent(3) - this entry is currently in use
                and will remain so after the next reset of
                the bridge.
            deleteOnReset(4) - this entry is currently in
                use and will remain so until the next
                reset of the bridge.
            deleteOnTimeout(5) - this entry is currently in
                use and will remain so until it is aged out."
    DEFVAL      { permanent }
    ::= { dot1qStaticUnicastEntry 4 }

dot1qStaticMulticastTable OBJECT-TYPE
    SYNTAX      SEQUENCE OF Dot1qStaticMulticastEntry
    MAX-ACCESS  not-accessible
    STATUS      current
    DESCRIPTION
        "A table containing filtering information for Multicast
        and Broadcast MAC addresses for each VLAN, configured
        into the device by (local or network) management
        specifying the set of ports to which frames received
        from specific ports and containing specific Multicast
        and Broadcast destination addresses are allowed to be
        forwarded.  A value of zero in this table as the port
        number from which frames with a specific destination
        address are received, is used to specify all ports for
        which there is no specific entry in this table for that
        particular destination address.  Entries are valid for
        Multicast and Broadcast addresses only."
    REFERENCE
        "IEEE 802.1Q/D11 Section 12.7.7,
        ISO/IEC 15802-3 Section 7.9.1"
    ::= { dot1qStatic 2 }

dot1qStaticMulticastEntry OBJECT-TYPE
    SYNTAX      Dot1qStaticMulticastEntry
    MAX-ACCESS  not-accessible
    STATUS      current
    DESCRIPTION
        "Filtering information configured into the device by
        (local or network) management specifying the set of
        ports to which frames received from this specific port
        for this VLAN and containing this Multicast or Broadcast
        destination address are allowed to be forwarded."
    INDEX   {
        dot1qVlanIndex,
        dot1qStaticMulticastAddress,
        dot1qStaticMulticastReceivePort
    }
    ::= { dot1qStaticMulticastTable 1 }

Dot1qStaticMulticastEntry ::=
    SEQUENCE {
        dot1qStaticMulticastAddress
            MacAddress,
        dot1qStaticMulticastReceivePort
            INTEGER,
        dot1qStaticMulticastStaticEgressPorts
            PortList,
        dot1qStaticMulticastForbiddenEgressPorts
            PortList,
        dot1qStaticMulticastStatus
            INTEGER
    }

dot1qStaticMulticastAddress OBJECT-TYPE
    SYNTAX      MacAddress
    MAX-ACCESS  not-accessible
    STATUS      current
    DESCRIPTION
        "The destination MAC address in a frame to which this
        entry's filtering information applies.  This object must
        take the value of a Multicast or Broadcast address."
    ::= { dot1qStaticMulticastEntry 1 }

dot1qStaticMulticastReceivePort OBJECT-TYPE
    SYNTAX      INTEGER (0..65535)
    MAX-ACCESS  not-accessible
    STATUS      current
    DESCRIPTION
        "Either the value '0', or the port number of the port
        from which a frame must be received in order for this
        entry's filtering information to apply.  A value of zero
        indicates that this entry applies on all ports of the
        device for which there is no other applicable entry."
    ::= { dot1qStaticMulticastEntry 2 }

dot1qStaticMulticastStaticEgressPorts OBJECT-TYPE
    SYNTAX      PortList
    MAX-ACCESS  read-write
    STATUS      current
    DESCRIPTION
        "The set of ports to which frames received from a
        specific port and destined for a specific Multicast or
        Broadcast MAC address must be forwarded, regardless of
        any dynamic information e.g. from GMRP.  A port may not
        be added in this set if it is already a member of the
        set of ports in dot1qStaticMulticastForbiddenEgressPorts.
        The default value of this object is a string of ones of
        appropriate length."
    ::= { dot1qStaticMulticastEntry 3 }

dot1qStaticMulticastForbiddenEgressPorts OBJECT-TYPE
    SYNTAX      PortList
    MAX-ACCESS  read-write
    STATUS      current
    DESCRIPTION
        "The set of ports to which frames received from a
        specific port and destined for a specific Multicast or
        Broadcast MAC address must not be forwarded, regardless
        of any dynamic information e.g. from GMRP.  A port may
        not be added in this set if it is already a member of the
        set of ports in dot1qStaticMulticastStaticEgressPorts.
        The default value of this object is a string of zeros of
        appropriate length."
    ::= { dot1qStaticMulticastEntry 4 }

dot1qStaticMulticastStatus OBJECT-TYPE
    SYNTAX      INTEGER {
                    other(1),
                    invalid(2),
                    permanent(3),
                    deleteOnReset(4),
                    deleteOnTimeout(5)
                }
    MAX-ACCESS  read-write
    STATUS      current
    DESCRIPTION
        "This object indicates the status of this entry.
            other(1) - this entry is currently in use but
                the conditions under which it will remain
                so differ from the following values.
            invalid(2) - writing this value to the object
                removes the corresponding entry.
            permanent(3) - this entry is currently in use
                and will remain so after the next reset of
                the bridge.
            deleteOnReset(4) - this entry is currently in
                use and will remain so until the next
                reset of the bridge.
            deleteOnTimeout(5) - this entry is currently in
                use and will remain so until it is aged out."
    DEFVAL      { permanent }
    ::= { dot1qStaticMulticastEntry 5 }

-- -------------------------------------------------------------
-- The Current VLAN Database
-- -------------------------------------------------------------

dot1qVlanNumDeletes OBJECT-TYPE
    SYNTAX     Counter32
    MAX-ACCESS read-only
    STATUS     current
    DESCRIPTION
        "The number of times a VLAN entry has been deleted from
        the dot1qVlanCurrentTable (for any reason).  If an entry
        is deleted, then inserted, and then deleted, this
        counter will be incremented by 2."
    ::= { dot1qVlan 1 }

dot1qVlanCurrentTable OBJECT-TYPE
    SYNTAX      SEQUENCE OF Dot1qVlanCurrentEntry
    MAX-ACCESS  not-accessible
    STATUS      current
    DESCRIPTION
        "A table containing current configuration information
        for each VLAN currently configured into the device by
        (local or network) management, or dynamically created
        as a result of GVRP requests received."
    ::= { dot1qVlan 2 }

dot1qVlanCurrentEntry OBJECT-TYPE
    SYNTAX      Dot1qVlanCurrentEntry
    MAX-ACCESS  not-accessible
    STATUS      current
    DESCRIPTION
        "Information for a VLAN configured into the device by
        (local or network) management, or dynamically created
        as a result of GVRP requests received."
    INDEX   { dot1qVlanTimeMark, dot1qVlanIndex }
    ::= { dot1qVlanCurrentTable 1 }

Dot1qVlanCurrentEntry ::=
    SEQUENCE {
        dot1qVlanTimeMark
            TimeFilter,
        dot1qVlanIndex
            VlanIndex,
        dot1qVlanFdbId
            Unsigned32,
        dot1qVlanCurrentEgressPorts
            PortList,
        dot1qVlanCurrentUntaggedPorts
            PortList,
        dot1qVlanStatus
            INTEGER,
        dot1qVlanCreationTime
            TimeTicks
    }

dot1qVlanTimeMark OBJECT-TYPE
    SYNTAX      TimeFilter
    MAX-ACCESS  not-accessible
    STATUS      current
    DESCRIPTION
        "A TimeFilter for this entry.  See the TimeFilter
        textual convention to see how this works."
    ::= { dot1qVlanCurrentEntry 1 }

dot1qVlanIndex OBJECT-TYPE
    SYNTAX      VlanIndex
    MAX-ACCESS  not-accessible
    STATUS      current
    DESCRIPTION
        "The VLAN-ID or other identifier refering to this VLAN."
    ::= { dot1qVlanCurrentEntry 2 }

dot1qVlanFdbId OBJECT-TYPE
    SYNTAX      Unsigned32
    MAX-ACCESS  read-only
    STATUS      current
    DESCRIPTION
        "The Filtering Database used by this VLAN.  This is one
        of the dot1qFdbId values in the dot1qFdbTable.  This
        value is allocated automatically by the device whenever
        the VLAN is created: either dynamically by GVRP, or by
        management, in dot1qVlanStaticTable.  Allocation of this
        value follows the learning constraints defined for this
        VLAN in dot1qLearningConstraintsTable."
    ::= { dot1qVlanCurrentEntry 3 }

dot1qVlanCurrentEgressPorts OBJECT-TYPE
    SYNTAX      PortList
    MAX-ACCESS  read-only
    STATUS      current
    DESCRIPTION
        "The set of ports which are transmitting traffic for
        this VLAN as either tagged or untagged frames."
    REFERENCE
        "IEEE 802.1Q/D11 Section 12.10.2.1"
    ::= { dot1qVlanCurrentEntry 4 }

dot1qVlanCurrentUntaggedPorts OBJECT-TYPE
    SYNTAX      PortList
    MAX-ACCESS  read-only
    STATUS      current
    DESCRIPTION
        "The set of ports which are transmitting traffic for
        this VLAN as untagged frames."
    REFERENCE
        "IEEE 802.1Q/D11 Section 12.10.2.1"
    ::= { dot1qVlanCurrentEntry 5 }

dot1qVlanStatus OBJECT-TYPE
    SYNTAX      INTEGER {
                    other(1),
                    permanent(2),
                    dynamicGvrp(3)
                }
    MAX-ACCESS  read-only
    STATUS      current
    DESCRIPTION
        "This object indicates the status of this entry.
            other(1) - this entry is currently in use but the
                conditions under which it will remain so differ
                from the following values.
            permanent(2) - this entry, corresponding to an entry
                in dot1qVlanStaticTable, is currently in use and
                will remain so after the next reset of the
                device.  The port lists for this entry include
                ports from the equivalent dot1qVlanStaticTable
                entry and ports learnt dynamically.
            dynamicGvrp(3) - this entry is currently in use
                and will remain so until removed by GVRP.  There
                is no static entry for this VLAN and it will be
                removed when the last port leaves the VLAN."
    ::= { dot1qVlanCurrentEntry 6 }

dot1qVlanCreationTime OBJECT-TYPE
    SYNTAX      TimeTicks
    MAX-ACCESS  read-only
    STATUS      current
    DESCRIPTION
        "The value of sysUpTime when this VLAN was created."
    ::= { dot1qVlanCurrentEntry 7 }

-- -------------------------------------------------------------
-- The Static VLAN Database
-- -------------------------------------------------------------

dot1qVlanStaticTable OBJECT-TYPE
    SYNTAX      SEQUENCE OF Dot1qVlanStaticEntry
    MAX-ACCESS  not-accessible
    STATUS      current
    DESCRIPTION
        "A table containing static configuration information for
        each VLAN configured into the device by (local or
        network) management.  All entries are permanent and will
        be restored after the device is reset."
    ::= { dot1qVlan 3 }

dot1qVlanStaticEntry OBJECT-TYPE
    SYNTAX      Dot1qVlanStaticEntry
    MAX-ACCESS  not-accessible
    STATUS      current
    DESCRIPTION
        "Static information for a VLAN configured into the
        device by (local or network) management."
    INDEX   { dot1qVlanIndex }
    ::= { dot1qVlanStaticTable 1 }

Dot1qVlanStaticEntry ::=
    SEQUENCE {
        dot1qVlanStaticName
            SnmpAdminString,
        dot1qVlanStaticEgressPorts
            PortList,
        dot1qVlanForbiddenEgressPorts
            PortList,
        dot1qVlanStaticUntaggedPorts
            PortList,
        dot1qVlanStaticRowStatus
            RowStatus
    }

dot1qVlanStaticName OBJECT-TYPE
    SYNTAX      SnmpAdminString (SIZE (0..32))
    MAX-ACCESS  read-create
    STATUS      current
    DESCRIPTION
        "An administratively assigned string, which may be used
        to identify the VLAN."
    REFERENCE
        "IEEE 802.1Q/D11 Section 12.10.2.1"
    ::= { dot1qVlanStaticEntry 1 }

dot1qVlanStaticEgressPorts OBJECT-TYPE
    SYNTAX      PortList
    MAX-ACCESS  read-create
    STATUS      current
    DESCRIPTION
        "The set of ports which are permanently assigned to the
        egress list for this VLAN by management.  Changes to a
        bit in this object affect the per-port per-VLAN
        Registrar control for Registration Fixed for the
        relevant GVRP state machine on each port.  A port may
        not be added in this set if it is already a member of
        the set of ports in dot1qVlanForbiddenEgressPorts.  The
        default value of this object is a string of zeros of
        appropriate length, indicating not fixed."
    REFERENCE
        "IEEE 802.1Q/D11 Section 12.7.7.3, 11.2.3.2.3"
    ::= { dot1qVlanStaticEntry 2 }

dot1qVlanForbiddenEgressPorts OBJECT-TYPE
    SYNTAX      PortList
    MAX-ACCESS  read-create
    STATUS      current
    DESCRIPTION
        "The set of ports which are prohibited by management
        from being included in the egress list for this VLAN.
        Changes to this object that cause a port to be included
        or excluded affect the per-port per-VLAN Registrar
        control for Registration Forbidden for the relevant GVRP
        state machine on each port.  A port may not be added in
        this set if it is already a member of the set of ports
        in dot1qVlanStaticEgressPorts.  The default value of
        this object is a string of zeros of appropriate length,
        excluding all ports from the forbidden set."
    REFERENCE
        "IEEE 802.1Q/D11 Section 12.7.7.3, 11.2.3.2.3"
    ::= { dot1qVlanStaticEntry 3 }

dot1qVlanStaticUntaggedPorts OBJECT-TYPE
    SYNTAX      PortList
    MAX-ACCESS  read-create
    STATUS      current
    DESCRIPTION
        "The set of ports which should transmit egress packets
        for this VLAN as untagged.  The default value of this
        object for the default VLAN (dot1qVlanIndex = 1) is a string
        of appropriate length including all ports.  There is no
        specified default for other VLANs.  If a device agent cannot
        support the set of ports being set then it will reject the
        set operation with an error. An example might be if a
        manager attempts to set more than one VLAN to be untagged
        on egress where the device does not support this IEEE 802.1Q
        option."
    REFERENCE
        "IEEE 802.1Q/D11 Section 12.10.2.1"
    ::= { dot1qVlanStaticEntry 4 }

dot1qVlanStaticRowStatus OBJECT-TYPE
    SYNTAX      RowStatus
    MAX-ACCESS  read-create
    STATUS      current
    DESCRIPTION
        "This object indicates the status of this entry."
    ::= { dot1qVlanStaticEntry 5 }

dot1qNextFreeLocalVlanIndex OBJECT-TYPE
    SYNTAX      INTEGER (0|4096..2147483647)
    MAX-ACCESS  read-only
    STATUS      current
    DESCRIPTION
        "The next available value for dot1qVlanIndex of a local
        VLAN entry in dot1qVlanStaticTable.  This will report
        values >=4096 if a new Local VLAN may be created or else
        the value 0 if this is not possible.
        A row creation operation in this table for an entry with a local
        VlanIndex value may fail if the current value of this object
        is not used as the index. Even if the value read is used,
        there is no guarantee that it will still be the valid index
        when the create operation is attempted - another manager may
        have already got in during the intervening time interval.
        In this case, dot1qNextFreeLocalVlanIndex should be re-read
        and the creation re-tried with the new value.

        This value will automatically change when the current value is
        used to create a new row."
    ::= { dot1qVlan 4 }

-- -------------------------------------------------------------
-- The VLAN Port Configuration Table
-- -------------------------------------------------------------

dot1qPortVlanTable OBJECT-TYPE
    SYNTAX      SEQUENCE OF Dot1qPortVlanEntry
    MAX-ACCESS  not-accessible
    STATUS      current
    DESCRIPTION
        "A table containing per port control and status
        information for VLAN configuration in the device."
    ::= { dot1qVlan 5 }

dot1qPortVlanEntry OBJECT-TYPE
    SYNTAX      Dot1qPortVlanEntry
    MAX-ACCESS  not-accessible
    STATUS      current
    DESCRIPTION
        "Information controlling VLAN configuration for a port
        on the device.  This is indexed by dot1dBasePort."
    AUGMENTS { dot1dBasePortEntry }
    ::= { dot1qPortVlanTable 1 }

Dot1qPortVlanEntry ::=
    SEQUENCE {
        dot1qPvid
            VlanIndex,
        dot1qPortAcceptableFrameTypes
            INTEGER,
        dot1qPortIngressFiltering
            TruthValue,
        dot1qPortGvrpStatus
            EnabledStatus,
        dot1qPortGvrpFailedRegistrations
            Counter32,
        dot1qPortGvrpLastPduOrigin
            MacAddress
    }

dot1qPvid OBJECT-TYPE
    SYNTAX      VlanIndex
    MAX-ACCESS  read-write
    STATUS      current
    DESCRIPTION
        "The PVID, the VLAN ID assigned to untagged frames or
        Priority-Tagged frames received on this port."
    REFERENCE
        "IEEE 802.1Q/D11 Section 12.10.1.1"
    DEFVAL      { 1 }
    ::= { dot1qPortVlanEntry 1 }

dot1qPortAcceptableFrameTypes OBJECT-TYPE
    SYNTAX      INTEGER {
                    admitAll(1),
                    admitOnlyVlanTagged(2)
                }
    MAX-ACCESS  read-write
    STATUS      current
    DESCRIPTION
        "When this is admitOnlyVlanTagged(2) the device will
        discard untagged frames or Priority-Tagged frames
        received on this port.  When admitAll(1), untagged
        frames or Priority-Tagged frames received on this port
        will be accepted and assigned to the PVID for this port.

        This control does not affect VLAN independent BPDU
        frames, such as GVRP and STP.  It does affect VLAN
        dependent BPDU frames, such as GMRP."
    REFERENCE
        "IEEE 802.1Q/D11 Section 12.10.1.3"
    DEFVAL      { admitAll }
    ::= { dot1qPortVlanEntry 2 }

dot1qPortIngressFiltering OBJECT-TYPE
    SYNTAX      TruthValue
    MAX-ACCESS  read-write
    STATUS      current
    DESCRIPTION
        "When this is true(1) the device will discard incoming
        frames for VLANs which do not include this Port in its
        Member set.  When false(2), the port will accept all
        incoming frames.

        This control does not affect VLAN independent BPDU
        frames, such as GVRP and STP.  It does affect VLAN
        dependent BPDU frames, such as GMRP."
    REFERENCE
        "IEEE 802.1Q/D11 Section 12.10.1.4"
    DEFVAL      { false }
    ::= { dot1qPortVlanEntry 3 }

dot1qPortGvrpStatus OBJECT-TYPE
    SYNTAX      EnabledStatus
    MAX-ACCESS  read-write
    STATUS      current
    DESCRIPTION
        "The state of GVRP operation on this port.  The value
        enabled(1) indicates that GVRP is enabled on this port,
        as long as dot1qGvrpStatus is also enabled for this
        device.  When disabled(2) but dot1qGvrpStatus is still
        enabled for the device, GVRP is disabled on this port:
        any GVRP packets received will be silently discarded and
        no GVRP registrations will be propagated from other
        ports.  This object affects all GVRP Applicant and
        Registrar state machines on this port.  A transition
        from disabled(2) to enabled(1) will cause a reset of all
        GVRP state machines on this port."
    DEFVAL      { enabled }
    ::= { dot1qPortVlanEntry 4 }

dot1qPortGvrpFailedRegistrations OBJECT-TYPE
    SYNTAX      Counter32
    MAX-ACCESS  read-only
    STATUS      current
    DESCRIPTION
        "The total number of failed GVRP registrations, for any
        reason, on this port."
    ::= { dot1qPortVlanEntry 5 }

dot1qPortGvrpLastPduOrigin OBJECT-TYPE
    SYNTAX      MacAddress
    MAX-ACCESS  read-only
    STATUS      current
    DESCRIPTION
        "The Source MAC Address of the last GVRP message
        received on this port."
    ::= { dot1qPortVlanEntry 6 }

-- -------------------------------------------------------------
-- Per port VLAN Statistics Table
-- -------------------------------------------------------------

dot1qPortVlanStatisticsTable OBJECT-TYPE
    SYNTAX      SEQUENCE OF Dot1qPortVlanStatisticsEntry
    MAX-ACCESS  not-accessible
    STATUS      current
    DESCRIPTION
        "A table containing per-port, per-VLAN statistics for
        traffic received. Separate objects are provided for both the
        most-significant and least-significant bits of statistics
        counters for ports that are associated with this transparent
        bridge. The most-significant bit objects are only required on
        high capacity interfaces, as defined in the conformance clauses
        for these objects. This mechanism is provided as a way to read
        64-bit counters for agents which support only SNMPv1.

        Note that the reporting of most-significant and least-
        significant counter bits separately runs the risk of missing
        an overflow of the lower bits in the interval between sampling.
        The manager must be aware of this possibility, even within the
        same varbindlist, when interpreting the results of a request or
        asynchronous notification."
    ::= { dot1qVlan 6 }

dot1qPortVlanStatisticsEntry OBJECT-TYPE
    SYNTAX      Dot1qPortVlanStatisticsEntry
    MAX-ACCESS  not-accessible
    STATUS      current
    DESCRIPTION
        "Traffic statistics for a VLAN on an interface."
    INDEX   { dot1dBasePort, dot1qVlanIndex }
    ::= { dot1qPortVlanStatisticsTable 1 }

Dot1qPortVlanStatisticsEntry ::=
    SEQUENCE {
        dot1qTpVlanPortInFrames
            Counter32,
        dot1qTpVlanPortOutFrames
            Counter32,
        dot1qTpVlanPortInDiscards
            Counter32,
        dot1qTpVlanPortInOverflowFrames
            Counter32,
        dot1qTpVlanPortOutOverflowFrames
            Counter32,
        dot1qTpVlanPortInOverflowDiscards
            Counter32
    }

dot1qTpVlanPortInFrames OBJECT-TYPE
    SYNTAX      Counter32
    MAX-ACCESS  read-only
    STATUS      current
    DESCRIPTION
        "The number of valid frames received by this port from
        its segment which were classified as belonging to this
        VLAN.  Note that a frame received on this port is
        counted by this object if and only if it is for a
        protocol being processed by the local forwarding process
        for this VLAN.  This object includes received bridge
        management frames classified as belonging to this VLAN
        (e.g. GMRP, but not GVRP or STP)."
    REFERENCE
        "IEEE 802.1Q/D11 Section 12.6.1.1.3(a)"
    ::= { dot1qPortVlanStatisticsEntry 1 }

dot1qTpVlanPortOutFrames OBJECT-TYPE
    SYNTAX      Counter32
    MAX-ACCESS  read-only
    STATUS      current
    DESCRIPTION
        "The number of valid frames transmitted by this port to
        its segment from the local forwarding process for this
        VLAN.  This includes bridge management frames originated
        by this device which are classified as belonging to this
        VLAN (e.g. GMRP, but not GVRP or STP)."
    REFERENCE
        "IEEE 802.1Q/D11 Section 12.6.1.1.3(d)"
    ::= { dot1qPortVlanStatisticsEntry 2 }

dot1qTpVlanPortInDiscards OBJECT-TYPE
    SYNTAX      Counter32
    MAX-ACCESS  read-only
    STATUS      current
    DESCRIPTION
        "The number of valid frames received by this port from
        its segment which were classified as belonging to this
        VLAN which were discarded due to VLAN related reasons.
        Specifically, the IEEE 802.1Q counters for Discard
        Inbound and Discard on Ingress Filtering."
    REFERENCE
        "IEEE 802.1Q/D11 Section 12.6.1.1.3"
    ::= { dot1qPortVlanStatisticsEntry 3 }

dot1qTpVlanPortInOverflowFrames OBJECT-TYPE
    SYNTAX      Counter32
    MAX-ACCESS  read-only
    STATUS      current
    DESCRIPTION
        "The number of times the associated
        dot1qTpVlanPortInFrames counter has overflowed."
    REFERENCE
        "ISO/IEC 15802-3 Section 14.6.1.1.3"
    ::= { dot1qPortVlanStatisticsEntry 4 }

dot1qTpVlanPortOutOverflowFrames OBJECT-TYPE
    SYNTAX      Counter32
    MAX-ACCESS  read-only
    STATUS      current
    DESCRIPTION
        "The number of times the associated
        dot1qTpVlanPortOutFrames counter has overflowed."
    REFERENCE
        "ISO/IEC 15802-3 Section 14.6.1.1.3"
    ::= { dot1qPortVlanStatisticsEntry 5 }

dot1qTpVlanPortInOverflowDiscards OBJECT-TYPE
    SYNTAX      Counter32
    MAX-ACCESS  read-only
    STATUS      current
    DESCRIPTION
        "The number of times the associated
        dot1qTpVlanPortInDiscards counter has overflowed."
    REFERENCE
        "ISO/IEC 15802-3 Section 14.6.1.1.3"
    ::= { dot1qPortVlanStatisticsEntry 6 }

dot1qPortVlanHCStatisticsTable OBJECT-TYPE
    SYNTAX      SEQUENCE OF Dot1qPortVlanHCStatisticsEntry
    MAX-ACCESS  not-accessible
    STATUS      current
    DESCRIPTION
        "A table containing per port, per VLAN statistics for
        traffic on high capacity interfaces."
    ::= { dot1qVlan 7 }

dot1qPortVlanHCStatisticsEntry OBJECT-TYPE
    SYNTAX      Dot1qPortVlanHCStatisticsEntry
    MAX-ACCESS  not-accessible
    STATUS      current
    DESCRIPTION
        "Traffic statistics for a VLAN on a high capacity
        interface."
    INDEX   { dot1dBasePort, dot1qVlanIndex }
    ::= { dot1qPortVlanHCStatisticsTable 1 }

Dot1qPortVlanHCStatisticsEntry ::=
    SEQUENCE {
        dot1qTpVlanPortHCInFrames
            Counter64,
        dot1qTpVlanPortHCOutFrames
            Counter64,
        dot1qTpVlanPortHCInDiscards
            Counter64
    }

dot1qTpVlanPortHCInFrames OBJECT-TYPE
    SYNTAX      Counter64
    MAX-ACCESS  read-only
    STATUS      current
    DESCRIPTION
        "The number of valid frames received by this port from
        its segment which were classified as belonging to this
        VLAN.  Note that a frame received on this port is
        counted by this object if and only if it is for a
        protocol being processed by the local forwarding process
        for this VLAN.  This object includes received bridge
        management frames classified as belonging to this VLAN
        (e.g. GMRP, but not GVRP or STP)."
    REFERENCE
        "IEEE 802.1Q/D11 Section 12.6.1.1.3(a)"
    ::= { dot1qPortVlanHCStatisticsEntry 1 }

dot1qTpVlanPortHCOutFrames OBJECT-TYPE
    SYNTAX      Counter64
    MAX-ACCESS  read-only
    STATUS      current
    DESCRIPTION
        "The number of valid frames transmitted by this port to
        its segment from the local forwarding process for this
        VLAN.  This includes bridge management frames originated
        by this device which are classified as belonging to this
        VLAN (e.g. GMRP, but not GVRP or STP)."
    REFERENCE
        "IEEE 802.1Q/D11 Section 12.6.1.1.3(d)"
    ::= { dot1qPortVlanHCStatisticsEntry 2 }

dot1qTpVlanPortHCInDiscards OBJECT-TYPE
    SYNTAX      Counter64
    MAX-ACCESS  read-only
    STATUS      current
    DESCRIPTION
        "The number of valid frames received by this port from
        its segment which were classified as belonging to this
        VLAN which were discarded due to VLAN related reasons.
        Specifically, the IEEE 802.1Q counters for Discard
        Inbound and Discard on Ingress Filtering."
    REFERENCE
        "IEEE 802.1Q/D11 Section 12.6.1.1.3"
    ::= { dot1qPortVlanHCStatisticsEntry 3 }

-- -------------------------------------------------------------
-- The VLAN Learning Constraints Table
-- -------------------------------------------------------------

dot1qLearningConstraintsTable OBJECT-TYPE
    SYNTAX      SEQUENCE OF Dot1qLearningConstraintsEntry
    MAX-ACCESS  not-accessible
    STATUS      current
    DESCRIPTION
        "A table containing learning constraints for sets of
        Shared and Independendent VLANs."
    REFERENCE
        "IEEE 802.1Q/D11 Section 12.10.3.1"
    ::= { dot1qVlan 8 }

dot1qLearningConstraintsEntry OBJECT-TYPE
    SYNTAX      Dot1qLearningConstraintsEntry
    MAX-ACCESS  not-accessible
    STATUS      current

    DESCRIPTION
        "A learning constraint defined for a VLAN."
    INDEX   { dot1qConstraintVlan, dot1qConstraintSet }
    ::= { dot1qLearningConstraintsTable 1 }

Dot1qLearningConstraintsEntry ::=
    SEQUENCE {
        dot1qConstraintVlan
            VlanIndex,
        dot1qConstraintSet
            INTEGER,
        dot1qConstraintType
            INTEGER,
        dot1qConstraintStatus
            RowStatus
    }

dot1qConstraintVlan OBJECT-TYPE
    SYNTAX      VlanIndex
    MAX-ACCESS  not-accessible
    STATUS      current
    DESCRIPTION
        "The index of the row in dot1qVlanCurrentTable for the
        VLAN constrained by this entry."
    ::= { dot1qLearningConstraintsEntry 1 }

dot1qConstraintSet OBJECT-TYPE
    SYNTAX      INTEGER (0..65535)
    MAX-ACCESS  not-accessible
    STATUS      current
    DESCRIPTION
        "The identity of the constraint set to which
        dot1qConstraintVlan belongs.  These values may be chosen
        by the management station."
    ::= { dot1qLearningConstraintsEntry 2 }

dot1qConstraintType OBJECT-TYPE
    SYNTAX      INTEGER {
                    independent(1),
                    shared(2)
                }
    MAX-ACCESS  read-create
    STATUS      current
    DESCRIPTION
        "The type of constraint this entry defines.
            independent(1) - the VLAN, dot1qConstraintVlan,
                uses an independent filtering database from all

                other VLANs in the same set, defined by
                dot1qConstraintSet.
            shared(2) - the VLAN, dot1qConstraintVlan, shares
                the same filtering database as all other VLANs
                in the same set, defined by dot1qConstraintSet."
    ::= { dot1qLearningConstraintsEntry 3 }

dot1qConstraintStatus OBJECT-TYPE
    SYNTAX      RowStatus
    MAX-ACCESS  read-create
    STATUS      current
    DESCRIPTION
        "The status of this entry."
    ::= { dot1qLearningConstraintsEntry 4 }

dot1qConstraintSetDefault OBJECT-TYPE
    SYNTAX      INTEGER (0..65535)
    MAX-ACCESS  read-write
    STATUS      current
    DESCRIPTION
        "The identity of the constraint set to which a VLAN
        belongs, if there is not an explicit entry for that VLAN
        in dot1qLearningConstraintsTable."
    ::= { dot1qVlan 9 }

dot1qConstraintTypeDefault OBJECT-TYPE
    SYNTAX      INTEGER {
                    independent(1),
                    shared(2)
                }
    MAX-ACCESS  read-write
    STATUS      current
    DESCRIPTION
        "The type of constraint set to which a VLAN belongs, if
        there is not an explicit entry for that VLAN in
        dot1qLearningConstraintsTable.  The types are as defined
        for dot1qConstraintType."
    ::= { dot1qVlan 10 }

-- -------------------------------------------------------------
-- IEEE 802.1Q MIB - Conformance Information
-- -------------------------------------------------------------

qBridgeConformance OBJECT IDENTIFIER ::= { qBridgeMIB 2 }

qBridgeGroups OBJECT IDENTIFIER ::= { qBridgeConformance 1 }

qBridgeCompliances OBJECT IDENTIFIER
    ::= { qBridgeConformance 2 }

-- -------------------------------------------------------------
-- units of conformance
-- -------------------------------------------------------------

qBridgeBaseGroup OBJECT-GROUP
    OBJECTS {
        dot1qVlanVersionNumber,
        dot1qMaxVlanId,
        dot1qMaxSupportedVlans,
        dot1qNumVlans,
        dot1qGvrpStatus
    }
    STATUS      current
    DESCRIPTION
        "A collection of objects providing device level control
        and status information for the Virtual LAN bridge
        services."
    ::= { qBridgeGroups 1 }

qBridgeFdbUnicastGroup OBJECT-GROUP
    OBJECTS {
        dot1qFdbDynamicCount,
        dot1qTpFdbPort,
        dot1qTpFdbStatus
    }
    STATUS      current
    DESCRIPTION
        "A collection of objects providing information about all
        unicast addresses, learnt dynamically or statically
        configured by management, in each Filtering Database."
    ::= { qBridgeGroups 2 }

qBridgeFdbMulticastGroup OBJECT-GROUP
    OBJECTS {
        dot1qTpGroupEgressPorts,
        dot1qTpGroupLearnt
    }

    STATUS      current
    DESCRIPTION
        "A collection of objects providing information about all
        multicast addresses, learnt dynamically or statically
        configured by management, in each Filtering Database."
    ::= { qBridgeGroups 3 }

qBridgeServiceRequirementsGroup OBJECT-GROUP
    OBJECTS {
        dot1qForwardAllPorts,
        dot1qForwardAllStaticPorts,
        dot1qForwardAllForbiddenPorts,
        dot1qForwardUnregisteredPorts,
        dot1qForwardUnregisteredStaticPorts,
        dot1qForwardUnregisteredForbiddenPorts
    }
    STATUS      current
    DESCRIPTION
        "A collection of objects providing information about
        service requirements, learnt dynamically or statically
        configured by management, in each Filtering Database."
    ::= { qBridgeGroups 4 }

qBridgeFdbStaticGroup OBJECT-GROUP
    OBJECTS {
        dot1qStaticUnicastAllowedToGoTo,
        dot1qStaticUnicastStatus,
        dot1qStaticMulticastStaticEgressPorts,
        dot1qStaticMulticastForbiddenEgressPorts,
        dot1qStaticMulticastStatus
    }
    STATUS      current
    DESCRIPTION
        "A collection of objects providing information about
        unicast and multicast addresses statically configured by
        management, in each Filtering Database or VLAN."
    ::= { qBridgeGroups 5 }

qBridgeVlanGroup OBJECT-GROUP
    OBJECTS {
        dot1qVlanNumDeletes,
        dot1qVlanFdbId,
        dot1qVlanCurrentEgressPorts,
        dot1qVlanCurrentUntaggedPorts,
        dot1qVlanStatus,
        dot1qVlanCreationTime
    }

    STATUS      current
    DESCRIPTION
        "A collection of objects providing information about
        all VLANs currently configured on this device."
    ::= { qBridgeGroups 6 }

qBridgeVlanStaticGroup OBJECT-GROUP
    OBJECTS {
        dot1qVlanStaticName,
        dot1qVlanStaticEgressPorts,
        dot1qVlanForbiddenEgressPorts,
        dot1qVlanStaticUntaggedPorts,
        dot1qVlanStaticRowStatus,
        dot1qNextFreeLocalVlanIndex
    }
    STATUS      current
    DESCRIPTION
        "A collection of objects providing information about
        VLANs statically configured by management."
    ::= { qBridgeGroups 7 }

qBridgePortGroup OBJECT-GROUP
    OBJECTS {
        dot1qPvid,
        dot1qPortAcceptableFrameTypes,
        dot1qPortIngressFiltering,
        dot1qPortGvrpStatus,
        dot1qPortGvrpFailedRegistrations,
        dot1qPortGvrpLastPduOrigin
    }
    STATUS      current
    DESCRIPTION
        "A collection of objects providing port level VLAN
        control and status information for all ports."
    ::= { qBridgeGroups 8 }

qBridgeVlanStatisticsGroup OBJECT-GROUP
    OBJECTS {
        dot1qTpVlanPortInFrames,
        dot1qTpVlanPortOutFrames,
        dot1qTpVlanPortInDiscards
    }
    STATUS      current
    DESCRIPTION
        "A collection of objects providing per-port packet
        statistics for all VLANs currently configured on this
        device."
    ::= { qBridgeGroups 9 }

qBridgeVlanStatisticsOverflowGroup OBJECT-GROUP
    OBJECTS {
        dot1qTpVlanPortInOverflowFrames,
        dot1qTpVlanPortOutOverflowFrames,
        dot1qTpVlanPortInOverflowDiscards
    }
    STATUS      current
    DESCRIPTION
        "A collection of objects providing overflow counters for
        per-port packet statistics for all VLANs currently configured
        on this device for high capacity interfaces, defined as those
        that have the value of the corresponding instance of
        ifSpeed greater than 650,000,000 bits/second."
    ::= { qBridgeGroups 10 }

qBridgeVlanHCStatisticsGroup OBJECT-GROUP
    OBJECTS {
        dot1qTpVlanPortHCInFrames,
        dot1qTpVlanPortHCOutFrames,
        dot1qTpVlanPortHCInDiscards
    }
    STATUS      current
    DESCRIPTION
        "A collection of objects providing per-port packet
        statistics for all VLANs currently configured on this
        device for high capacity interfaces, defined as those
        that have the value of the corresponding instance of
        ifSpeed greater than 650,000,000 bits/second."
    ::= { qBridgeGroups 11 }

qBridgeLearningConstraintsGroup OBJECT-GROUP
    OBJECTS {
        dot1qConstraintType,
        dot1qConstraintStatus
    }
    STATUS      current
    DESCRIPTION
        "A collection of objects defining the Filtering Database
        constraints all VLANs have with each other."
    ::= { qBridgeGroups 12 }

qBridgeLearningConstraintDefaultGroup OBJECT-GROUP
    OBJECTS {
        dot1qConstraintSetDefault,
        dot1qConstraintTypeDefault
    }

    STATUS      current
    DESCRIPTION
        "A collection of objects defining the default Filtering
        Database constraints for VLANs which have no specific
        constraints defined."
    ::= { qBridgeGroups 13 }

-- -------------------------------------------------------------
-- compliance statements
-- -------------------------------------------------------------

qBridgeCompliance MODULE-COMPLIANCE
    STATUS  current
    DESCRIPTION
        "The compliance statement for device support of Virtual
        LAN Bridge services."

    MODULE
        MANDATORY-GROUPS {
            qBridgeBaseGroup,
            qBridgeVlanGroup,
            qBridgeVlanStaticGroup,
            qBridgePortGroup
        }

        GROUP       qBridgeFdbUnicastGroup
        DESCRIPTION
            "This group is mandatory for bridges that implement
            802.1Q transparent bridging."

        GROUP       qBridgeFdbMulticastGroup
        DESCRIPTION
            "This group is mandatory for bridges that implement
            802.1Q transparent bridging."

        GROUP       qBridgeServiceRequirementsGroup
        DESCRIPTION
            "This group is mandatory for bridges that implement
            extended filtering services.  All objects must be
            read-write if extended-filtering services are
            enabled."

        GROUP       qBridgeFdbStaticGroup
        DESCRIPTION
            "This group is optional."

        GROUP       qBridgeVlanStatisticsGroup
        DESCRIPTION
            "This group is optional as there may be significant
            implementation cost associated with its support."

        GROUP       qBridgeVlanStatisticsOverflowGroup
        DESCRIPTION
            "This group is optional as there may be significant
            implementation cost associated with its support. It is most
            relevant for high capacity interfaces where the SNMP agent
            supports only SNMPv1."

        GROUP       qBridgeVlanHCStatisticsGroup
        DESCRIPTION
            "This group is optional as there may be significant
            implementation cost associated with its support. It is most
            relevant for high capacity interfaces."

        GROUP       qBridgeLearningConstraintsGroup
        DESCRIPTION
            "This group is mandatory for devices implementing
             both Independent VLAN Learning (IVL) and Shared
             VLAN Learning (SVL) modes of operation of the
             filtering database, as defined by IEEE 802.1Q."

        GROUP       qBridgeLearningConstraintDefaultGroup
        DESCRIPTION
            "This group is mandatory for devices implementing
             both Independent VLAN Learning (IVL) and Shared
             VLAN Learning (SVL) modes of operation of the
             filtering database, as defined by IEEE 802.1Q."

        OBJECT      dot1qPortAcceptableFrameTypes
        MIN-ACCESS  read-only
        DESCRIPTION
            "Write access is not required as this is an optional
            capability in IEEE 802.1Q."

        OBJECT      dot1qPortIngressFiltering
        MIN-ACCESS  read-only
        DESCRIPTION
            "Write access is not required as this is an optional
            capability in IEEE 802.1Q."

        OBJECT      dot1qConstraintSetDefault
        MIN-ACCESS  read-only
        DESCRIPTION
            "Write access is not required as this is an optional
            capability in IEEE 802.1Q."

        OBJECT      dot1qConstraintTypeDefault
        MIN-ACCESS  read-only
        DESCRIPTION
            "Write access is not required as this is an optional
            capability in IEEE 802.1Q."

       ::= { qBridgeCompliances 1 }
END

------------------------------------------------------------------------------
------------------------------------------------------------------------------
--
--  File         : wrsMasterMib.mi2
--  Description  : Sample WRS Master OID Definition MIB 
--  Version      : 0.6 
--  Date         : August 29, 2000     
--
--  Copyright (c) 2000 Wind River Systems, Inc.  All Rights Reserved.
--
--  Reproduction of this document is authorized on condition that this
--  copyright notice is included.  This sample WRS Master Enterprise MIB
--  embodies proprietary intellectual property of Wind River Systems (WRS). 
--  WRS retains all title and ownership in the specification, including any
--  revisions.
--
--  It is the intent of WRS to encourage the widespread use of this
--  specification in connection with the management of TMS-based products.  
--  WRS grants vendors, end-users, and other interested parties a
--  non-exclusive license to use this specification in connection with the
--  management of TMS products.
--
--  This specification is supplied "AS IS", and WRS makes no warranty,
--  either express or implied, as to the use, operations, condition,
--  or performance of this specification.
--
------------------------------------------------------------------------------
------------------------------------------------------------------------------
--  Sample WRS Master Enterprise MIB
--
--  NOTES:
--   1. This is a SMIv2 MIB - all definitions are automatically 'exported'.
--
--   2. This MIB:
--        - defines the 'WRS Product' OIDs (used as IMPORTS)
--        - defines the 'TMS Major Category' OIDs (used as IMPORTS)
--        - defines the 'TMS Internal MIB Module' OIDs (used as IMPORTS)
--        - defines/documents the 'TMS Generic' MIB OIDs
--        - documents the 'TMS OEM swAPI' MIB OIDs
--        - documents the 'TMS OEM Product' MIB OIDs
--
--   3. Note that the 'defined/documents' items provide a common place to
--      define or document the required OIDs.  SMIv1 MIBs can be defined
--      here and then imported into the corresponding MIB.  The SMIv2 
--      'MODULE-IDENTITY' macro does not allow the second OID parameter to
--      be imported from an external MIB file.  The authors of these
--      'documented' MIBs must verify, by procedure, that the values used
--      match the values in this document.
--
--   4. Note that some MIB compilers do not accept two sets of comments on the
--      same line.  Consequently, for commented out document items, do not
--      use a second comment on the same line.
--
--   5. Note that the Wind River enterprise ID (731) is used in the sample
--      MIBs.  The customer "must" replace the Wind River enterprise ID with
--      the registered enterprise identifier for the specific company or
--      product.  The customer must also replace the WRS information
--      located in the 'MODULE-IDENTITY' in each sample MIB.
--
------------------------------------------------------------------------------
------------------------------------------------------------------------------

WRS-MASTER-MIB DEFINITIONS ::= BEGIN

IMPORTS
    MODULE-IDENTITY, enterprises              FROM SNMPv2-SMI;

    zte MODULE-IDENTITY
        LAST-UPDATED    "0008290000Z"  -- August 29, 2000
        ORGANIZATION    "Wind River Systems, Inc."
        CONTACT-INFO    "Wind River Systems, Inc.
                         E-mail: support@windriver.com"

        DESCRIPTION     "WRS Master MIB OID defines and documentation."

        REVISION        "0008290000Z"  -- August 29, 2000
        DESCRIPTION     "Initial MIB creation."

        ::= { enterprises 3902 }
    
-- ZXA1- Products
	zxDsl	OBJECT IDENTIFIER ::= { zte 1004 }
	zxDslam OBJECT IDENTIFIER ::= { zxDsl 1 }
	zxLan	OBJECT IDENTIFIER ::= { zxDslam 10 }
	zxIma   OBJECT IDENTIFIER ::= { zxDslam 11 }
       zxWand  OBJECT IDENTIFIER  ::= { zxDslam 12 }
       uas  OBJECT IDENTIFIER  ::= { zxDslam 13 }

-- TMS Major MIB Categories
    idb             OBJECT IDENTIFIER ::= { zxLan 1 }     -- IDB MIBs
--    tmsGeneric      OBJECT IDENTIFIER ::= { zxLan 2 }     -- TMS Generic MIBs
    oemSwapi        OBJECT IDENTIFIER ::= { zxLan 3 }     -- OEM swAPI MIBs
    oemProd         OBJECT IDENTIFIER ::= { zxLan 4 }     -- OEM Product MIBs   
    lanGeneric      OBJECT IDENTIFIER ::= { zxLan 3 }  

-- TMS Major MIB Categories
    idb             OBJECT IDENTIFIER ::= { zxWand 1 }     -- IDB MIBs
    oemSwapi        OBJECT IDENTIFIER ::= { zxWand 2 }     -- OEM swAPI MIBs
    wandOemProd         OBJECT IDENTIFIER ::= { zxWand 3 }     -- OEM Product MIBs
    ixpGeneric      OBJECT IDENTIFIER ::= { zxWand 4 }     -- IXP Generic MIBs
    wandGeneric     OBJECT IDENTIFIER ::= { zxWand 5 }     -- IXP Generic MIBs

-- TMS IDB Internal Module MIBs
    rmonMib         OBJECT IDENTIFIER ::= { idb 1 }
--  garpMib         OBJECT IDENTIFIER ::= { idb 2 }         SMIv2
--  stpMib          OBJECT IDENTIFIER ::= { idb 3 }         SMIv2

-- wand MIBs
	 wandComLagMib    OBJECT IDENTIFIER ::= { wandGeneric 1 } 
	 wandCommMib      OBJECT IDENTIFIER ::= { wandGeneric 2 }
	 wandPvcMib       OBJECT IDENTIFIER ::= { wandGeneric 3 }
    
-- TMS Generic MIBs
--  tmsCommonMib    OBJECT IDENTIFIER ::= { tmsGeneric 1 }  SMIv2
--  lacpMib         OBJECT IDENTIFIER ::= { tmsGeneric 2 }  SMIv2

-- OEM swAPI MIBs
--  pmSwapi         OBJECT IDENTIFIER ::= { oemSwapi 1 }    SMIv2
--  bcmSwapi        OBJECT IDENTIFIER ::= { oemSwapi 2 }    SMIv2
--  pcSwapi         OBJECT IDENTIFIER ::= { oemSwapi 3 }    SMIv2

-- OEM Product MIBs
--  pm3575          OBJECT IDENTIFIER ::= { oemProd 1 }     SMIv2
--  bcm5600         OBJECT IDENTIFIER ::= { oemProd 2 }     SMIv2
--  pcSwitch        OBJECT IDENTIFIER ::= { oemProd 3 }     SMIv2

--
-- END of WRS-MASTER-MIB
--

END

 IMA-GROUP-MIB DEFINITIONS ::= BEGIN
 IMPORTS
  	MODULE-IDENTITY, OBJECT-TYPE, Integer32, 
  	Counter32, Gauge32, NOTIFICATION-TYPE     FROM SNMPv2-SMI
		
	MODULE-COMPLIANCE, OBJECT-GROUP, 
	NOTIFICATION-GROUP                        FROM SNMPv2-CONF
		                                
	TEXTUAL-CONVENTION, DateAndTime, 
	RowStatus                                 FROM SNMPv2-TC
	
	InterfaceIndex, InterfaceIndexOrZero, 
	ifIndex					  FROM IF-MIB

                    
	zxIma     	                          FROM WRS-MASTER-MIB;


atmfImaGroupMib MODULE-IDENTITY
	LAST-UPDATED "9902111830Z"
	ORGANIZATION "The ATM Forum"
	CONTACT-INFO
		"ATM Forum
		World Headquarters
		2570 West El Camino Real
		Suite 304
		Mountain View, CA 94040-1313
		USA
		Phone: +1 415 949 6700
		Fax: +1 415 949 6705
		email: info@atmforum.com"
	DESCRIPTION
		"The MIB module for managing ATM Forum Inverse Multiplexing
		for ATM (IMA) interfaces."
	REVISION "9902111830Z"
	DESCRIPTION
		"Updated and repaired version of the IMA-MIB released with the
		IMA v1.1 specification (af-phy-0086.001)."
	REVISION "9701092245Z"
	DESCRIPTION
		"Initial incomplete version of the IMA-MIB as published in the
		IMA v1.0 specification (af-phy-0086.000)."
	::= { zxIma 2 }

-- The object identifier subtree for the IMA-MIB

atmfImaGroupMibObjects OBJECT IDENTIFIER ::= { atmfImaGroupMib 1 }
atmfImaMibTraps OBJECT IDENTIFIER ::=  { atmfImaGroupMib 2 }
atmfImaMibTrapPrefix OBJECT IDENTIFIER ::= { atmfImaMibTraps 0 }

atmfImaMibGroupConformance OBJECT IDENTIFIER ::= { atmfImaGroupMib 3 }
atmfImaGroupGroups         OBJECT IDENTIFIER ::= { atmfImaMibGroupConformance 1}
atmfImaGroupCompliances    OBJECT IDENTIFIER ::= { atmfImaMibGroupConformance 2 }
	
-- Textual conventions
ImaGroupState ::= TEXTUAL-CONVENTION
	STATUS current
	DESCRIPTION
		"State of the IMA group."
	REFERENCE
		"ATM Forum IMA v1.1, Section 10.2.1 on page 55"
	SYNTAX INTEGER{
		notConfigured(1),
		startUp(2),
		startUpAck(3),
		configAbortUnsupportedM(4),
		configAbortIncompatibleSymmetry(5),
		configAbortOther(6),
		insufficientLinks(7),
		blocked(8),
		operational(9),
		configAbortUnsupportedImaVersion(10) }

ImaAlarmStatus ::= TEXTUAL-CONVENTION
	STATUS current
	DESCRIPTION
		"A qualification of the IMA trap which indicates if the
		condition causing the trap has been detected (declared)
		or is no longer present (cleared)."
	SYNTAX INTEGER{
		cleared(1),
		declared(2) }
		
ImaAlarmType ::= TEXTUAL-CONVENTION
	STATUS current
	DESCRIPTION
		"An identification of the event that caused the generation
		of the IMA trap."
	REFERENCE
		"ATM Forum IMA v1.1, Section 12.2.3 on page 79"
	SYNTAX INTEGER {
		imaAlarmLinkLif(1),
		imaAlarmLinkLods(2),
		imaAlarmLinkRfi(3),
		imaAlarmLinkTxMisConnect(4),
		imaAlarmLinkRxMisConnect(5),
		imaAlarmLinkTxFault(6),
		imaAlarmLinkRxFault(7),
		imaAlarmLinkTxUnusableFe(8),
		imaAlarmLinkRxUnusableFe(9),
		imaAlarmGroupStartupFe(10),
		imaAlarmGroupCfgAbort(11),
		imaAlarmGroupCfgAbortFe(12),
		imaAlarmGroupInsuffLinks(13),
		imaAlarmGroupInsuffLinksFe(14),
		imaAlarmGroupBlockedFe(15),
		imaAlarmGroupTimingSynch(16) }

ImaGroupTxClkMode ::= TEXTUAL-CONVENTION
	STATUS current
	DESCRIPTION
		"Indicate the transmit clock mode of the IMA group.
		There are two possible modes: the Common Transmit
		Clock (CTC) and the Independent Transmit Clock (ITC).
		The CTC mode corresponds to the case when the transmit clock
		of all IMA links are derived from the same source. The ITC
		configuration corresponds to the case where there is at least
		one IMA link whose transmit clock is derived from a source
		different than at least another link transmit clock."
	REFERENCE
		"ATM Forum IMA v1.1, Section 7 on page 38"
	SYNTAX INTEGER{
		ctc(1),
		itc(2) }

ImaGroupSymmetry ::= TEXTUAL-CONVENTION
	STATUS current
	DESCRIPTION
		"The group symmetry mode adjusted during the group start-up."
	REFERENCE
		"ATM Forum IMA v1.1, Section 5.2.2.7 on page 35"
	SYNTAX INTEGER {
		symmetricOperation(1),
		asymmetricOperation(2),
		asymmetricConfiguration(3) }

ImaFrameLength ::= TEXTUAL-CONVENTION
	STATUS current
	DESCRIPTION
		"Length of the IMA frames."
	REFERENCE
		"ATM Forum IMA v1.1, Section 5.2.2.4.2 on page 34"
	SYNTAX INTEGER {
		m32(32),
		m64(64),
		m128(128),
		m256(256) }

-- The IMA Group subtree
-- The IMA Group subtree consists of the number of IMA groups and a
-- table of IMA groups. Each entry in the table of IMA groups contains
-- information (configuration and status) specific to each group.

imaGroupNumber OBJECT-TYPE
	SYNTAX INTEGER  
	MAX-ACCESS read-only
	STATUS current
	DESCRIPTION
		"The number of IMA groups configured on this system."
::= { atmfImaGroupMibObjects 1 }

imaGroupTable OBJECT-TYPE
	SYNTAX SEQUENCE OF ImaGroupEntry
	MAX-ACCESS not-accessible
	STATUS current
	DESCRIPTION
	     "The IMA Group Configuration table."
::= { atmfImaGroupMibObjects 2 }

imaGroupEntry OBJECT-TYPE
	SYNTAX ImaGroupEntry
	MAX-ACCESS not-accessible
	STATUS current
	DESCRIPTION
		"An entry in the IMA Group table."
	INDEX { imaGroupIndex }
::= { imaGroupTable 1 }

ImaGroupEntry ::= SEQUENCE {
	imaGroupIndex           INTEGER,
	imaMemberOfGroup        INTEGER,
	imaGroupRowStatus       RowStatus,
	imaGroupIfIndex         InterfaceIndex,
	imaGroupNeState         ImaGroupState,
	imaGroupFeState         ImaGroupState,
	imaGroupSymmetry        ImaGroupSymmetry,
	imaGroupMinNumTxLinks   INTEGER,
	imaGroupMinNumRxLinks   INTEGER,
	imaGroupNeTxClkMode     ImaGroupTxClkMode,
	imaGroupTxImaId 	INTEGER,
	imaGroupRxImaId 	INTEGER,
	imaGroupTxFrameLength 	ImaFrameLength,
	imaGroupRxFrameLength 	ImaFrameLength,
	imaGroupLeastDelayLink 	INTEGER,
	imaGroupNumTxCfgLinks 	Gauge32,
	imaGroupNumRxCfgLinks 	Gauge32,
	imaGroupNumTxActLinks 	Gauge32,
	imaGroupNumRxActLinks 	Gauge32,
	imaGroupImaVersion    	INTEGER,
	imaGroupGtsmState     	INTEGER,
	imaGroupInhibitStatus   INTEGER,
	imaGroupRxTilLid       	INTEGER,
	imaGroupDiffDelayMaxObs Counter32,
	imaGroupCLKMode		INTEGER
}
	
imaGroupIndex OBJECT-TYPE
	SYNTAX 	   INTEGER
	MAX-ACCESS read-only
	STATUS     current
	DESCRIPTION
	"A unique value for the IMA Group."
::= { imaGroupEntry 1 }

imaMemberOfGroup   OBJECT-TYPE
	SYNTAX     INTEGER
	MAX-ACCESS read-write
	STATUS current
	DESCRIPTION
		"The links of the Group "
::= { imaGroupEntry 2 }

imaGroupRowStatus OBJECT-TYPE
	SYNTAX 		RowStatus
	MAX-ACCESS 	read-create
	STATUS current
	DESCRIPTION
	       "The imaGroupRowStatus object allows create, change, and delete
		operations on imaGroupTable entries.
		To create a new conceptual row (or instance) of the imaGroupTable,
		imaGroupRowStatus must be set to 'createAndWait' or 'createAndGo'.
		If settable, a successful set of the following objects must be
		performed before the imaGroupRowStatus of a new conceptual row can
		be set to 'active':
			imaGroupMinNumTxLinks
			imaGroupMinNumRxLinks
			imaGroupTxImaId
		Some objects in the imaGroupTable control settings which can only
		be established or changed at group start-up time. These objects
		include:
			imaGroupTxImaId
			imaGroupSymmetry
			imaGroupTxFrameLength
		To change (modify) the imaGroupTxImaId object, the manager must
		first set imaGroupRowStatus to 'notInService'. However, changes
		to the following two objects can be optionally allowed while the
			imaGroupRowStatus is 'active':
			imaGroupSymmetry
			imaGroupTxFrameLength
		These two objects can be changed when the imaGroupRowStatus is
		'active' in order to allow the far-end to recover from its
		Config-Aborted state without having to force the near-end Group
		State machine to go to the 'Not Configured' state. Changing
		these object values after group start-up has completed causes a
		restart of the IMA group.
		Alternatively, as noted above, the agent implementation may
		simply require the imaGroupRowStatus object to first be set to
		'notInService' before allowing changes to either of these two
		objects.
			To remove (delete) an imaGroupTable entry from this table, set
		imaGroupRowStatus to 'destroy'.
		Setting the imaGroupRowStatus to 'active' has the effect of
		activating the Group Startup Procedure. The Group Startup
		Procedure uses provisioned links that have imaLinkRowStatus set
		to 'active' and imaLinkGroupIndex set to the imaGroupIndex in
		this conceptual row.
			When the imaGroupRowStatus is not in 'active' state, the Group
		State machine is in its 'Not Configured' state."
::= { imaGroupEntry 3 }

imaGroupIfIndex OBJECT-TYPE
	SYNTAX InterfaceIndex
	MAX-ACCESS read-only
	STATUS current
	DESCRIPTION
		"This object identifies the logical interface number ('ifIndex')
		assigned to this IMA group, and is used to identify corresponding
		rows in the Interfaces MIB.
		Note that re-initialization of the management agent may cause
		a client's 'imaGroupIfIndex' to change."
::= { imaGroupEntry 4 }

imaGroupNeState OBJECT-TYPE
	SYNTAX ImaGroupState
	MAX-ACCESS read-only
	STATUS current
	DESCRIPTION
		"The current operational state of the near-end IMA Group State
	Machine."
	REFERENCE
		"ATM Forum IMA v1.1, Section 10.2.1 on page 55"
::= { imaGroupEntry 5 }

imaGroupFeState OBJECT-TYPE
	SYNTAX ImaGroupState
	MAX-ACCESS read-only
	STATUS current
	DESCRIPTION
		"The current operational state of the far-end IMA Group State
	Machine."
	REFERENCE
		"ATM Forum IMA v1.1, Section 10.2.1 on page 55"
::= { imaGroupEntry 6 }

imaGroupSymmetry OBJECT-TYPE
	SYNTAX ImaGroupSymmetry
	MAX-ACCESS read-only
	STATUS current
	DESCRIPTION
		"Symmetry of the IMA group."
	REFERENCE
	"ATM Forum IMA v1.1, Section 5.2.2.7 on page 35"
		DEFVAL { symmetricOperation }
::= { imaGroupEntry 7 }

imaGroupMinNumTxLinks OBJECT-TYPE
	SYNTAX INTEGER
	MAX-ACCESS read-write
	STATUS current
	DESCRIPTION
		"Minimum number of transmit links required to be Active for
	the IMA group to be in the Operational state."
	REFERENCE
		"ATM Forum IMA v1.1, Section 10.2.1.1 on page 55"
::= { imaGroupEntry 8 }

imaGroupMinNumRxLinks OBJECT-TYPE
	SYNTAX INTEGER
	MAX-ACCESS read-write
	STATUS current
	DESCRIPTION
		"Minimum number of receive links required to be Active for
	the IMA group to be in the Operational state."
	REFERENCE
		"ATM Forum IMA v1.1, Section 10.2.1.1 on page 55"
::= { imaGroupEntry 9 }

imaGroupNeTxClkMode OBJECT-TYPE
	SYNTAX ImaGroupTxClkMode{
	              ctc(1),
	              itc(2)
	}	
	MAX-ACCESS read-write
	STATUS current
	DESCRIPTION
		"Transmit clocking mode used by the near-end IMA group."
	REFERENCE
	"ATM Forum IMA v1.1, Section 7 on page 38"
	DEFVAL { ctc }
::= { imaGroupEntry 10 }

imaGroupTxImaId OBJECT-TYPE
	SYNTAX INTEGER
	MAX-ACCESS read-write
	STATUS current
	DESCRIPTION
		"The IMA ID currently in use by the near-end IMA function."
	REFERENCE
		"ATM Forum IMA v1.1, Section 5.2.2.6 on page 35"
::= { imaGroupEntry 11 }

imaGroupRxImaId OBJECT-TYPE
	SYNTAX INTEGER
	MAX-ACCESS read-only
	STATUS current
	DESCRIPTION
		"The IMA ID currently in use by the far-end IMA function."
	REFERENCE
		"ATM Forum IMA v1.1, Section 5.2.2.6 on page 35"
::= { imaGroupEntry 12 }

imaGroupTxFrameLength OBJECT-TYPE
	SYNTAX ImaFrameLength
	MAX-ACCESS read-write
	STATUS current
	DESCRIPTION
		"The frame length to be used by the IMA group in the transmit
	direction. Can only be set when the IMA group is startup."
	REFERENCE
		"ATM Forum IMA v1.1, Section 5.2.2.4.2 on page 34"
	DEFVAL { m128 }
::= { imaGroupEntry 13 }

imaGroupRxFrameLength OBJECT-TYPE
	SYNTAX ImaFrameLength
	MAX-ACCESS read-only
	STATUS current
	DESCRIPTION
		"Value of IMA frame length as received from remote IMA function."
	REFERENCE
		"ATM Forum IMA v1.1, Section 5.2.2.4.2 on page 34"
::= { imaGroupEntry 14 }

imaGroupLeastDelayLink OBJECT-TYPE
	SYNTAX INTEGER
	MAX-ACCESS read-only
	STATUS current
	DESCRIPTION
		"The ifIndex of the link configured in the IMA group which has
	the smallest link propagation delay. The distinguished value of
	zero may be used if no link has been configured in the IMA group,
	or if the link with the smallest link propagation delay has not
	yet been determined."
	REFERENCE
		"ATM Forum IMA v1.1, Section 9.2 on page 45"
::= { imaGroupEntry 15 }

imaGroupNumTxCfgLinks OBJECT-TYPE
	SYNTAX Gauge32
	MAX-ACCESS read-only
	STATUS current
	DESCRIPTION
		"The number of links that are configured to transmit in this IMA
	group. This attribute overwrites the value of the
	imaGroupNumRxActLinks attribute when the IMA group is configured
	in the Symmetrical Configuration group symmetry mode."
::= { imaGroupEntry 16 }

imaGroupNumRxCfgLinks OBJECT-TYPE
	SYNTAX Gauge32
	MAX-ACCESS read-only
	STATUS current
	DESCRIPTION
		"The number of links that are configured to receive in this IMA
	group. This attribute is overwritten by the value of the
	imaGroupNumTxActLinks attribute when the IMA group is configured
	in the Symmetrical Configuration group symmetry mode."
::= { imaGroupEntry 17 }

imaGroupNumTxActLinks OBJECT-TYPE
	SYNTAX Gauge32
	MAX-ACCESS read-only
	STATUS current
	DESCRIPTION
		"The number of links which are configured to transmit and are
	currently Active in this IMA group."
::= { imaGroupEntry 18 }

imaGroupNumRxActLinks OBJECT-TYPE
	SYNTAX Gauge32
	MAX-ACCESS read-only
	STATUS current
	DESCRIPTION
		"The number of links which are configured to receive and are
	currently Active in this IMA group."
::= { imaGroupEntry 19 }

imaGroupImaVersion OBJECT-TYPE
	SYNTAX     INTEGER{ 
	                    version10(0),
	                    version11(1)
	}
	MAX-ACCESS read-write
	STATUS current
	DESCRIPTION
		"The version of Group  "
::= { imaGroupEntry 20 }

imaGroupGtsmState OBJECT-TYPE
	SYNTAX     INTEGER
	MAX-ACCESS read-only
	STATUS current
	DESCRIPTION
		"The state of Group "
::= { imaGroupEntry 21 }

imaGroupInhibitStatus OBJECT-TYPE
	SYNTAX     INTEGER{
	                   up(1),
	                 down(2)
	}
	MAX-ACCESS read-write
	STATUS current
	DESCRIPTION
		"The state of Group  "
::= { imaGroupEntry 22 }

imaGroupRxTilLid OBJECT-TYPE
	SYNTAX     INTEGER
	MAX-ACCESS read-only
	STATUS current
	DESCRIPTION
		" "
::= { imaGroupEntry 23 }

imaGroupDiffDelayMaxObs OBJECT-TYPE
	SYNTAX     Counter32 
	MAX-ACCESS read-only
	STATUS current
	DESCRIPTION
		" The latest maximum differential delay observed (in milliseconds)
	between the links having the least and most link propagation delay,
	among the receive links that are currently configured in the IMA
	group."
::= { imaGroupEntry 24 }

imaGroupCLKMode   OBJECT-TYPE
	SYNTAX     INTEGER{
			master(0),
			 slave(1)
	}
	MAX-ACCESS read-write
	STATUS current
	DESCRIPTION
		"The clock mode of the Group "
::= { imaGroupEntry 25 }

-- IMA Failure Alarms
-- Implementation of the imaFailureAlarm Trap is optional.
imaAlarmStatus OBJECT-TYPE
	SYNTAX ImaAlarmStatus
	MAX-ACCESS accessible-for-notify
	STATUS current
	DESCRIPTION
		"Status of the IMA alarm."
::= { atmfImaGroupMibObjects 3 }

imaAlarmType OBJECT-TYPE
	SYNTAX ImaAlarmType
	MAX-ACCESS accessible-for-notify
	STATUS current
	DESCRIPTION
		"The Type of IMA alarm declared or cleared. The value of
	ImaAlarmType identifies the type of alarm according to the
	definitions in the IMA specification."
	REFERENCE
		"ATM Forum IMA v1.1, Section 12.2.3 on page 79"
::= { atmfImaGroupMibObjects 4 }

imaFailureAlarm NOTIFICATION-TYPE
	OBJECTS {
		ifIndex,
		imaAlarmStatus,
		imaAlarmType }
	STATUS current
	DESCRIPTION
		"The imaFailureAlarm provides a method for an agent implementing IMA
	to notify an NMS of an alarm condition."
	REFERENCE
		"ATM Forum IMA v1.1, Section 12.2.3 on page 79"
::= { atmfImaMibTrapPrefix 1 }

-- The IMA Group Current Statistics subtree
-- The IMA Group Current Statistics subtree consists of a single table:
-- the IMA Group Current Table.    This table contains various statistics
-- collected by each IMA group for the current 15 minute interval.
-- Implementation of IMA Group Current Table is optional.
imaGroupCurrentTable OBJECT-TYPE
           SYNTAX         SEQUENCE OF ImaGroupCurrentEntry
           MAX-ACCESS    not-accessible
           STATUS         current
           DESCRIPTION
              " The IMA Group Current table."
           ::=  {atmfImaGroupMibObjects 5 }

imaGroupCurrentEntry OBJECT-TYPE
           SYNTAX           ImaGroupCurrentEntry
           MAX-ACCESS      not-accessible
           STATUS           current
           DESCRIPTION
              " An entry in the IMA Group Current table."
           INDEX      {imaGroupIndex }
           ::= { imaGroupCurrentTable 1 }

ImaGroupCurrentEntry ::= SEQUENCE{ 
          imaGroupCurrentTxDiscardedCells   Gauge32,
          imaGroupCurrentTxCells            Gauge32,
          imaGroupCurrentTxFillerCells      Gauge32,
          imaGroupCurrentRxCells            Gauge32,
          imaGroupCurrentRxDroppedCells     Gauge32,
          imaGroupCurrentRxFilleredCells    Gauge32,
          imaGroupCurrentRxFillerCells      Gauge32}
                              
                    
imaGroupCurrentTxDiscardedCells OBJECT-TYPE
           SYNTAX         Gauge32
           MAX-ACCESS    read-only
           STATUS         current
           DESCRIPTION
              "The current value of Group TxDiscardedCells"
           REFERENCE
              " "
           ::=  {imaGroupCurrentEntry 1}

imaGroupCurrentTxCells    OBJECT-TYPE
           SYNTAX         Gauge32
           MAX-ACCESS    read-only
           STATUS         current
           DESCRIPTION
              " The current value of Group TxCells"
           REFERENCE
              " "
           ::=  {imaGroupCurrentEntry 2}
           
imaGroupCurrentTxFillerCells    OBJECT-TYPE
           SYNTAX         Gauge32
           MAX-ACCESS    read-only
           STATUS         current
           DESCRIPTION
              " The current value of Group RxFillerCells"
           REFERENCE
              " "
           ::=  {imaGroupCurrentEntry 3}
           
imaGroupCurrentRxCells    OBJECT-TYPE
           SYNTAX         Gauge32
           MAX-ACCESS    read-only
           STATUS         current
           DESCRIPTION
              " "
           REFERENCE
              " The current value of Group RxCells"
           ::=  {imaGroupCurrentEntry 4}           
           
imaGroupCurrentRxDroppedCells    OBJECT-TYPE
           SYNTAX         Gauge32
           MAX-ACCESS    read-only
           STATUS         current
           DESCRIPTION
              " The current value of Group DroppedCells"
           REFERENCE
              " "
           ::=  {imaGroupCurrentEntry 5}             

imaGroupCurrentRxFilleredCells    OBJECT-TYPE
           SYNTAX         Gauge32
           MAX-ACCESS    read-only
           STATUS         current
           DESCRIPTION
              " The current value of Group FilleredCells"
           REFERENCE
              " "
           ::=  {imaGroupCurrentEntry 6} 
           
           
imaGroupCurrentRxFillerCells    OBJECT-TYPE
           SYNTAX         Gauge32
           MAX-ACCESS    read-only
           STATUS         current
           DESCRIPTION
              " The current value of Group RxFillerCells"
           REFERENCE
              " "
           ::=  {imaGroupCurrentEntry 7}
           
           
-- The IMA Group Interval Statistics subtree
-- The IMA Group Interval Statistics subtree consists of a single table:
-- the IMA Group Interval Table. This table contains various statistics
-- collected by each IMA group over the previous 24 hours of operation.
-- The past 24 hours are broken into 96 completed 15 minute intervals.
-- Implementation of IMA Group Interval Table is optional.

imaGroupIntervalTable OBJECT-TYPE
	SYNTAX SEQUENCE OF ImaGroupIntervalEntry
	MAX-ACCESS not-accessible
	STATUS current
	DESCRIPTION
		"The IMA Group Interval table."
::= { atmfImaGroupMibObjects 6 }

imaGroupIntervalEntry OBJECT-TYPE
	SYNTAX ImaGroupIntervalEntry
	MAX-ACCESS not-accessible
	STATUS current
	DESCRIPTION
		"An entry in the IMA Group Interval table."
	INDEX { imaGroupIndex, imaGroupIntervalNumber }
::= { imaGroupIntervalTable 1 }

ImaGroupIntervalEntry ::= SEQUENCE{
	imaGroupIntervalNumber               INTEGER,
	imaGroupIntervalTxDiscardedCells     Gauge32,
	imaGroupIntervalTxCells              Gauge32,
	imaGroupIntervalTxFillerCells        Gauge32,
	imaGroupIntervalRxCells              Gauge32,
	imaGroupIntervalRxDroppedCells       Gauge32,
	imaGroupIntervalRxFilleredCells      Gauge32,
	imaGroupIntervalRxFillerCells        Gauge32}
			
imaGroupIntervalNumber OBJECT-TYPE
	SYNTAX INTEGER
	MAX-ACCESS read-only
	STATUS current
	DESCRIPTION
		"A number between 1 and 96, where 1 is the most
	recently completed 15 minute interval and 96 is the least
	recently completed 15 minutes interval (assuming that all
	96 intervals are valid)."
::= { imaGroupIntervalEntry 1 }

imaGroupIntervalTxDiscardedCells OBJECT-TYPE
	SYNTAX    Gauge32
	MAX-ACCESS read-only
	STATUS current
	DESCRIPTION
		" A number between 1 and 96, where 1 is the most
	recently completed 15 minute interval and 96 is the least
	recently completed 15 minutes interval (assuming that all
	96 intervals are valid)."
::= { imaGroupIntervalEntry 2 }

imaGroupIntervalTxCells     OBJECT-TYPE
	SYNTAX    Gauge32
	MAX-ACCESS read-only
	STATUS current
	DESCRIPTION
		" A number between 1 and 96, where 1 is the most
	recently completed 15 minute interval and 96 is the least
	recently completed 15 minutes interval (assuming that all
	96 intervals are valid)."
::= { imaGroupIntervalEntry 3 }

imaGroupIntervalTxFillerCells     OBJECT-TYPE
	SYNTAX    Gauge32
	MAX-ACCESS read-only
	STATUS current
	DESCRIPTION
		"A number between 1 and 96, where 1 is the most
	recently completed 15 minute interval and 96 is the least
	recently completed 15 minutes interval (assuming that all
	96 intervals are valid). "
::= { imaGroupIntervalEntry 4 }


imaGroupIntervalRxCells           OBJECT-TYPE
	SYNTAX    Gauge32
	MAX-ACCESS read-only
	STATUS current
	DESCRIPTION
		"A number between 1 and 96, where 1 is the most
	recently completed 15 minute interval and 96 is the least
	recently completed 15 minutes interval (assuming that all
	96 intervals are valid). "
::= { imaGroupIntervalEntry 5 }


imaGroupIntervalRxDroppedCells    OBJECT-TYPE
	SYNTAX    Gauge32
	MAX-ACCESS read-only
	STATUS current
	DESCRIPTION
		" A number between 1 and 96, where 1 is the most
	recently completed 15 minute interval and 96 is the least
	recently completed 15 minutes interval (assuming that all
	96 intervals are valid)."
::= { imaGroupIntervalEntry 6 }

imaGroupIntervalRxFilleredCells    OBJECT-TYPE
	SYNTAX    Gauge32
	MAX-ACCESS read-only
	STATUS current
	DESCRIPTION
		" A number between 1 and 96, where 1 is the most
	recently completed 15 minute interval and 96 is the least
	recently completed 15 minutes interval (assuming that all
	96 intervals are valid)."
::= { imaGroupIntervalEntry 7 }

imaGroupIntervalRxFillerCells    OBJECT-TYPE
	SYNTAX    Gauge32
	MAX-ACCESS read-only
	STATUS current
	DESCRIPTION
		" A number between 1 and 96, where 1 is the most
	recently completed 15 minute interval and 96 is the least
	recently completed 15 minutes interval (assuming that all
	96 intervals are valid)."
::= { imaGroupIntervalEntry 8 }

-- The IMA Group Total Statistics subtree
-- The IMA Group Total Statistics subtree consists of a single table:
-- the IMA Group Total Table. This table contains various statistics
-- collected by each IMA group over the previous 24 hours of operation.
-- The past 24 hours are broken into 96 completed 15 minute intervals.
-- Implementation of IMA Group Interval Table is optional.

imaGroupTotalTable OBJECT-TYPE
	SYNTAX SEQUENCE OF ImaGroupTotalEntry
	MAX-ACCESS not-accessible
	STATUS current
	DESCRIPTION
		"The IMA Group Total table."
::= { atmfImaGroupMibObjects 7 }

imaGroupTotalEntry OBJECT-TYPE
	SYNTAX ImaGroupTotalEntry
	MAX-ACCESS not-accessible
	STATUS current
	DESCRIPTION
		"An entry in the IMA Group Total table."
	INDEX { imaGroupIndex }
::= { imaGroupTotalTable 1 }

ImaGroupTotalEntry ::= SEQUENCE{
	imaGroupTotalTxDiscardedCells     Gauge32,
	imaGroupTotalTxCells              Gauge32,
	imaGroupTotalTxFillerCells        Gauge32,
	imaGroupTotalRxCells              Gauge32,
	imaGroupTotalRxDroppedCells       Gauge32,
	imaGroupTotalRxFilleredCells      Gauge32,
	imaGroupTotalRxFillerCells        Gauge32}
			
imaGroupTotalTxDiscardedCells OBJECT-TYPE
	SYNTAX    Gauge32
	MAX-ACCESS read-only
	STATUS current
	DESCRIPTION
		" The Total value of Group TxDiscardedCells"
::= { imaGroupTotalEntry 1 }

imaGroupTotalTxCells     OBJECT-TYPE
	SYNTAX    Gauge32
	MAX-ACCESS read-only
	STATUS current
	DESCRIPTION
		" The Total value of Group TxCells"
::= { imaGroupTotalEntry 2 }

imaGroupTotalTxFillerCells     OBJECT-TYPE
	SYNTAX    Gauge32
	MAX-ACCESS read-only
	STATUS current
	DESCRIPTION
		" The Total value of Group TxFillerCells"
::= { imaGroupTotalEntry 3 }


imaGroupTotalRxCells           OBJECT-TYPE
	SYNTAX    Gauge32
	MAX-ACCESS read-only
	STATUS current
	DESCRIPTION
		" The Total value of Group RxCells"
::= { imaGroupTotalEntry 4 }


imaGroupTotalRxDroppedCells    OBJECT-TYPE
	SYNTAX    Gauge32
	MAX-ACCESS read-only
	STATUS current
	DESCRIPTION
		" The Total value of Group RxDroppedCells"
::= { imaGroupTotalEntry 5 }

imaGroupTotalRxFilleredCells    OBJECT-TYPE
	SYNTAX    Gauge32
	MAX-ACCESS read-only
	STATUS current
	DESCRIPTION
		" The Total value of Group RxFilleredCells"
::= { imaGroupTotalEntry 6 }

imaGroupTotalRxFillerCells    OBJECT-TYPE
	SYNTAX    Gauge32
	MAX-ACCESS read-only
	STATUS current
	DESCRIPTION
		"The Total value of Group RxFillerCells "
::= { imaGroupTotalEntry 7 }

imaSlotStand  OBJECT-TYPE
	SYNTAX INTEGER
	MAX-ACCESS read-only
	STATUS current
	DESCRIPTION
		"the slot of ima in the dislam"
::= { atmfImaGroupMibObjects 8 }

--  units of conformance
imaGroupNumberGroup OBJECT-GROUP
  OBJECTS{
     imaGroupNumber
  }
 STATUS  current
 DESCRIPTION 
       "imaGroupNumber group"
 ::={atmfImaGroupGroups 1}
 
 imaGroupGroup OBJECT-GROUP
  OBJECTS{ 
    	imaGroupNumber,
	imaMemberOfGroup,
	imaGroupRowStatus,
	imaGroupIfIndex,
	imaGroupNeState,
	imaGroupFeState,
	imaGroupSymmetry,
	imaGroupMinNumTxLinks,
	imaGroupMinNumRxLinks,
	imaGroupNeTxClkMode,
	imaGroupTxImaId,
	imaGroupRxImaId,
	imaGroupTxFrameLength,
	imaGroupRxFrameLength ,
	imaGroupLeastDelayLink,
	imaGroupNumTxCfgLinks ,
	imaGroupNumRxCfgLinks ,
	imaGroupNumTxActLinks ,
	imaGroupNumRxActLinks ,
	imaGroupImaVersion    ,
	imaGroupGtsmState     ,
	imaGroupInhibitStatus   ,
	imaGroupRxTilLid       	 ,
	imaGroupDiffDelayMaxObs  ,
	imaGroupCLKMode 
}    
       STATUS          current
       DESCRIPTION
              " A set of objects providing configuration and status information for
              an IMA group definition."
       ::=  {atmfImaGroupGroups 2 }
       
   imaAlarmGroup OBJECT-GROUP
           OBJECTS {
              imaAlarmStatus,
              imaAlarmType }
           STATUS          current
           DESCRIPTION
              " Objects used in the imaFailureAlarm notification."
   ::=  {atmfImaGroupGroups 3}
   
   imaGroupCurrentGroup OBJECT-GROUP
   OBJECTS{
          imaGroupCurrentTxDiscardedCells   ,
          imaGroupCurrentTxCells            ,
          imaGroupCurrentTxFillerCells      ,
          imaGroupCurrentRxCells            ,
          imaGroupCurrentRxDroppedCells     ,
          imaGroupCurrentRxFilleredCells    ,
          imaGroupCurrentRxFillerCells}
        STATUS          current
        DESCRIPTION
              " Objects containing current statistics for an IMA group."
           ::=  {atmfImaGroupGroups 4} 

   imaGroupIntervalGroup OBJECT-GROUP
      OBJECTS{
        imaGroupIntervalNumber        ,
	imaGroupIntervalTxDiscardedCells     ,
	imaGroupIntervalTxCells              ,
	imaGroupIntervalTxFillerCells        ,
	imaGroupIntervalRxCells              ,
	imaGroupIntervalRxDroppedCells       ,
	imaGroupIntervalRxFilleredCells      ,
	imaGroupIntervalRxFillerCells }       
        STATUS          current
        DESCRIPTION
              " Objects containing interval statistics for an IMA group."
           ::=  {atmfImaGroupGroups 5}  
  
  imaGroupTotalGroup OBJECT-GROUP
     OBJECTS{ 
    	imaGroupTotalTxDiscardedCells     ,
		imaGroupTotalTxCells              ,
		imaGroupTotalTxFillerCells        ,
		imaGroupTotalRxCells              ,
		imaGroupTotalRxDroppedCells       ,
		imaGroupTotalRxFilleredCells      ,
		imaGroupTotalRxFillerCells  }
            STATUS          current
        DESCRIPTION
              " Objects containing total statistics for an IMA group."
           ::=  {atmfImaGroupGroups 6}  
 
     imaNotificationsGroup NOTIFICATION-GROUP
          NOTIFICATIONS 
             {imaFailureAlarm}
          STATUS          current
          DESCRIPTION
              " Notifications that must be implemented for IMA groups and links."
           ::=  {atmfImaGroupGroups 7} 
           
	imaSlotStandGroup OBJECT-GROUP
  	OBJECTS{
     			imaSlotStand
  		}
 	STATUS  current
 	DESCRIPTION 
              " Objects used in the imaGroup."
   ::=  {atmfImaGroupGroups 8}


                         
--  compliance statements
    atmfImaMibCompliance MODULE-COMPLIANCE
    STATUS  current
    DESCRIPTION
           "The compliance statement."
    MODULE  -- this module
    MANDATORY-GROUPS{
            imaGroupNumberGroup,
            imaGroupGroup,
            imaAlarmGroup,
            imaGroupCurrentGroup,
            imaGroupIntervalGroup,
            imaGroupTotalGroup,
            imaNotificationsGroup,
            imaSlotStandGroup
            }
        ::= { atmfImaGroupCompliances 1 }
END

 
 IMA-SYS-MIB DEFINITIONS ::= BEGIN
     IMPORTS
        MODULE-IDENTITY, OBJECT-TYPE,
        Counter32, Gauge32,
        Unsigned32, Integer32                  FROM SNMPv2-SMI
        
        RowStatus, TruthValue, 
        DisplayString, MacAddress               FROM SNMPv2-TC
       
        MODULE-COMPLIANCE, OBJECT-GROUP         FROM SNMPv2-CONF
        
        zxIma     	                        FROM WRS-MASTER-MIB;

 	
  atmfImaSysMib MODULE-IDENTITY
		LAST-UPDATED "9902111830Z"
		ORGANIZATION "The ATM Forum"
		CONTACT-INFO
			"ATM Forum	World Headquarters
			2570 West El Camino Real
			Suite 304 Mountain View, CA 94040-1313
			USA
			Phone: +1 415 949 6700
			Fax: +1 415 949 6705
			email: info@atmforum.com"
		DESCRIPTION
				"The MIB module for managing ATM Forum Inverse Multiplexing
			for ATM (IMA) interfaces."
			REVISION "9902111830Z"
		DESCRIPTION
				"Updated and repaired version of the IMA-MIB released with the
			IMA v1.1 specification (af-phy-0086.001)."
			REVISION "9701092245Z"
		DESCRIPTION
			"Initial incomplete version of the IMA-MIB as published in the
		IMA v1.0 specification (af-phy-0086.000)."
	::= { zxIma 1 }

-- The object identifier subtree for the IMA-MIB.

atmfImaSysMibObjects    OBJECT IDENTIFIER ::= { atmfImaSysMib 1 }
atmfImaSysMibConformance OBJECT IDENTIFIER ::= { atmfImaSysMib 2 }

atmfImaSysGroups         OBJECT IDENTIFIER ::= { atmfImaSysMibConformance 1}
atmfImaSysCompliances    OBJECT IDENTIFIER ::= { atmfImaSysMibConformance 2 }

imaSysMaxSupportedGroupNumber OBJECT-TYPE
	SYNTAX Integer32
	MAX-ACCESS read-only
	STATUS current
	DESCRIPTION
		"The max number of IMA groups supported in this system
	the default value:16 "
::= { atmfImaSysMibObjects 1 }

imaSysMaxSupportedLinkNumber OBJECT-TYPE
	SYNTAX Integer32
	MAX-ACCESS read-only
	STATUS current
	DESCRIPTION
		"The max number of IMA Links supported in this system
	the default value:16 "
::= { atmfImaSysMibObjects 2 }

imaSysSaveCommand OBJECT-TYPE
	SYNTAX INTEGER{
		noop(1),            -- no operation
                save(2),           -- save the data into flash
               inProgress(3)       -- read-only: process in progress
	}
	MAX-ACCESS read-write
	STATUS current
	DESCRIPTION
		"save  the data in the flash
	the default value:1 "
::= { atmfImaSysMibObjects 3 }

imaSysClearCommand OBJECT-TYPE
	SYNTAX INTEGER{
		noop(1),            -- no operation
                clear(2),           -- clear the data in flash
               inProgress(3)       -- read-only: process in progress
	}
	MAX-ACCESS read-write
	STATUS current
	DESCRIPTION
		"clear the data in the flash
	the default value:1 "
::= { atmfImaSysMibObjects 4 }

imaSysResetCommand OBJECT-TYPE
	SYNTAX INTEGER{
		noop(1),            -- no operation
                reset(2)           -- resets the unit
	}
	MAX-ACCESS read-write
	STATUS current
	DESCRIPTION
		"performs a hardware reset of the unit
	the default value:1 "
::= { atmfImaSysMibObjects 5 }

--the IMA system configuration MIB 
--
-- The IMA system subtree

imaSystemConfigurationTable OBJECT-TYPE
	SYNTAX SEQUENCE OF ImaSystemConfigurationEntry
	MAX-ACCESS not-accessible
	STATUS current
	DESCRIPTION
		"The system configuration table."
::= { atmfImaSysMibObjects 6 }

imaSystemConfigurationEntry OBJECT-TYPE
	SYNTAX ImaSystemConfigurationEntry
	MAX-ACCESS not-accessible
	STATUS current
	DESCRIPTION
		"An entry in the system configuration table."
	INDEX { imaSysIndex }
::= { imaSystemConfigurationTable 1 }

ImaSystemConfigurationEntry ::= SEQUENCE {
	imaSysIndex                 Integer32,
	imaSysAlphaValue            Integer32,
	imaSysBetaValue     	    Integer32,
	imaSysToutStartUpAck        Integer32,
	imaSysToutGrpCfgAbort       Integer32,
	imaSysToutRxUsable          Integer32,
	imaSysToutRxActive          Integer32,
	imaSysToutTxActive          Integer32,
	imaSysToutTxLinkDel         Integer32,
	imaSysToutRxLinkBlk         Integer32,
	imaSysToutRxLinkDel         Integer32,
	imaSysGamma                 Integer32,
	imaSysTimeTickCfg           Integer32
	}

imaSysIndex OBJECT-TYPE
	SYNTAX Integer32
	MAX-ACCESS read-only
	STATUS current
	DESCRIPTION
	    "A unique value for the IMA SystemGroup."
::= { imaSystemConfigurationEntry 1 }

imaSysAlphaValue OBJECT-TYPE
	SYNTAX Integer32
	MAX-ACCESS read-only
	STATUS current
	DESCRIPTION
	       "IFSM parameter of IMA system "
::= { imaSystemConfigurationEntry 2 }

imaSysBetaValue OBJECT-TYPE
	SYNTAX Integer32
	MAX-ACCESS read-only
	STATUS current
	DESCRIPTION
		"IFSM parameter of the IMA system "
::= { imaSystemConfigurationEntry 3 }

imaSysToutStartUpAck OBJECT-TYPE
	SYNTAX Integer32
	MAX-ACCESS read-only
	STATUS current
	DESCRIPTION
		"Determines how long GSM stays in 
	Startup-Ack state before moving back to Startup state(0-15) "
::= { imaSystemConfigurationEntry 4 }

imaSysToutGrpCfgAbort OBJECT-TYPE
	SYNTAX Integer32
	MAX-ACCESS read-only
	STATUS current
	DESCRIPTION
		"Determines how long GSM stays in Config-Aborted state
	before moving back to Startup state (0-15) "
::= { imaSystemConfigurationEntry 5 }


imaSysToutRxUsable OBJECT-TYPE
	SYNTAX Integer32
	MAX-ACCESS read-only
	STATUS current
	DESCRIPTION
		"Determine when a Group startup/LASR procedure times out 
	if RX links don't become usable "
::= { imaSystemConfigurationEntry 6 }

imaSysToutRxActive OBJECT-TYPE
	SYNTAX Integer32
	MAX-ACCESS read-only
	STATUS current
	DESCRIPTION
		"Determine when a Group startup/LASR procedure times out 
	if RX links don't move from usable to active state (0-15)"
::= { imaSystemConfigurationEntry 7 }

imaSysToutTxActive OBJECT-TYPE
	SYNTAX Integer32
	MAX-ACCESS read-only
	STATUS current
	DESCRIPTION
		"Determines how much time should elapse before moving TX 
	LSMs to active state in Group Startup/LASR procedures (0-15) "
::= { imaSystemConfigurationEntry 8}

imaSysToutTxLinkDel OBJECT-TYPE
	SYNTAX Integer32
	MAX-ACCESS read-only
	STATUS current
	DESCRIPTION
		"Determines how long the TX LSM should stay in deleted 
        state before it can move to unassigned state (0-15) "
::= { imaSystemConfigurationEntry 9}

imaSysToutRxLinkBlk OBJECT-TYPE
	SYNTAX Integer32
	MAX-ACCESS read-only
	STATUS current
	DESCRIPTION
		"Determines how long the RX LSM should stay in blocked 
	state before it can move to unusable state (0-15) "
::= { imaSystemConfigurationEntry 10}

imaSysToutRxLinkDel OBJECT-TYPE
	SYNTAX Integer32
	MAX-ACCESS read-only
	STATUS current
	DESCRIPTION
		"Determines how long the RX LSM should stay in deleted
	state before it can move to unassigned state (0-15) "
::= { imaSystemConfigurationEntry 11}

imaSysGamma OBJECT-TYPE
	SYNTAX     Integer32
	MAX-ACCESS read-only
	STATUS current
	DESCRIPTION
		"IFSM parameter(1-5)"
::= { imaSystemConfigurationEntry 12}

imaSysTimeTickCfg OBJECT-TYPE
	SYNTAX     Integer32
	MAX-ACCESS read-only
	STATUS current
	DESCRIPTION
		"Timer tick interval (divisor) (0-0xffff)"
::= { imaSystemConfigurationEntry 13}


--  units of conformance
--  add part of self_definition
          
  imaSysMaxSupportedGroupNumberGroup  OBJECT-GROUP
        OBJECTS {
            imaSysMaxSupportedGroupNumber        
        }
        STATUS  current
        DESCRIPTION
           "lanGenericObjects group "
        ::= { atmfImaSysGroups 1 }
        
   imaSysMaxSupportedLinkNumberGroup   OBJECT-GROUP
        OBJECTS {
            imaSysMaxSupportedLinkNumber        
        }
        STATUS  current
        DESCRIPTION
           "lanGenericObjects group "
        ::= { atmfImaSysGroups 2 }
        
   imaSysSaveCommandGroup  OBJECT-GROUP
        OBJECTS{
            imaSysSaveCommand        
        }
        STATUS  current
        DESCRIPTION
           " "
        ::= { atmfImaSysGroups 3 }
     
     imaSysClearCommandGroup  OBJECT-GROUP
        OBJECTS{
            imaSysClearCommand        
        }
        STATUS  current
        DESCRIPTION
           " "
        ::= { atmfImaSysGroups 4 }
        
      imaSysResetCommandGroup  OBJECT-GROUP
        OBJECTS{
            imaSysResetCommand        
        }
        STATUS  current
        DESCRIPTION
           " "
        ::= { atmfImaSysGroups 5 }	
        
   imaSystemConfigurationGroup  OBJECT-GROUP
    OBJECTS 
    {
		imaSysAlphaValue            ,
		imaSysBetaValue     	    ,
		imaSysToutStartUpAck        ,
		imaSysToutGrpCfgAbort       ,
		imaSysToutRxUsable          ,
		imaSysToutRxActive          ,
		imaSysToutTxActive          ,
		imaSysToutTxLinkDel         ,
		imaSysToutRxLinkBlk         ,
		imaSysToutRxLinkDel         ,
		imaSysGamma                 ,
		imaSysTimeTickCfg}           
	
	STATUS          current
    DESCRIPTION
              " Objects containing system configuration of IMA link."
::=  {atmfImaSysGroups 6} 
           
--  compliance statements

    atmfImaSysMibCompliance MODULE-COMPLIANCE
    STATUS  current
    DESCRIPTION
           "The compliance statement."
    MODULE  -- this module
    MANDATORY-GROUPS {
                  imaSysMaxSupportedGroupNumberGroup,
                  imaSysMaxSupportedLinkNumberGroup,
                  imaSysSaveCommandGroup,
                  imaSysClearCommandGroup,
                  imaSysResetCommandGroup,	
                  imaSystemConfigurationGroup}
       ::= { atmfImaSysCompliances 1 }
        
END
 
 IMA-LINK-MIB DEFINITIONS ::= BEGIN

 IMPORTS
  	MODULE-IDENTITY, OBJECT-TYPE, Integer32, Counter32, Gauge32,
	NOTIFICATION-TYPE, enterprises
		FROM SNMPv2-SMI
	MODULE-COMPLIANCE, OBJECT-GROUP, NOTIFICATION-GROUP
		FROM SNMPv2-CONF
	TEXTUAL-CONVENTION, DateAndTime, RowStatus
		FROM SNMPv2-TC
	InterfaceIndex, InterfaceIndexOrZero, ifIndex
		FROM IF-MIB
	zxIma     	  FROM WRS-MASTER-MIB;

atmfImaLinkMib MODULE-IDENTITY
	LAST-UPDATED "9902111830Z"
	ORGANIZATION "The ATM Forum"
	CONTACT-INFO
		"ATM Forum
		World Headquarters
		2570 West El Camino Real
		Suite 304
		Mountain View, CA 94040-1313
		USA
		Phone: +1 415 949 6700
		Fax: +1 415 949 6705
		email: info@atmforum.com"
	DESCRIPTION
		"The MIB module for managing ATM Forum Inverse Multiplexing
		for ATM (IMA) interfaces."
	REVISION "9902111830Z"
	DESCRIPTION
		"Updated and repaired version of the IMA-MIB released with the
		IMA v1.1 specification (af-phy-0086.001)."
	REVISION "9701092245Z"
	DESCRIPTION
		"Initial incomplete version of the IMA-MIB as published in the
		IMA v1.0 specification (af-phy-0086.000)."
	::= { zxIma 3 }

-- The object identifier subtree for the IMA-MIB.


atmfImaLinkMibObjects OBJECT IDENTIFIER ::= { atmfImaLinkMib 1 }
atmfImaMibGroupConformance OBJECT IDENTIFIER ::= { atmfImaLinkMib 2 }
atmfImaLinkGroups          OBJECT IDENTIFIER ::= { atmfImaMibGroupConformance 1}
atmfImaLinkCompliances     OBJECT IDENTIFIER ::= { atmfImaMibGroupConformance 2 }


-- Textual conventions		
ImaLinkState ::= TEXTUAL-CONVENTION
	STATUS current
	DESCRIPTION
		"State of a link belonging to an IMA group."
	REFERENCE
		"ATM Forum IMA v1.1, Section 10.1.2 on page 48"
	SYNTAX INTEGER {
		notInGroup(1),
		unusableNoGivenReason(2),
		unusableFault(3),
		unusableMisconnected(4),
		unusableInhibited(5),
		unusableFailed(6),
		usable(7),
		active(8) }

-- The IMA Link subtree
-- The IMA Link subtree consists of a table of IMA links. Each entry
-- in the table contains status information about a link which is part
-- of an IMA group, and also contains a configuration object to select
-- to which IMA group the link belongs.

imaLinkTable   OBJECT-TYPE
	SYNTAX SEQUENCE OF ImaLinkEntry
	MAX-ACCESS not-accessible
	STATUS current
	DESCRIPTION
	   "The IMA group Link Status and Configuration table."
::= { atmfImaLinkMibObjects 1 }

imaLinkEntry OBJECT-TYPE
	SYNTAX ImaLinkEntry
	MAX-ACCESS not-accessible
	STATUS current
	DESCRIPTION
		"An entry in the IMA Group Link table."
	INDEX { imaLinkIfIndex }
::= { imaLinkTable 1 }

ImaLinkEntry ::= SEQUENCE {
	imaLinkIfIndex    InterfaceIndex,
	imaLinkRowStatus  RowStatus,
	imaLinkGroupIndex INTEGER,
	imaLinkNeTxState  ImaLinkState,
	imaLinkNeRxState  ImaLinkState,
	imaLinkFeTxState  ImaLinkState,
	imaLinkFeRxState  ImaLinkState,
	imaLinkTxLid INTEGER,
	imaLinkRxLid INTEGER,
    	imaLinkIcpOffset       INTEGER,
    	imaLinkPhyLink      INTEGER,
	imaLinkScramble   INTEGER
}
		
imaLinkIfIndex OBJECT-TYPE
	SYNTAX InterfaceIndex
	MAX-ACCESS  read-only
	STATUS current
	DESCRIPTION
		"This corresponds to the 'ifIndex' of the MIB-II interface
	on which this link is established. This object also
	corresponds to the logical number ('ifIndex') assigned to
	this IMA link."
::= { imaLinkEntry 1 }

imaLinkRowStatus OBJECT-TYPE
	SYNTAX RowStatus
	MAX-ACCESS read-only
	STATUS current
	DESCRIPTION
		"The imaLinkRowStatus object allows create, change, and delete
	operations on imaLinkTable entries.
	To create a new conceptual row (or instance) of the imaLinkTable,
	imaLinkRowStatus must be set to 'createAndWait' or 'createAndGo'.
	A successful set of the imaLinkGroupIndex object must be performed
	before the imaLinkRowStatus of a new conceptual row can be set to
	'active'.
		To change (modify) the imaLinkGroupIndex in an imaLinkTable entry,
	the imaLinkRowStatus object must first be set to 'notInService'.
	Only then can this object in the conceptual row be modified.
	This is due to the fact that the imaLinkGroupIndex object provides
	the association between a physical IMA link and the IMA group to
	which it belongs, and setting the imaLinkGroupIndex object to a
	different value has the effect of changing the association between
	a physical IMA link and an IMA group. To place the link 'in group',
	the imaLinkRowStatus object is set to 'active'. While the row is
	not in 'active' state, both the Transmit and Receive IMA link state
	machines are in the 'Not In Group' state.
	To remove (delete) an imaLinkTable entry from this table, set
	this object to 'destroy'."
::= { imaLinkEntry 2 }

imaLinkGroupIndex OBJECT-TYPE
	SYNTAX INTEGER
	MAX-ACCESS read-only
	STATUS current
	DESCRIPTION
		"The value which identifies the IMA group (imaGroupIndex)
	of which this link is a member."
::= { imaLinkEntry 3 }

imaLinkNeTxState OBJECT-TYPE
	SYNTAX ImaLinkState
	MAX-ACCESS read-only
	STATUS current
	DESCRIPTION
		"The current state of the near-end transmit link."
	REFERENCE
		"ATM Forum IMA v1.1, Section 10.1.2 on page 48"
::= { imaLinkEntry 4 }

imaLinkNeRxState OBJECT-TYPE
	SYNTAX ImaLinkState
	MAX-ACCESS read-only
	STATUS current
	DESCRIPTION
		"The current state of the near-end receive link."
	REFERENCE
		"ATM Forum IMA v1.1, Section 10.1.2 on page 48"
::= { imaLinkEntry 5 }

imaLinkFeTxState OBJECT-TYPE
	SYNTAX ImaLinkState
	MAX-ACCESS read-only
	STATUS current
	DESCRIPTION
		"The current state of the far-end transmit link as reported
	via ICP cells."
	REFERENCE
		"ATM Forum IMA v1.1, Section 10.1.2 on page 48"
::= { imaLinkEntry 6 }

imaLinkFeRxState OBJECT-TYPE
	SYNTAX ImaLinkState
	MAX-ACCESS read-only
	STATUS current
	DESCRIPTION
		"The current state of the far-end receive link as reported
	via ICP cells."
	REFERENCE
		"ATM Forum IMA v1.1, Section 10.1.2 on page 48"
::= { imaLinkEntry 7 }

imaLinkTxLid OBJECT-TYPE
	SYNTAX INTEGER
	MAX-ACCESS read-only
	STATUS current
	DESCRIPTION
		"The outgoing LID used currently on the link by the local end.
	This value has meaning only if the link belongs to an IMA group."
	REFERENCE
		"ATM Forum IMA v1.1, Section 5.2.2.1 on page 26"
::= { imaLinkEntry 8 }

imaLinkRxLid OBJECT-TYPE
	SYNTAX        INTEGER
	MAX-ACCESS read-only
	STATUS current
	DESCRIPTION
		"The incoming LID used currently on the link by the remote
	end as reported via ICP cells. This value has meaning only
	if the link belongs to an IMA group."
	REFERENCE
		"ATM Forum IMA v1.1, Section 5.2.2.1 on page 26"
::= { imaLinkEntry 9 }


imaLinkIcpOffset OBJECT-TYPE
	SYNTAX        INTEGER
	MAX-ACCESS read-only
	STATUS current
	DESCRIPTION
		""
	REFERENCE
		"ATM Forum IMA v1.1, Section 5.2.2.1 on page 26"
::= { imaLinkEntry 10 }

imaLinkPhyLink OBJECT-TYPE
	SYNTAX        INTEGER
	MAX-ACCESS read-only
	STATUS current
	DESCRIPTION
		""
	REFERENCE
		"ATM Forum IMA v1.1, Section 5.2.2.1 on page 26"
::= { imaLinkEntry 11 }

imaLinkScramble OBJECT-TYPE
	SYNTAX        INTEGER{
			disable(0),
			 enable(1)
	}
	MAX-ACCESS read-write
	STATUS current
	DESCRIPTION
		"enable/disable the scramble status of the link"
::= { imaLinkEntry 12 }

-- The IMA Link Current Statistics subtree
-- The IMA Link Current Statistics subtree consists of a single table:
-- the IMA Link Current Table. This table contains various statistics
-- collected by each IMA link for the current 15 minute interval.
-- Implementation of IMA Link Current Table is optional.
--
imaLinkCurrentTable OBJECT-TYPE
	SYNTAX SEQUENCE OF ImaLinkCurrentEntry
	MAX-ACCESS not-accessible
	STATUS current
	DESCRIPTION
		"The IMA Link Current table."
::= { atmfImaLinkMibObjects 2 }

imaLinkCurrentEntry OBJECT-TYPE
	SYNTAX ImaLinkCurrentEntry
	MAX-ACCESS not-accessible
	STATUS current
	DESCRIPTION
		"An entry in the IMA Link Current table."
	INDEX { ifIndex }
::= { imaLinkCurrentTable 1 }

ImaLinkCurrentEntry ::= SEQUENCE {
		imaLinkCurrentImaViolations Gauge32,
		imaLinkCurrentOifAnomalies 	Gauge32,
    	imaLinkCurrentTxStuffs		Gauge32,
		imaLinkCurrentRxStuffs 		Gauge32,
		imaLinkCurrentTxUserCells  	Gauge32, 
		imaLinkCurrentRxUserCells  	Gauge32, 
		imaLinkCurrentFilteredCells Gauge32, 
		imaLinkCurrentDroppedCells 	Gauge32, 
		imaLinkCurrentIcpCells  	Gauge32, 
		imaLinkCurrentRxFillerCells Gauge32, 
		imaLinkCurrentHcsErrs 		Gauge32}

imaLinkCurrentImaViolations OBJECT-TYPE
	SYNTAX Gauge32
	MAX-ACCESS read-only
	STATUS current
	DESCRIPTION
		"ICP violations: count of errored, invalid or missing ICP cells,
	except during SES-IMA or UAS-IMA conditions, in the current
	15 minute interval."
	REFERENCE
		"ATM Forum IMA v1.1, (R-125) and (O-26) in Section 12.2.2.2
	on page 77"
::= { imaLinkCurrentEntry 1 }

imaLinkCurrentOifAnomalies OBJECT-TYPE
	SYNTAX Gauge32
	MAX-ACCESS read-only
	STATUS current
	DESCRIPTION
		"The number of OIF anomalies, except during SES-IMA or UAS-IMA
	conditions, at the near-end in the current 15 minute interval.
	This is an optional attribute."
	REFERENCE
		"ATM Forum IMA v1.1, (O-20) and (O-26) in Section 12.2.2.2
	on page 77"
::= { imaLinkCurrentEntry 2 }

imaLinkCurrentTxStuffs OBJECT-TYPE
	SYNTAX Gauge32
	MAX-ACCESS read-only
	STATUS current
	DESCRIPTION
		"Count of stuff events inserted in the transmit direction in
	the current 15 minute interval. This is an optional attribute."
	REFERENCE
		"ATM Forum IMA v1.1, (O-23) and (O-26) in Section 12.2.2.2
	on page 77"
::= { imaLinkCurrentEntry 3 }

imaLinkCurrentRxStuffs OBJECT-TYPE
	SYNTAX Gauge32
	MAX-ACCESS read-only
	STATUS current
	DESCRIPTION
		"Count of stuff events detected in the receive direction in
	the current 15 minute interval. This is an optional attribute."
	REFERENCE
		"ATM Forum IMA v1.1, (O-24) and (O-26) in Section 12.2.2.2
	on page 77"
::= { imaLinkCurrentEntry 4 }

imaLinkCurrentTxUserCells OBJECT-TYPE
	SYNTAX Gauge32
	MAX-ACCESS read-only
	STATUS current
	DESCRIPTION
		"Count of TxUserCells the current 15 minute interval."
	REFERENCE
		"ATM Forum IMA v1.1, (O-24) and (O-26) in Section 12.2.2.2
	on page 77"
::= { imaLinkCurrentEntry 5 }

imaLinkCurrentRxUserCells OBJECT-TYPE
	SYNTAX Gauge32
	MAX-ACCESS read-only
	STATUS current
	DESCRIPTION
		"Count of RxUserCells the current 15 minute interval"
	REFERENCE
		"ATM Forum IMA v1.1, (O-24) and (O-26) in Section 12.2.2.2
	on page 77"
::= { imaLinkCurrentEntry 6 }

imaLinkCurrentFilteredCells OBJECT-TYPE
	SYNTAX Gauge32
	MAX-ACCESS read-only
	STATUS current
	DESCRIPTION
		"Count of FileredCells the current 15 minute interval"
	REFERENCE
		"ATM Forum IMA v1.1, (O-24) and (O-26) in Section 12.2.2.2
	on page 77"
::= { imaLinkCurrentEntry 7 }

imaLinkCurrentDroppedCells OBJECT-TYPE
	SYNTAX Gauge32
	MAX-ACCESS read-only
	STATUS current
	DESCRIPTION
		"Count of DroppedCells the current 15 minute interval"
	REFERENCE
		"ATM Forum IMA v1.1, (O-24) and (O-26) in Section 12.2.2.2
	on page 77"
::= { imaLinkCurrentEntry 8 }

imaLinkCurrentIcpCells OBJECT-TYPE
	SYNTAX Gauge32
	MAX-ACCESS read-only
	STATUS current
	DESCRIPTION
		"Count of IcpCells the current 15 minute interval"
	REFERENCE
		"ATM Forum IMA v1.1, (O-24) and (O-26) in Section 12.2.2.2
	on page 77"
::= { imaLinkCurrentEntry 9 }

imaLinkCurrentRxFillerCells OBJECT-TYPE
	SYNTAX Gauge32
	MAX-ACCESS read-only
	STATUS current
	DESCRIPTION
		"Count of RxFillerCells the current 15 minute interval"
	REFERENCE
		"ATM Forum IMA v1.1, (O-24) and (O-26) in Section 12.2.2.2
	on page 77"
::= { imaLinkCurrentEntry 10 }


imaLinkCurrentHcsErrs OBJECT-TYPE
	SYNTAX Gauge32
	MAX-ACCESS read-only
	STATUS current
	DESCRIPTION
		"Count of HcsErrs the current 15 minute interval"
	REFERENCE
		"ATM Forum IMA v1.1, (O-24) and (O-26) in Section 12.2.2.2
	on page 77"
::= { imaLinkCurrentEntry 11 }

-- The IMA Link Interval Statistics subtree
-- The IMA Link Interval Statistics subtree consists of a single table:
-- the IMA Link Interval Table. This table contains various statistics
-- collected by each IMA link over the previous 24 hours of operation.
-- The past 24 hours are broken into 96 completed 15 minute intervals.
-- Implementation of IMA Link Interval Table is optional.

imaLinkIntervalTable OBJECT-TYPE
	SYNTAX SEQUENCE OF ImaLinkIntervalEntry
	MAX-ACCESS not-accessible
	STATUS current
	DESCRIPTION
		"The IMA Link Interval table."
::= { atmfImaLinkMibObjects 3 }

imaLinkIntervalEntry OBJECT-TYPE
	SYNTAX ImaLinkIntervalEntry
	MAX-ACCESS not-accessible
	STATUS current
	DESCRIPTION
		"An entry in the IMA Link Interval table."
	INDEX { ifIndex, imaLinkIntervalNumber }
::= { imaLinkIntervalTable 1 }

ImaLinkIntervalEntry ::= SEQUENCE {
		imaLinkIntervalNumber 		 	INTEGER,
	   	imaLinkIntervalImaViolations 	Gauge32,
   		imaLinkIntervalOifAnomalies 	Gauge32,
    	imaLinkIntervalTxStuffs 		Gauge32,
		imaLinkIntervalRxStuffs 		Gauge32,
   		imaLinkIntervalTxUserCells  	Gauge32, 
		imaLinkIntervalRxUserCells  	Gauge32, 
		imaLinkIntervalFilteredCells 	Gauge32, 
		imaLinkIntervalDroppedCells 	Gauge32, 
		imaLinkIntervalIcpCells  		Gauge32, 
		imaLinkIntervalRxFillerCells 	Gauge32, 
		imaLinkIntervalHcsErrs 			Gauge32}

imaLinkIntervalNumber OBJECT-TYPE
	SYNTAX INTEGER
	MAX-ACCESS not-accessible
	STATUS current
	DESCRIPTION
		"A number between 1 and 96, where 1 is the most
	recently completed 15 minute interval and 96 is the least
	recently completed 15 minutes interval (assuming that all
	96 intervals are valid)."
::= { imaLinkIntervalEntry 1 }

imaLinkIntervalImaViolations OBJECT-TYPE
	SYNTAX Gauge32
	MAX-ACCESS read-only
	STATUS current
	DESCRIPTION
		"ICP violations: count of errored, invalid or missing ICP cells,
	except during SES-IMA or UAS-IMA conditions, in one of the
	previous 96, individual 15 minute, intervals."
	REFERENCE
		"ATM Forum IMA v1.1, (R-125) and (O-26) in Section 12.2.2.2
	on page 77"
::= { imaLinkIntervalEntry 2 }

imaLinkIntervalOifAnomalies  OBJECT-TYPE
	SYNTAX Gauge32
	MAX-ACCESS read-only
	STATUS current
	DESCRIPTION
		"The number of times a far-end receive failure alarm condition
	has been entered on this link (i.e., Rx-Unusable-FE) in one of
	the previous 96, individual 15 minute, intervals. This is an
	optional attribute."
	REFERENCE
		"ATM Forum IMA v1.1, (O-22) and (O-26) in Section 12.2.2.2
	on page 77"
::= { imaLinkIntervalEntry 3 }

imaLinkIntervalTxStuffs OBJECT-TYPE
	SYNTAX Gauge32
	MAX-ACCESS read-only
	STATUS current
	DESCRIPTION
		"Count of stuff events inserted in the transmit direction in
	one of the previous 96, individual 15 minute, intervals. This
	is an optional attribute."
	REFERENCE
		"ATM Forum IMA v1.1, (O-23) and (O-26) in Section 12.2.2.2
	on page 77"
::= { imaLinkIntervalEntry 4 }

imaLinkIntervalRxStuffs OBJECT-TYPE
	SYNTAX Gauge32
	MAX-ACCESS read-only
	STATUS current
	DESCRIPTION
		"Count of stuff events detected in the receive direction in
	one of the previous 96, individual 15 minute, intervals. This
	is an optional attribute."
	REFERENCE
		"ATM Forum IMA v1.1, (O-24) and (O-26) in Section 12.2.2.2
	on page 77"
::= { imaLinkIntervalEntry 5}

imaLinkIntervalTxUserCells OBJECT-TYPE
	SYNTAX Gauge32
	MAX-ACCESS read-only
	STATUS current
	DESCRIPTION
		"Count of TxUserCells detected in the receive direction in
	one of the previous 96, individual 15 minute, intervals. This
	is an optional attribute."
	REFERENCE
		"ATM Forum IMA v1.1, (O-24) and (O-26) in Section 12.2.2.2
	on page 77"
::= { imaLinkIntervalEntry 6}

imaLinkIntervalRxUserCells OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 7}

imaLinkIntervalFilteredCells OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 8}

imaLinkIntervalDroppedCells OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 9}

imaLinkIntervalIcpCells OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 10}

imaLinkIntervalRxFillerCells OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 11}

imaLinkIntervalHcsErrs OBJECT-TYPE
	SYNTAX Gauge32
	MAX-ACCESS read-only
	STATUS current
	DESCRIPTION
		""
	REFERENCE
		"ATM Forum IMA v1.1, (O-24) and (O-26) in Section 12.2.2.2
	on page 77"
::= { imaLinkIntervalEntry 12}

-- The IMA Link Total Statistics subtree
-- The IMA Link Total Statistics subtree consists of a single table:
-- the IMA Link Total Table. This table contains the cumulative sum
-- of the various statistics collected by each IMA link for the 24 hour
-- period preceding the current interval.
-- Implementation of IMA Link Total Table is optional.

imaLinkTotalTable OBJECT-TYPE
	SYNTAX SEQUENCE OF ImaLinkTotalEntry
	MAX-ACCESS not-accessible
	STATUS current
	DESCRIPTION
		"The IMA Link Total table."
::= { atmfImaLinkMibObjects 4 }

imaLinkTotalEntry OBJECT-TYPE
	SYNTAX ImaLinkTotalEntry
	MAX-ACCESS not-accessible
	STATUS current
	DESCRIPTION
		"An entry in the IMA Link Total table."
	INDEX { ifIndex }
::= { imaLinkTotalTable 1 }

ImaLinkTotalEntry ::= SEQUENCE {
		imaLinkTotalImaViolations Gauge32,
   		imaLinkTotalOifAnomalies Gauge32,
    	imaLinkTotalTxStuffs Gauge32,
		imaLinkTotalRxStuffs Gauge32,
   		imaLinkTotalTxUserCells  Gauge32, 
		imaLinkTotalRxUserCells  Gauge32, 
		imaLinkTotalFilteredCells Gauge32, 
		imaLinkTotalDroppedCells Gauge32, 
		imaLinkTotalIcpCells  Gauge32, 
		imaLinkTotalRxFillerCells Gauge32, 
		imaLinkTotalHcsErrs    Gauge32}
		
imaLinkTotalImaViolations OBJECT-TYPE
	SYNTAX Gauge32
	MAX-ACCESS read-only
	STATUS current
	DESCRIPTION
		"ICP violations: count of errored, invalid or missing ICP cells,
	except during SES-IMA or UAS-IMA conditions, in the previous 24
	hour interval. Invalid 15 minute intervals count as 0."
	REFERENCE
		"ATM Forum IMA v1.1, (R-125) and (O-27) in Section 12.2.2.2
	on page 77"
::= { imaLinkTotalEntry 1 }

imaLinkTotalOifAnomalies OBJECT-TYPE
	SYNTAX Gauge32
	MAX-ACCESS read-only
	STATUS current
	DESCRIPTION
		"The number of OIF anomalies, except during SES-IMA or UAS-IMA
	conditions, at the near-end in the previous 24 hour interval.
	Invalid 15 minute intervals count as 0. This is an optional
	attribute."
	REFERENCE
		"ATM Forum IMA v1.1, (O-20) and (O-27) in Section 12.2.2.2
	on page 77"
::= { imaLinkTotalEntry 2 }

imaLinkTotalTxStuffs OBJECT-TYPE
	SYNTAX Gauge32
	MAX-ACCESS read-only
	STATUS current
	DESCRIPTION
		"Count of stuff events inserted in the transmit direction in
	the previous 24 hour interval. Invalid 15 minute intervals
	count as 0. This is an optional attribute."
	REFERENCE
		"ATM Forum IMA v1.1, (O-23) and (O-27) in Section 12.2.2.2
	on page 77"
::= { imaLinkTotalEntry 3 }

imaLinkTotalRxStuffs OBJECT-TYPE
	SYNTAX Gauge32
	MAX-ACCESS read-only
	STATUS current
	DESCRIPTION
		"Count of stuff events detected in the receive direction in
	the previous 24 hour interval. Invalid 15 minute intervals
	count as 0. This is an optional attribute."
	REFERENCE
		"ATM Forum IMA v1.1, (O-24) and (O-27) in Section 12.2.2.2
	on page 77"
::= { imaLinkTotalEntry 4 }


imaLinkTotalTxUserCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 5 }

imaLinkTotalRxUserCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 6 }

imaLinkTotalFilteredCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 7}

imaLinkTotalDroppedCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 8}

imaLinkTotalIcpCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 9}

imaLinkTotalRxFillerCells OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 10}

imaLinkTotalHcsErrs OBJECT-TYPE
	SYNTAX Gauge32
	MAX-ACCESS read-only
	STATUS current
	DESCRIPTION
		""
	REFERENCE
		"ATM Forum IMA v1.1, (O-24) and (O-27) in Section 12.2.2.2
	on page 77"
::= { imaLinkTotalEntry 11}


-- Conformance Information
 imaLinkGroup OBJECT-GROUP
       OBJECTS{ 
       	imaLinkIfIndex   ,
	imaLinkRowStatus  ,
	imaLinkGroupIndex ,
	imaLinkNeTxState  ,
	imaLinkNeRxState  ,
	imaLinkFeTxState  ,
	imaLinkFeRxState  ,
	imaLinkTxLid ,
	imaLinkRxLid,
	imaLinkIcpOffset  ,
    imaLinkPhyLink  ,
	imaLinkScramble   }    
       STATUS          current
       DESCRIPTION
              " A set of objects providing configuration and status information for
              an IMA Link definition."
       ::=  {atmfImaLinkGroups 1 }


imaLinkCurrentGroup OBJECT-GROUP
   OBJECTS{	
   		imaLinkCurrentImaViolations ,
		imaLinkCurrentOifAnomalies 	,
    	imaLinkCurrentTxStuffs		,
		imaLinkCurrentRxStuffs 		,
		imaLinkCurrentTxUserCells  	, 
		imaLinkCurrentRxUserCells  	, 
		imaLinkCurrentFilteredCells , 
		imaLinkCurrentDroppedCells 	, 
		imaLinkCurrentIcpCells  	, 
		imaLinkCurrentRxFillerCells , 
		imaLinkCurrentHcsErrs }
		
        STATUS          current
        DESCRIPTION
              " Objects containing current statistics for an IMA Link."
           ::=  {atmfImaLinkGroups 2} 


   imaLinkIntervalGroup OBJECT-GROUP
      OBJECTS{
	   	imaLinkIntervalImaViolations 	,
   		imaLinkIntervalOifAnomalies 	,
    	imaLinkIntervalTxStuffs 		,
		imaLinkIntervalRxStuffs 	,
   		imaLinkIntervalTxUserCells  	, 
		imaLinkIntervalRxUserCells  	, 
		imaLinkIntervalFilteredCells 	, 
		imaLinkIntervalDroppedCells 	, 
		imaLinkIntervalIcpCells  		, 
		imaLinkIntervalRxFillerCells 	, 
		imaLinkIntervalHcsErrs 			 }       
        STATUS          current
        DESCRIPTION
              " Objects containing interval statistics for an IMA Link."
           ::=  {atmfImaLinkGroups 3}         
    
    imaLinkTotalGroup OBJECT-GROUP
          OBJECTS{
		imaLinkTotalImaViolations ,
   		imaLinkTotalOifAnomalies ,
    	imaLinkTotalTxStuffs ,
		imaLinkTotalRxStuffs ,
   		imaLinkTotalTxUserCells  , 
		imaLinkTotalRxUserCells  , 
		imaLinkTotalFilteredCells , 
		imaLinkTotalDroppedCells , 
		imaLinkTotalIcpCells  , 
		imaLinkTotalRxFillerCells , 
		imaLinkTotalHcsErrs}    
		   
        STATUS          current
        DESCRIPTION
              " Objects containing total statistics for an IMA Link."
           
           ::=  {atmfImaLinkGroups 4} 
           
--  compliance statements
    atmfImaMibCompliance MODULE-COMPLIANCE
    STATUS  current
    DESCRIPTION
           "The compliance statement."
    MODULE  -- this module
    MANDATORY-GROUPS{
            imaLinkGroup,
            imaLinkCurrentGroup,
            imaLinkIntervalGroup,
            imaLinkTotalGroup
            }
        ::= { atmfImaLinkCompliances 1 }
END


-- -------------------------------------------------------------
-- Rfc2674p
-- -------------------------------------------------------------

P-BRIDGE-MIB DEFINITIONS ::= BEGIN

-- -------------------------------------------------------------
-- MIB for IEEE 802.1p devices
-- -------------------------------------------------------------

IMPORTS
    MODULE-IDENTITY, OBJECT-TYPE, Counter32, Counter64
        FROM SNMPv2-SMI
    TruthValue, TimeInterval, MacAddress, TEXTUAL-CONVENTION
        FROM SNMPv2-TC
    MODULE-COMPLIANCE, OBJECT-GROUP
        FROM SNMPv2-CONF
    dot1dTp, dot1dTpPort, dot1dBridge,
    dot1dBasePortEntry, dot1dBasePort
        FROM BRIDGE-MIB;

pBridgeMIB MODULE-IDENTITY
    LAST-UPDATED "9908250000Z"
    ORGANIZATION "IETF Bridge MIB Working Group"
    CONTACT-INFO
        "       Les Bell
        Postal: 3Com Europe Ltd.
                3Com Centre, Boundary Way
                Hemel Hempstead, Herts. HP2 7YU
                UK
         Phone: +44 1442 438025
         Email: Les_Bell@3Com.com

                Andrew Smith
        Postal: Extreme Networks
                3585 Monroe St.
                Santa Clara CA 95051
                USA
         Phone: +1 408 579 2821
         Email: andrew@extremenetworks.com

                Paul Langille
        Postal: Newbridge Networks
                5 Corporate Drive
                Andover, MA 01810
                USA
         Phone: +1 978 691 4665
         Email: langille@newbridge.com

                Anil Rijhsinghani
        Postal: Cabletron Systems
                50 Minuteman Road
                Andover, MA 01810
                USA
         Phone: +1 978 684 1295
         Email: anil@cabletron.com

                Keith McCloghrie
        Postal: cisco Systems, Inc.
                170 West Tasman Drive
                San Jose, CA 95134-1706
                USA
         Phone: +1 408 526 5260
         Email: kzm@cisco.com"

    DESCRIPTION
        "The Bridge MIB Extension module for managing Priority
        and Multicast Filtering, defined by IEEE 802.1D-1998."

-- revision history

    REVISION     "9908250000Z"
    DESCRIPTION
         "Initial version, published as RFC 2674."

    ::= { dot1dBridge 6 }

pBridgeMIBObjects OBJECT IDENTIFIER ::= { pBridgeMIB 1 }

-- -------------------------------------------------------------
-- Textual Conventions
-- -------------------------------------------------------------

EnabledStatus ::= TEXTUAL-CONVENTION
    STATUS      current
    DESCRIPTION
        "A simple status value for the object."
    SYNTAX      INTEGER { enabled(1), disabled(2) }

-- -------------------------------------------------------------

-- -------------------------------------------------------------
-- groups in the P-BRIDGE MIB
-- -------------------------------------------------------------

dot1dExtBase    OBJECT IDENTIFIER ::= { pBridgeMIBObjects 1 }
dot1dPriority   OBJECT IDENTIFIER ::= { pBridgeMIBObjects 2 }
dot1dGarp       OBJECT IDENTIFIER ::= { pBridgeMIBObjects 3 }
dot1dGmrp       OBJECT IDENTIFIER ::= { pBridgeMIBObjects 4 }

-- -------------------------------------------------------------

-- -------------------------------------------------------------
-- the dot1dExtBase group
-- -------------------------------------------------------------

dot1dDeviceCapabilities OBJECT-TYPE
    SYNTAX      BITS {
        dot1dExtendedFilteringServices(0),
                              -- can perform filtering of
                              -- individual multicast addresses
                              -- controlled by GMRP.
        dot1dTrafficClasses(1),
                              -- can map user priority to
                              -- multiple traffic classes.

        dot1qStaticEntryIndividualPort(2),
                              -- dot1qStaticUnicastReceivePort &
                              -- dot1qStaticMulticastReceivePort
                              -- can represent non-zero entries.
        dot1qIVLCapable(3),   -- Independent VLAN Learning.
        dot1qSVLCapable(4),   -- Shared VLAN Learning.
        dot1qHybridCapable(5),
                              -- both IVL & SVL simultaneously.
        dot1qConfigurablePvidTagging(6),
                              -- whether the implementation
                              -- supports the ability to
                              -- override the default PVID
                              -- setting and its egress status
                              -- (VLAN-Tagged or Untagged) on
                              -- each port.
        dot1dLocalVlanCapable(7)
                              -- can support multiple local
                              -- bridges, outside of the scope
                              -- of 802.1Q defined VLANs.
    }
    MAX-ACCESS  read-only
    STATUS      current
    DESCRIPTION
        "Indicates the optional parts of IEEE 802.1D and 802.1Q
        that are implemented by this device and are manageable
        through this MIB.  Capabilities that are allowed on a
        per-port basis are indicated in dot1dPortCapabilities."
    REFERENCE
        "ISO/IEC 15802-3 Section 5.2,
        IEEE 802.1Q/D11 Section 5.2, 12.10.1.1.3/b/2"
    ::= { dot1dExtBase 1 }

dot1dTrafficClassesEnabled OBJECT-TYPE
    SYNTAX      TruthValue
    MAX-ACCESS  read-write
    STATUS      current
    DESCRIPTION
        "The value true(1) indicates that Traffic Classes are
        enabled on this bridge.  When false(2), the bridge
        operates with a single priority level for all traffic."
    DEFVAL      { true }
    ::= { dot1dExtBase 2 }

dot1dGmrpStatus OBJECT-TYPE
    SYNTAX      EnabledStatus
    MAX-ACCESS  read-write
    STATUS      current
    DESCRIPTION

        "The administrative status requested by management for
        GMRP.  The value enabled(1) indicates that GMRP should
        be enabled on this device, in all VLANs, on all ports
        for which it has not been specifically disabled.  When
        disabled(2), GMRP is disabled, in all VLANs, on all
        ports and all GMRP packets will be forwarded
        transparently.  This object affects both Applicant and
        Registrar state machines.  A transition from disabled(2)
        to enabled(1) will cause a reset of all GMRP state
        machines on all ports."
    DEFVAL      { enabled }
    ::= { dot1dExtBase 3 }

-- -------------------------------------------------------------
-- Port Capabilities Table
-- -------------------------------------------------------------

dot1dPortCapabilitiesTable OBJECT-TYPE
    SYNTAX      SEQUENCE OF Dot1dPortCapabilitiesEntry
    MAX-ACCESS  not-accessible
    STATUS      current
    DESCRIPTION
        "A table that contains capabilities information about
        every port that is associated with this bridge."
    ::= { dot1dExtBase 4 }

dot1dPortCapabilitiesEntry OBJECT-TYPE
    SYNTAX      Dot1dPortCapabilitiesEntry
    MAX-ACCESS  not-accessible
    STATUS      current
    DESCRIPTION
        "A set of capabilities information about this port
        indexed by dot1dBasePort."
    AUGMENTS { dot1dBasePortEntry }
    ::= { dot1dPortCapabilitiesTable 1 }

Dot1dPortCapabilitiesEntry ::=
    SEQUENCE {
        dot1dPortCapabilities
            BITS
    }

dot1dPortCapabilities OBJECT-TYPE
    SYNTAX      BITS {
        dot1qDot1qTagging(0), -- supports 802.1Q VLAN tagging of
                              -- frames and GVRP.
        dot1qConfigurableAcceptableFrameTypes(1),
                              -- allows modified values of

                              -- dot1qPortAcceptableFrameTypes.
        dot1qIngressFiltering(2)
                              -- supports the discarding of any
                              -- frame received on a Port whose
                              -- VLAN classification does not
                              -- include that Port in its Member
                              -- set.
    }
    MAX-ACCESS  read-only
    STATUS      current
    DESCRIPTION
        "Indicates the parts of IEEE 802.1D and 802.1Q that are
        optional on a per-port basis that are implemented by
        this device and are manageable through this MIB."
    REFERENCE
        "ISO/IEC 15802-3 Section 5.2,
        IEEE 802.1Q/D11 Section 5.2"
    ::= { dot1dPortCapabilitiesEntry 1 }

-- -------------------------------------------------------------
-- the dot1dPriority group
-- -------------------------------------------------------------

-- -------------------------------------------------------------
-- Port Priority Table
-- -------------------------------------------------------------

dot1dPortPriorityTable OBJECT-TYPE
    SYNTAX      SEQUENCE OF Dot1dPortPriorityEntry
    MAX-ACCESS  not-accessible
    STATUS      current
    DESCRIPTION
        "A table that contains information about every port that
        is associated with this transparent bridge."
    ::= { dot1dPriority 1 }

dot1dPortPriorityEntry OBJECT-TYPE
    SYNTAX      Dot1dPortPriorityEntry
    MAX-ACCESS  not-accessible
    STATUS      current
    DESCRIPTION
        "A list of Default User Priorities for each port of a
        transparent bridge.  This is indexed by dot1dBasePort."
    AUGMENTS { dot1dBasePortEntry }
    ::= { dot1dPortPriorityTable 1 }

Dot1dPortPriorityEntry ::=
    SEQUENCE {

        dot1dPortDefaultUserPriority
            INTEGER,
        dot1dPortNumTrafficClasses
            INTEGER
    }

dot1dPortDefaultUserPriority OBJECT-TYPE
    SYNTAX      INTEGER (0..7)
    MAX-ACCESS  read-write
    STATUS      current
    DESCRIPTION
        "The default ingress User Priority for this port.  This
        only has effect on media, such as Ethernet, that do not
        support native User Priority."
    ::= { dot1dPortPriorityEntry 1 }

dot1dPortNumTrafficClasses OBJECT-TYPE
    SYNTAX      INTEGER (1..8)
    MAX-ACCESS  read-write
    STATUS      current
    DESCRIPTION
        "The number of egress traffic classes supported on this
        port.  This object may optionally be read-only."
    ::= { dot1dPortPriorityEntry 2 }

-- -------------------------------------------------------------
-- User Priority Regeneration Table
-- -------------------------------------------------------------

dot1dUserPriorityRegenTable OBJECT-TYPE
    SYNTAX      SEQUENCE OF Dot1dUserPriorityRegenEntry
    MAX-ACCESS  not-accessible
    STATUS      current
    DESCRIPTION
        "A list of Regenerated User Priorities for each received
        User Priority on each port of a bridge.  The Regenerated
        User Priority value may be used to index the Traffic
        Class Table for each input port.  This only has effect
        on media that support native User Priority.  The default
        values for Regenerated User Priorities are the same as
        the User Priorities."
    REFERENCE
        "ISO/IEC 15802-3 Section 6.4"
    ::= { dot1dPriority 2 }

dot1dUserPriorityRegenEntry OBJECT-TYPE
    SYNTAX      Dot1dUserPriorityRegenEntry
    MAX-ACCESS  not-accessible
    STATUS      current
    DESCRIPTION
        "A mapping of incoming User Priority to a Regenerated
        User Priority."
    INDEX   { dot1dBasePort, dot1dUserPriority }
    ::= { dot1dUserPriorityRegenTable 1 }

Dot1dUserPriorityRegenEntry ::=
    SEQUENCE {
        dot1dUserPriority
            INTEGER,
        dot1dRegenUserPriority
            INTEGER
    }

dot1dUserPriority OBJECT-TYPE
    SYNTAX      INTEGER (0..7)
    MAX-ACCESS  not-accessible
    STATUS      current
    DESCRIPTION
        "The User Priority for a frame received on this port."
    ::= { dot1dUserPriorityRegenEntry 1 }

dot1dRegenUserPriority OBJECT-TYPE
    SYNTAX      INTEGER (0..7)
    MAX-ACCESS  read-write
    STATUS      current
    DESCRIPTION
        "The Regenerated User Priority the incoming User
        Priority is mapped to for this port."
    ::= { dot1dUserPriorityRegenEntry 2 }

-- -------------------------------------------------------------
-- Traffic Class Table
-- -------------------------------------------------------------

dot1dTrafficClassTable OBJECT-TYPE
    SYNTAX      SEQUENCE OF Dot1dTrafficClassEntry
    MAX-ACCESS  not-accessible
    STATUS      current
    DESCRIPTION
        "A table mapping evaluated User Priority to Traffic
        Class, for forwarding by the bridge.  Traffic class is a
        number in the range (0..(dot1dPortNumTrafficClasses-1))."
    REFERENCE

        "ISO/IEC 15802-3 Table 7-2"
    ::= { dot1dPriority 3 }

dot1dTrafficClassEntry OBJECT-TYPE
    SYNTAX      Dot1dTrafficClassEntry
    MAX-ACCESS  not-accessible
    STATUS      current
    DESCRIPTION
        "User Priority to Traffic Class mapping."
    INDEX   { dot1dBasePort, dot1dTrafficClassPriority }
    ::= { dot1dTrafficClassTable 1 }

Dot1dTrafficClassEntry ::=
    SEQUENCE {
        dot1dTrafficClassPriority
            INTEGER,
        dot1dTrafficClass
            INTEGER
    }

dot1dTrafficClassPriority OBJECT-TYPE
    SYNTAX      INTEGER (0..7)
    MAX-ACCESS  not-accessible
    STATUS      current
    DESCRIPTION
        "The Priority value determined for the received frame.
        This value is equivalent to the priority indicated in
        the tagged frame received, or one of the evaluated
        priorities, determined according to the media-type.

        For untagged frames received from Ethernet media, this
        value is equal to the dot1dPortDefaultUserPriority value
        for the ingress port.

        For untagged frames received from non-Ethernet media,
        this value is equal to the dot1dRegenUserPriority value
        for the ingress port and media-specific user priority."
    ::= { dot1dTrafficClassEntry 1 }

dot1dTrafficClass OBJECT-TYPE
    SYNTAX      INTEGER (0..7)
    MAX-ACCESS  read-write
    STATUS      current
    DESCRIPTION
        "The Traffic Class the received frame is mapped to."
    ::= { dot1dTrafficClassEntry 2 }

-- -------------------------------------------------------------

-- Outbound Access Priority Table
-- -------------------------------------------------------------

dot1dPortOutboundAccessPriorityTable OBJECT-TYPE
    SYNTAX      SEQUENCE OF Dot1dPortOutboundAccessPriorityEntry
    MAX-ACCESS  not-accessible
    STATUS      current
    DESCRIPTION
        "A table mapping Regenerated User Priority to Outbound
        Access Priority.  This is a fixed mapping for all port
        types, with two options for 802.5 Token Ring."
    REFERENCE
        "ISO/IEC 15802-3 Table 7-3"
    ::= { dot1dPriority 4 }

dot1dPortOutboundAccessPriorityEntry OBJECT-TYPE
    SYNTAX      Dot1dPortOutboundAccessPriorityEntry
    MAX-ACCESS  not-accessible
    STATUS      current
    DESCRIPTION
        "Regenerated User Priority to Outbound Access Priority
        mapping."
    INDEX   { dot1dBasePort, dot1dRegenUserPriority }
    ::= { dot1dPortOutboundAccessPriorityTable 1 }

Dot1dPortOutboundAccessPriorityEntry ::=
    SEQUENCE {
        dot1dPortOutboundAccessPriority
            INTEGER
    }

dot1dPortOutboundAccessPriority OBJECT-TYPE
    SYNTAX      INTEGER (0..7)
    MAX-ACCESS  read-only
    STATUS      current
    DESCRIPTION
        "The Outbound Access Priority the received frame is
        mapped to."
    ::= { dot1dPortOutboundAccessPriorityEntry 1 }

-- -------------------------------------------------------------
-- the dot1dGarp group
-- -------------------------------------------------------------

-- -------------------------------------------------------------
-- The GARP Port Table
-- -------------------------------------------------------------

dot1dPortGarpTable OBJECT-TYPE
    SYNTAX      SEQUENCE OF Dot1dPortGarpEntry
    MAX-ACCESS  not-accessible
    STATUS      current
    DESCRIPTION
        "A table of GARP control information about every bridge
        port.  This is indexed by dot1dBasePort."
    ::= { dot1dGarp 1 }

dot1dPortGarpEntry OBJECT-TYPE
    SYNTAX      Dot1dPortGarpEntry
    MAX-ACCESS  not-accessible
    STATUS      current
    DESCRIPTION
        "GARP control information for a bridge port."
    AUGMENTS { dot1dBasePortEntry }
    ::= { dot1dPortGarpTable 1 }

Dot1dPortGarpEntry ::=
    SEQUENCE {
        dot1dPortGarpJoinTime
            TimeInterval,
        dot1dPortGarpLeaveTime
            TimeInterval,
        dot1dPortGarpLeaveAllTime
            TimeInterval
    }

dot1dPortGarpJoinTime OBJECT-TYPE
    SYNTAX      TimeInterval
    MAX-ACCESS  read-write
    STATUS      current
    DESCRIPTION
        "The GARP Join time, in centiseconds."
    DEFVAL      { 20 }
    ::= { dot1dPortGarpEntry 1 }

dot1dPortGarpLeaveTime OBJECT-TYPE
    SYNTAX      TimeInterval
    MAX-ACCESS  read-write
    STATUS      current
    DESCRIPTION
        "The GARP Leave time, in centiseconds."
    DEFVAL      { 60 }
    ::= { dot1dPortGarpEntry 2 }

dot1dPortGarpLeaveAllTime OBJECT-TYPE
    SYNTAX      TimeInterval
    MAX-ACCESS  read-write
    STATUS      current
    DESCRIPTION
        "The GARP LeaveAll time, in centiseconds."
    DEFVAL      { 1000 }
    ::= { dot1dPortGarpEntry 3 }

-- -------------------------------------------------------------
-- The GMRP Port Configuration and Status Table
-- -------------------------------------------------------------

dot1dPortGmrpTable OBJECT-TYPE
    SYNTAX      SEQUENCE OF Dot1dPortGmrpEntry
    MAX-ACCESS  not-accessible
    STATUS      current
    DESCRIPTION
        "A table of GMRP control and status information about
        every bridge port.  Augments the dot1dBasePortTable."
    ::= { dot1dGmrp 1 }

dot1dPortGmrpEntry OBJECT-TYPE
    SYNTAX      Dot1dPortGmrpEntry
    MAX-ACCESS  not-accessible
    STATUS      current
    DESCRIPTION
        "GMRP control and status information for a bridge port."
    AUGMENTS { dot1dBasePortEntry }
    ::= { dot1dPortGmrpTable 1 }

Dot1dPortGmrpEntry ::=
    SEQUENCE {
        dot1dPortGmrpStatus
            EnabledStatus
--        dot1dPortGmrpFailedRegistrations
--            Counter32,
--        dot1dPortGmrpLastPduOrigin
--            MacAddress
    }

dot1dPortGmrpStatus OBJECT-TYPE
    SYNTAX      EnabledStatus
    MAX-ACCESS  read-write
    STATUS      current

    DESCRIPTION
        "The administrative state of GMRP operation on this port. The
        value enabled(1) indicates that GMRP is enabled on this port
        in all VLANs as long as dot1dGmrpStatus is also enabled(1).
        A value of disabled(2) indicates that GMRP is disabled on
        this port in all VLANs: any GMRP packets received will
        be silently discarded and no GMRP registrations will be
        propagated from other ports. Setting this to a value of
        enabled(1) will be stored by the agent but will only take
        effect on the GMRP protocol operation if dot1dGmrpStatus
        also indicates the value enabled(1).  This object affects
        all GMRP Applicant and Registrar state machines on this
        port.  A transition from disabled(2) to enabled(1) will
        cause a reset of all GMRP state machines on this port."
    DEFVAL      { enabled }
    ::= { dot1dPortGmrpEntry 1 }

--dot1dPortGmrpFailedRegistrations OBJECT-TYPE
--    SYNTAX      Counter32
--    MAX-ACCESS  read-only
--    STATUS      current
--    DESCRIPTION
--        "The total number of failed GMRP registrations, for any
--        reason, in all VLANs, on this port."
--    ::= { dot1dPortGmrpEntry 2 }

--dot1dPortGmrpLastPduOrigin OBJECT-TYPE
--    SYNTAX      MacAddress
--    MAX-ACCESS  read-only
--    STATUS      current
--    DESCRIPTION
--        "The Source MAC Address of the last GMRP message
--        received on this port."
--    ::= { dot1dPortGmrpEntry 3 }

-- -------------------------------------------------------------
--  High Capacity Port Table for Transparent Bridges
-- -------------------------------------------------------------

dot1dTpHCPortTable OBJECT-TYPE
    SYNTAX      SEQUENCE OF Dot1dTpHCPortEntry
    MAX-ACCESS  not-accessible
    STATUS      current
    DESCRIPTION
        "A table that contains information about every high
        capacity port that is associated with this transparent
        bridge."
    ::= { dot1dTp 5 }

dot1dTpHCPortEntry OBJECT-TYPE
    SYNTAX      Dot1dTpHCPortEntry
    MAX-ACCESS  not-accessible
    STATUS      current
    DESCRIPTION
        "Statistics information for each high capacity port of a
        transparent bridge."
    INDEX   { dot1dTpPort }
    ::= { dot1dTpHCPortTable 1 }

Dot1dTpHCPortEntry ::=
    SEQUENCE {
        dot1dTpHCPortInFrames
            Counter64,
        dot1dTpHCPortOutFrames
            Counter64,
        dot1dTpHCPortInDiscards
            Counter64
    }

dot1dTpHCPortInFrames OBJECT-TYPE
    SYNTAX      Counter64
    MAX-ACCESS  read-only
    STATUS      current
    DESCRIPTION
        "The number of frames that have been received by this
        port from its segment.  Note that a frame received on
        the interface corresponding to this port is only counted
        by this object if and only if it is for a protocol being
        processed by the local bridging function, including
        bridge management frames."
    REFERENCE
        "ISO/IEC 15802-3 Section 14.6.1.1.3"
    ::= { dot1dTpHCPortEntry 1 }

dot1dTpHCPortOutFrames OBJECT-TYPE
    SYNTAX      Counter64
    MAX-ACCESS  read-only
    STATUS      current
    DESCRIPTION
        "The number of frames that have been transmitted by this
        port to its segment.  Note that a frame transmitted on
        the interface corresponding to this port is only counted
        by this object if and only if it is for a protocol being
        processed by the local bridging function, including
        bridge management frames."

    REFERENCE
        "ISO/IEC 15802-3 Section 14.6.1.1.3"
    ::= { dot1dTpHCPortEntry 2 }

dot1dTpHCPortInDiscards OBJECT-TYPE
    SYNTAX      Counter64
    MAX-ACCESS  read-only
    STATUS      current
    DESCRIPTION
        "Count of valid frames that have been received by this
        port from its segment which were discarded (i.e.,
        filtered) by the Forwarding Process."
    REFERENCE
        "ISO/IEC 15802-3 Section 14.6.1.1.3"
    ::= { dot1dTpHCPortEntry 3 }

-- ----------------------------------------------------
--  Upper part of High Capacity Port Table for Transparent Bridges
-- ----------------------------------------------------

dot1dTpPortOverflowTable OBJECT-TYPE
    SYNTAX      SEQUENCE OF Dot1dTpPortOverflowEntry
    MAX-ACCESS  not-accessible
    STATUS      current
    DESCRIPTION
        "A table that contains the most-significant bits of
        statistics counters for ports that are associated with this
        transparent bridge that are on high capacity interfaces, as
        defined in the conformance clauses for this table. This table
        is provided as a way to read 64-bit counters for agents which
        support only SNMPv1.

        Note that the reporting of most-significant and
        least-significant counter bits separately runs the risk of
        missing an overflow of the lower bits in the interval between
        sampling. The manager must be aware of this possibility, even
        within the same varbindlist, when interpreting the results of
        a request or asynchronous notification."
    ::= { dot1dTp 6 }

dot1dTpPortOverflowEntry OBJECT-TYPE
    SYNTAX      Dot1dTpPortOverflowEntry
    MAX-ACCESS  not-accessible

    STATUS      current
    DESCRIPTION
        "The most significant bits of statistics counters for a high
        capacity interface of a transparent bridge. Each object is
        associated with a corresponding object in dot1dTpPortTable
        which indicates the least significant bits of the counter."
    INDEX   { dot1dTpPort }
    ::= { dot1dTpPortOverflowTable 1 }

Dot1dTpPortOverflowEntry ::=
    SEQUENCE {
        dot1dTpPortInOverflowFrames
            Counter32,
        dot1dTpPortOutOverflowFrames
            Counter32,
        dot1dTpPortInOverflowDiscards
            Counter32
    }

dot1dTpPortInOverflowFrames OBJECT-TYPE
    SYNTAX      Counter32
    MAX-ACCESS  read-only
    STATUS      current
    DESCRIPTION
        "The number of times the associated dot1dTpPortInFrames
        counter has overflowed."
    REFERENCE
        "ISO/IEC 15802-3 Section 14.6.1.1.3"
    ::= { dot1dTpPortOverflowEntry 1 }

dot1dTpPortOutOverflowFrames OBJECT-TYPE
    SYNTAX      Counter32
    MAX-ACCESS  read-only
    STATUS      current
    DESCRIPTION
        "The number of times the associated dot1dTpPortOutFrames
        counter has overflowed."
    REFERENCE
        "ISO/IEC 15802-3 Section 14.6.1.1.3"
    ::= { dot1dTpPortOverflowEntry 2 }

dot1dTpPortInOverflowDiscards OBJECT-TYPE
    SYNTAX      Counter32
    MAX-ACCESS  read-only
    STATUS      current

    DESCRIPTION
        "The number of times the associated
        dot1dTpPortInDiscards counter has overflowed."
    REFERENCE
        "ISO/IEC 15802-3 Section 14.6.1.1.3"
    ::= { dot1dTpPortOverflowEntry 3 }

-- -------------------------------------------------------------
-- IEEE 802.1p MIB - Conformance Information
-- -------------------------------------------------------------

pBridgeConformance OBJECT IDENTIFIER ::= { pBridgeMIB 2 }

pBridgeGroups OBJECT IDENTIFIER ::= { pBridgeConformance 1 }

pBridgeCompliances OBJECT IDENTIFIER
    ::= { pBridgeConformance 2 }

-- -------------------------------------------------------------
-- units of conformance
-- -------------------------------------------------------------

pBridgeExtCapGroup OBJECT-GROUP
    OBJECTS {
        dot1dDeviceCapabilities,
        dot1dPortCapabilities
    }
    STATUS      current
    DESCRIPTION
        "A collection of objects indicating the optional
        capabilites of the device."
    ::= { pBridgeGroups 1 }

pBridgeDeviceGmrpGroup OBJECT-GROUP
    OBJECTS {
        dot1dGmrpStatus
    }
    STATUS      current
    DESCRIPTION
        "A collection of objects providing device-level control
        for the Multicast Filtering extended bridge services."
    ::= { pBridgeGroups 2 }

pBridgeDevicePriorityGroup OBJECT-GROUP
    OBJECTS {
        dot1dTrafficClassesEnabled
    }
    STATUS      current
    DESCRIPTION
        "A collection of objects providing device-level control
        for the Priority services."
    ::= { pBridgeGroups 3 }

pBridgeDefaultPriorityGroup OBJECT-GROUP
    OBJECTS {
        dot1dPortDefaultUserPriority
    }
    STATUS      current
    DESCRIPTION
        "A collection of objects defining the User Priority
        applicable to each port for media which do not support
        native User Priority."
    ::= { pBridgeGroups 4 }

pBridgeRegenPriorityGroup OBJECT-GROUP
    OBJECTS {
        dot1dRegenUserPriority
    }
    STATUS      current
    DESCRIPTION
        "A collection of objects defining the User Priorities
        applicable to each port for media which support native
        User Priority."
    ::= { pBridgeGroups 5 }

pBridgePriorityGroup OBJECT-GROUP
    OBJECTS {
        dot1dPortNumTrafficClasses,
        dot1dTrafficClass
    }
    STATUS      current
    DESCRIPTION
        "A collection of objects defining the traffic classes
        within a bridge for each evaluated User Priority."
    ::= { pBridgeGroups 6 }

pBridgeAccessPriorityGroup OBJECT-GROUP
    OBJECTS {
        dot1dPortOutboundAccessPriority
    }
    STATUS      current
    DESCRIPTION
        "A collection of objects defining the media dependent
        outbound access level for each priority."
    ::= { pBridgeGroups 7 }

pBridgePortGarpGroup OBJECT-GROUP
    OBJECTS {
        dot1dPortGarpJoinTime,
        dot1dPortGarpLeaveTime,
        dot1dPortGarpLeaveAllTime
    }
    STATUS      current
    DESCRIPTION
        "A collection of objects providing port level control
        and status information for GARP operation."
    ::= { pBridgeGroups 8 }

pBridgePortGmrpGroup OBJECT-GROUP
    OBJECTS {
        dot1dPortGmrpStatus,
        dot1dPortGmrpFailedRegistrations,
        dot1dPortGmrpLastPduOrigin
    }
    STATUS      current
    DESCRIPTION
        "A collection of objects providing port level control
        and status information for GMRP operation."
    ::= { pBridgeGroups 9 }

pBridgeHCPortGroup OBJECT-GROUP
    OBJECTS {
        dot1dTpHCPortInFrames,
        dot1dTpHCPortOutFrames,
        dot1dTpHCPortInDiscards
    }
    STATUS      current
    DESCRIPTION
        "A collection of objects providing 64-bit statistics
         counters for high capacity bridge ports."
    ::= { pBridgeGroups 10 }

pBridgePortOverflowGroup OBJECT-GROUP
    OBJECTS {
        dot1dTpPortInOverflowFrames,
        dot1dTpPortOutOverflowFrames,
        dot1dTpPortInOverflowDiscards
    }
    STATUS      current
    DESCRIPTION
        "A collection of objects providing overflow statistics
        counters for high capacity bridge ports."
    ::= { pBridgeGroups 11 }

-- -------------------------------------------------------------
-- compliance statements
-- -------------------------------------------------------------

pBridgeCompliance MODULE-COMPLIANCE
    STATUS  current
    DESCRIPTION
        "The compliance statement for device support of Priority
        and Multicast Filtering extended bridging services."

    MODULE
        MANDATORY-GROUPS { pBridgeExtCapGroup }

        GROUP       pBridgeDeviceGmrpGroup
        DESCRIPTION
            "This group is mandatory for devices supporting the GMRP
            application, defined by IEEE 802.1D Extended Filtering
            Services."

        GROUP       pBridgeDevicePriorityGroup
        DESCRIPTION
            "This group is mandatory only for devices supporting
            the priority forwarding operations defined by IEEE
            802.1D."

        GROUP       pBridgeDefaultPriorityGroup
        DESCRIPTION
            "This group is mandatory only for devices supporting
            the priority forwarding operations defined by the
            extended bridge services with media types, such as
            Ethernet, that do not support native User Priority."

        GROUP       pBridgeRegenPriorityGroup
        DESCRIPTION
            "This group is mandatory only for devices supporting
            the priority forwarding operations defined by IEEE 802.1D
            and which have interface media types that support
            native User Priority e.g. IEEE 802.5."

        GROUP       pBridgePriorityGroup
        DESCRIPTION
            "This group is mandatory only for devices supporting
            the priority forwarding operations defined by IEEE 802.1D."

        GROUP       pBridgeAccessPriorityGroup
        DESCRIPTION
            "This group is optional and is relevant only for devices
            supporting the priority forwarding operations defined by
            IEEE 802.1D and which have interface media types that support
            native Access Priority e.g. IEEE 802.5."

        GROUP       pBridgePortGarpGroup
        DESCRIPTION
            "This group is mandatory for devices supporting any
            of the GARP applications: e.g. GMRP, defined by the
            extended filtering services of 802.1D; or GVRP,
            defined by 802.1Q (refer to the Q-BRIDGE-MIB for
            conformance statements for GVRP)."

        GROUP       pBridgePortGmrpGroup
        DESCRIPTION
            "This group is mandatory for devices supporting the
            GMRP application, as defined by IEEE 802.1D Extended
            Filtering Services."

        GROUP       pBridgeHCPortGroup
        DESCRIPTION
            "Support for this group in a device is mandatory for those
            bridge ports which map to network interfaces that have the
            value of the corresponding instance of ifSpeed
            greater than 650,000,000 bits/second."

        GROUP       pBridgePortOverflowGroup
        DESCRIPTION
            "Support for this group in a device is mandatory for those
            bridge ports which map to network interfaces that have the
            value of the corresponding instance of ifSpeed
            greater than 650,000,000 bits/second."

        OBJECT      dot1dPortNumTrafficClasses
        MIN-ACCESS  read-only
        DESCRIPTION
            "Write access is not required."

        OBJECT      dot1dTrafficClass
        MIN-ACCESS  read-only
        DESCRIPTION
            "Write access is not required."

        OBJECT      dot1dRegenUserPriority
        MIN-ACCESS  read-only
        DESCRIPTION
            "Write access is not required."

       ::= { pBridgeCompliances 1 }

END

------------------------------------------------------------------------------
------------------------------------------------------------------------------
--
--  File         : lanBridgeMib.mib
--  Description  : ZTE ADSL lan Bridge MIB  
--
------------------------------------------------------------------------------
------------------------------------------------------------------------------

LAN-BRIDGE-MIB DEFINITIONS ::= BEGIN

	IMPORTS
    		MODULE-IDENTITY, OBJECT-TYPE,
    		Counter32, Counter64, Unsigned32, TimeTicks,
			Integer32, enterprises					FROM SNMPv2-SMI
    
    		RowStatus, TruthValue, TEXTUAL-CONVENTION, MacAddress
        											FROM SNMPv2-TC
        											
			MODULE-COMPLIANCE, OBJECT-GROUP			FROM SNMPv2-CONF

			dot1dBridge, dot1dBasePortEntry, dot1dBasePort
													FROM BRIDGE-MIB;

------------------------------------------------------------------------------
------------------------------------------------------------------------------

    zte MODULE-IDENTITY
        LAST-UPDATED    "2002-05-21-00"  -- August 29, 2000
        ORGANIZATION    "ZTE Corporation."
        CONTACT-INFO    "ZTE Corporation.
                         http://www.zte.com.cn"
        DESCRIPTION     "ZTE ADSL lan Bridge MIB OID defines and documentation."
        REVISION        "0008290000Z"  -- August 29, 2000
        DESCRIPTION     "Initial MIB creation."

        ::= { enterprises 3902 }
    
-- DSL Products
	zxDsl	OBJECT IDENTIFIER ::= { zte 1004 }
	zxDslam OBJECT IDENTIFIER ::= { zxDsl 1 }
	zxLan	OBJECT IDENTIFIER ::= { zxDslam 10 }
------------------------------------------------------------------------------
------------------------------------------------------------------------------
--	lanCommon	OBJECT IDENTIFIER ::= { zxLan 2 }
	lanBridge	OBJECT IDENTIFIER ::= { zxLan 5 }
------------------------------------------------------------------------------
------------------------------------------------------------------------------
-- groups in the Q-BRIDGE MIB
---------------------------------------------------------------
    lanBridgeOnOff OBJECT-TYPE
        SYNTAX INTEGER {
               enable(1),
               disable(2)
        }
        MAX-ACCESS read-write
        STATUS current
        DESCRIPTION
            "DURABLE: { enable }
             Enable/Disable the bridge and the SAR functions."
        ::= { lanBridge 1 }


---------------------------------------------------------------
---------------------------------------------------------------
-- Textual Conventions
---------------------------------------------------------------
EnabledStatus ::= TEXTUAL-CONVENTION
    STATUS      current
    DESCRIPTION
        "A simple status value for the object."
    SYNTAX      INTEGER { enabled(1), disabled(2) }

TimeFilter ::= TEXTUAL-CONVENTION
    STATUS        current
    DESCRIPTION
        "To be used for the index to a table.  Allows an application
        to download only those rows changed since a particular time.
        A row is considered changed if the value of any object in the
        row changes or if the row is created or deleted.

        When sysUpTime is equal to zero, this table shall be empty.

        One entry exists for each past value of sysUpTime, except that
        the whole table is purged should sysUpTime wrap.

        As this basic row is updated new conceptual rows are created
        (which still share the now updated object values with all
        other instances).  The number of instances which are created
        is determined by the value of sysUpTime at which the basic row
        was last updated.  One instance will exist for each value of
        sysUpTime at the last update time for the row.  A new
        timeMark instance is created for each new sysUpTime value.
        Each new conceptual row will be associated with the timeMark
        instance which was created at the value of sysUpTime with
        which the conceptual row is to be associated.

        By definition all conceptual rows were updated at or after
        time zero and so at least one conceptual row (associated with
        timeMark.0) must exist for each underlying (basic) row.

        See the appendix for further discussion of this variable.

        Consider the following fooTable:

        fooTable ...
        INDEX { fooTimeMark, fooIndex }

        FooEntry {
           fooTimeMark  TimeFilter
           fooIndex     INTEGER,
           fooCounts    Counter
        }

        Should there be two basic rows in this table (fooIndex == 1,
        fooIndex == 2) and row 1 was updated most recently at time 6,
        while row 2 was updated most recently at time 8, and both rows
        had been updated on several earlier occasions such that the
        current values were 5 and 9 respectively then the following
        fooCounts instances would exist.

        fooCounts.0.1  5
        fooCounts.0.2  9
        fooCounts.1.1  5
        fooCounts.1.2  9
        fooCounts.2.1  5
        fooCounts.2.2  9
        fooCounts.3.1  5
        fooCounts.3.2  9
        fooCounts.4.1  5
        fooCounts.4.2  9
        fooCounts.5.1  5
        fooCounts.5.2  9
        fooCounts.6.1  5
        fooCounts.6.2  9
        fooCounts.7.2  9    -- note that row 1 doesn't exist for
        fooCounts.8.2  9    -- times 7 and 8"
    SYNTAX    TimeTicks

   SnmpAdminString ::= TEXTUAL-CONVENTION
       DISPLAY-HINT "255a"
       STATUS       current
       DESCRIPTION "An octet string containing administrative
                    information, preferably in human-readable form.

                    To facilitate internationalization, this
                    information is represented using the ISO/IEC
                    IS 10646-1 character set, encoded as an octet
                    string using the UTF-8 transformation format
                    described in [RFC2044].

                    Since additional code points are added by
                    amendments to the 10646 standard from time
                    to time, implementations must be prepared to
                    encounter any code point from 0x00000000 to
                    0x7fffffff.

                    The use of control codes should be avoided.

                    When it is necessary to represent a newline,
                    the control code sequence CR LF should be used.
                    The use of leading or trailing white space should
                    be avoided.

                    For code points not directly supported by user
                    interface hardware or software, an alternative
                    means of entry and display, such as hexadecimal,
                    may be provided.

                    For information encoded in 7-bit US-ASCII,
                    the UTF-8 encoding is identical to the
                    US-ASCII encoding.

                    Note that when this TC is used for an object that
                    is used or envisioned to be used as an index, then
                    a SIZE restriction must be specified so that the
                    number of sub-identifiers for any object instance
                    does not exceed the limit of 128, as defined by
                    [RFC1905].
                   "
       SYNTAX       OCTET STRING (SIZE (0..255))
       
PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING

VlanIndex ::= TEXTUAL-CONVENTION
    STATUS      current
    DESCRIPTION
        "A value used to index per-VLAN tables: values of 0 and
        4095 are not permitted; if the value is between 1 and
        4094 inclusive, it represents an IEEE 802.1Q VLAN-ID with
        global scope within a given bridged domain (see VlanId
        textual convention).  If the value is greater than 4095
        then it represents a VLAN with scope local to the
        particular agent, i.e. one without a global VLAN-ID
        assigned to it. Such VLANs are outside the scope of
        IEEE 802.1Q but it is convenient to be able to manage them
        in the same way using this MIB."
    SYNTAX      Unsigned32

VlanId ::= TEXTUAL-CONVENTION
    STATUS      current
    DESCRIPTION
        "A 12-bit VLAN ID used in the VLAN Tag header."
    SYNTAX      INTEGER (1..4094)

---------------------------------------------------------------
---------------------------------------------------------------
-- The dot1qBridgeVlanStatic Group 
---------------------------------------------------------------

lanVlanStaticTable OBJECT-TYPE
    SYNTAX      SEQUENCE OF LanVlanStaticEntry
    MAX-ACCESS  not-accessible
    STATUS      current
    DESCRIPTION
        "A table containing static configuration information for
        each VLAN configured into the device by (local or
        network) management.  All entries are permanent and will
        be restored after the device is reset."
    ::= { lanBridge 2 }

lanVlanStaticEntry OBJECT-TYPE
    SYNTAX      LanVlanStaticEntry
    MAX-ACCESS  not-accessible
    STATUS      current
    DESCRIPTION
        "Static information for a VLAN configured into the
        device by (local or network) management."
    INDEX   { lanVlanIndex }
    ::= { lanVlanStaticTable 1 }

LanVlanStaticEntry ::=
    SEQUENCE {
        lanVlanIndex
            VlanIndex,
        lanVlanStaticName
            SnmpAdminString,
        lanVlanStaticEgressPorts
            PortList,
        lanVlanStaticRowStatus
            RowStatus
    }

lanVlanIndex OBJECT-TYPE
    SYNTAX      VlanIndex
    MAX-ACCESS  not-accessible
    STATUS      current
    DESCRIPTION
        "The VLAN-ID or other identifier refering to this VLAN."
    ::= { lanVlanStaticEntry 1 }

lanVlanStaticName OBJECT-TYPE
    SYNTAX      SnmpAdminString (SIZE (0..32))
    MAX-ACCESS  read-create
    STATUS      current
    DESCRIPTION
        "An administratively assigned string, which may be used
        to identify the VLAN."
    REFERENCE
        "IEEE 802.1Q/D11 Section 12.10.2.1"
    ::= { lanVlanStaticEntry 2 }

lanVlanStaticEgressPorts OBJECT-TYPE
  SYNTAX      PortList
  MAX-ACCESS  read-create
  STATUS      current
  DESCRIPTION
      "The set of ports which are permanently assigned to the
      egress list for this VLAN by management.  Changes to a
      bit in this object affect the per-port per-VLAN
      Registrar control for Registration Fixed for the
      relevant GVRP state machine on each port.  A port may
      not be added in this set if it is already a member of
      the set of ports in dot1qVlanForbiddenEgressPorts.  The
      default value of this object is a string of zeros of
      appropriate length, indicating not fixed."
  REFERENCE
        "IEEE 802.1Q/D11 Section 12.7.7.3, 11.2.3.2.3"
    ::= { lanVlanStaticEntry 3 }

lanVlanStaticRowStatus OBJECT-TYPE
    SYNTAX      RowStatus
    MAX-ACCESS  read-create
    STATUS      current
    DESCRIPTION
        "This object indicates the status of this entry."
    ::= { lanVlanStaticEntry 4 }

----------------------------------------
----------------------------------------
-- lanPortVlanTable Group
----------------------------------------

lanPortVlanTable OBJECT-TYPE
    SYNTAX      SEQUENCE OF LanPortVlanEntry
    MAX-ACCESS  not-accessible
    STATUS      current
    DESCRIPTION
        "A table containing per port control and status
        information for VLAN configuration in the device."
    ::= { lanBridge 4 }

lanPortVlanEntry OBJECT-TYPE
    SYNTAX      LanPortVlanEntry
    MAX-ACCESS  not-accessible
    STATUS      current
    DESCRIPTION
        "Information controlling VLAN configuration for a port
        on the device.  This is indexed by dot1dBasePort."
    INDEX  { lanBasePort }
    ::= { lanPortVlanTable 1 }

LanPortVlanEntry ::=
    SEQUENCE {
        lanBasePort
            INTEGER,
        lanPvid
            VlanIndex
    }

lanBasePort OBJECT-TYPE
    SYNTAX  INTEGER (2..1000)
    ACCESS  read-only
    STATUS  mandatory
    DESCRIPTION
            "The port number of the port for which this entry
            contains bridge management information."
    ::= { lanPortVlanEntry 1 }

lanPvid OBJECT-TYPE
    SYNTAX      VlanIndex
    MAX-ACCESS  read-write
    STATUS      current
    DESCRIPTION
        "The PVID, the VLAN ID assigned to untagged frames or
        Priority-Tagged frames received on this port."
    REFERENCE
        "IEEE 802.1Q/D11 Section 12.10.1.1"
    DEFVAL      { 1 }
    ::= { lanPortVlanEntry 2 }


----------------------------------------
----------------------------------------
-- vcxNumber
----------------------------------------
    lanVcxNumber OBJECT-TYPE
        SYNTAX INTEGER (0..998)
        MAX-ACCESS read-write
        STATUS current
        DESCRIPTION
            "Total Vci Number"
        ::= { lanBridge 3 }

-- END of LAN-BRIDGE-MIB                
END


------------------------------------------------------------------------------
------------------------------------------------------------------------------
--
--  File         : lanMib.mib
--  Description  : ZTE lan MIB  
--
------------------------------------------------------------------------------
------------------------------------------------------------------------------

LAN-MIB DEFINITIONS ::= BEGIN

	IMPORTS
			MODULE-IDENTITY, OBJECT-TYPE,
			Integer32, enterprises					FROM SNMPv2-SMI

			MODULE-COMPLIANCE, OBJECT-GROUP			FROM SNMPv2-CONF

--			zxLan									FROM WRS-MASTER-MIB

			PortList, dot1qStaticMulticastEntry		FROM Q-BRIDGE-MIB;       

------------------------------------------------------------------------------
------------------------------------------------------------------------------

    zte MODULE-IDENTITY
        LAST-UPDATED    "0008290000Z"  -- August 29, 2000
        ORGANIZATION    "Wind River Systems, Inc."
        CONTACT-INFO    "Wind River Systems, Inc.
                         E-mail: support@windriver.com"

        DESCRIPTION     "WRS Master MIB OID defines and documentation."

        REVISION        "0008290000Z"  -- August 29, 2000
        DESCRIPTION     "Initial MIB creation."

        ::= { enterprises 3902 }
    
-- DSL Products
	zxDsl	OBJECT IDENTIFIER ::= { zte 1004 }
	zxDslam OBJECT IDENTIFIER ::= { zxDsl 1 }
	zxLan	OBJECT IDENTIFIER ::= { zxDslam 10 }
------------------------------------------------------------------------------
------------------------------------------------------------------------------

	lanCommon	OBJECT IDENTIFIER ::= { zxLan 2 }
--	lanBridge	OJBECT IDENTIFIER ::= { zxLan 5 }
------------------------------------------------------------------------------
------------------------------------------------------------------------------

    lanCleanFlash OBJECT-TYPE
        SYNTAX INTEGER {
               noop(1),            -- no operation
               clean(2),           -- clean the data in flash
               cleanInProgress(3)  -- read-only: flash clean in progress
        }
        MAX-ACCESS read-write
        STATUS current
        DESCRIPTION
            "When set to 'clean(2)', the data in flash are cleaned . This
             operations may be slow . Consequently, all or many updates 
             should be made before cleaning the flash.  Note that the SNMP
             set to 'clean(2)' returns immediately to the caller.  Gets on
             this object then return  'cleanInProgress(3)' until the clean
             operation completes, at which time 'noop(1)' is returned.  
             Consequently, a get operation always returns 'noop(1)' or 
             'cleanInProgress(3)' depending on the current state.
             
             The agent returns 'badValue' for SNMPv1 or 'inconsistentValue'
             for SNMPv2c/v3 for a set to 'clean(2)' while the current get
             state is 'cleanInProgress(3)'.
             
             Attempts to set this object to 'cleanInProgress(3)' returns
             'badValue' for SNMPv1 or 'wrongValue' for SNMPv2c/v3."
        ::= { lanCommon 1 }


    lanReset OBJECT-TYPE
        SYNTAX INTEGER {
               noop(1),           -- no operation
               reset(2),          -- reset unit
               resetToDefaults(3) -- reset to factory defaults/reset unit
        }
        MAX-ACCESS read-write
        STATUS current
        DESCRIPTION
            "Physically performs a hardware reset of the unit. 
             Use with care.  A 'reset(2)' resets the unit, a
             'resetToDefaults(3)' resets the NVM configuration
             to factory defaults and then resets the unit, and 'noop(1)'
             does nothing.  A value of 'noop(1)' is always returned for a
             GET operation."
        ::= { lanCommon 2 }

    lanVersionNumber OBJECT-TYPE
        SYNTAX OCTET STRING (SIZE (0..4))
        MAX-ACCESS read-only
        STATUS current
        DESCRIPTION
            "Get this MIB Major version number.  This number should 
             match the Major version given in the documentation header
             at the beginning text of this MIB.  Note that the '.c' file
             corresponding to this MIB has to be manually edited to
             change the version number if this file is modified and
             the version number is therefore changed."
        ::= { lanCommon 3 }


    lanSaveFlash OBJECT-TYPE
        SYNTAX INTEGER {
               noop(1),           -- no operation
               save(2),           -- save all configuration parameters to NVM
               saveInProgress(3)  -- read-only: NVM save in progress
        }
        MAX-ACCESS read-write
        STATUS current
        DESCRIPTION
            "When set to 'save(2)', all nonvolatile configuration
             parameters are saved to NVM (Nonvolatile Memory).  NVM save
             operations may be slow (e.g., erasing/writing Flash device).
             Consequently, all or many updates should be made before
             saving to NVM.  Note that the SNMP set to 'save(2)' returns
             immediately to the caller.  Gets on this object then return
             'saveInProgress(3)' until the save operation completes, at
             which time 'noop(1)' is returned.  Consequently, a get
             operation always returns 'noop(1)' or 'saveInProgress(3)'
             depending on the current state.
             
             The agent returns 'badValue' for SNMPv1 or 'inconsistentValue'
             for SNMPv2c/v3 for a set to 'Save(2)' while the current get
             state is 'saveInProgress(3)'.
             
             Attempts to set this object to 'saveInProgress(3)' returns
             'badValue' for SNMPv1 or 'wrongValue' for SNMPv2c/v3."
        ::= { lanCommon 4 }

    lanSpanOnOff OBJECT-TYPE
        SYNTAX INTEGER {
               enable(1),
               disable(2)
        }
        MAX-ACCESS read-write
        STATUS current
        DESCRIPTION
            "DURABLE: { enable }
             Enable/Disable Spanning Tree for the bridge.
             When 'disable(2)', all ports of the device are placed in the
             forwarding mode, regardless of current Spanning Tree state.
             When 'enable(1)', the normal STP state transitions take place."
        ::= { lanCommon 5 }

    lanLACPOnOff OBJECT-TYPE
        SYNTAX INTEGER {
               enable(1),
               disable(2)
        }
        MAX-ACCESS read-write
        STATUS current
        DESCRIPTION
            "DURABLE: { disable }
             Enable/Disable LACP operation for the TMS agent.
             When 'disable(2)', no LACP's are transmitted by the Application.
             When enabled, the Application sends LACP requests during
             system startup."
        ::= { lanCommon 6 }

    lanIgmpSnoopOnOff  OBJECT-TYPE
        SYNTAX INTEGER {
               enable(1),
               disable(2)
        }
        MAX-ACCESS read-write
        STATUS current
        DESCRIPTION
            "DURABLE: { disable }
             Enable/Disable IGMP Snooping operation for the TMS agent.
             Setting this object to enable(1) enables IGMP Snooping.  Setting
             it to disable(2) disables IGMP Snooping.
             
             Note that IGMP Snooping can function with or without GVRP and
             GMRP enabled."
        ::= { lanCommon 7 }

    lanIgmpSnoopAlertsOnOff  OBJECT-TYPE
        SYNTAX INTEGER {
               enable(1),
               disable(2)
        }
        MAX-ACCESS read-write
        STATUS current
        DESCRIPTION
            "DURABLE: { disable }
             Setting this object to enable(1) enables the IP Router Alert
             Option (as defined in RFC2113) for transmitted IGMP packets.
             Setting it to disable(2) disables this option."
        ::= { lanCommon 8 }

    lanIgmpSnoopAging  OBJECT-TYPE
        SYNTAX INTEGER (30..3600)
        MAX-ACCESS read-write
        STATUS current
        DESCRIPTION
            "DURABLE: { 300 }
             The timeout period in seconds for aging out Multicast Groups
             dynamically learned with IGMP Snooping.  Note that aging operates
             on a per interface per VLAN per multicast group basis."
        ::= { lanCommon 9 }

    lanIgmpSnoopTable OBJECT-TYPE
        SYNTAX           SEQUENCE OF LanIgmpSnoopEntry
        MAX-ACCESS not-accessible
        STATUS current
        DESCRIPTION
            "This table, which provides IGMP Snooping information, augments
             the 'dot1qStaticMulticastTable' in the Q-MIB (RFC2674)."
        ::= { lanCommon 10 }
        
    lanBoardID  OBJECT-TYPE
        SYNTAX Integer32 
        MAX-ACCESS read-only
        STATUS current
        DESCRIPTION
            "lan Board standing in the dislam"
        ::= { lanCommon 11 }

-------------------------------------------------
   tmsCommonIPMACAddr OBJECT-TYPE
        SYNTAX MacAddress
        MAX-ACCESS read-write
        STATUS current
        DESCRIPTION
            "DURABLE: { '000000000000'H }
             The base (i.e., first) MAC address used by the TMS agent for its
             in-band ports."
        ::= { lanCommon 12 }

    lanIgmpSnoopEntry OBJECT-TYPE
        SYNTAX LanIgmpSnoopEntry
        MAX-ACCESS not-accessible
        STATUS current
        DESCRIPTION
            "Displays by VLAN, Multicast Group, and Multicast receive port
             the set of ports enabled to forward Multicast Group traffic as
             determined by the IGMP Snooping task."
        AUGMENTS { dot1qStaticMulticastEntry }
        ::= { lanIgmpSnoopTable 1 }

    LanIgmpSnoopEntry ::= SEQUENCE {
        lanIgmpSnoopEgressPorts   PortList
    }

    lanIgmpSnoopEgressPorts  OBJECT-TYPE
        SYNTAX PortList
        MAX-ACCESS read-only
        STATUS current
        DESCRIPTION
            "This read-only object displays the set of ports enabled to
             forward specific Multicast Group traffic as determined by the
             IGMP Snooping task.
            
             It should be noted that the IGMP Snooping task generates a pseudo-
             static (i.e., not saved in NVM) port list similar to the RFC2674
             Q-MIB 'dot1qStaticMulticastStaticEgressPorts' object. Consequently,
             a port will not be a member of 'tmsCommonIgmpSnoopEgressPorts' if
             it is a member of 'dot1qStaticMulticastForbiddenEgressPorts'."
        ::= { lanIgmpSnoopEntry 1 }

-- END of LAN-MIB                
END


------------------------------------------------------------------------------
--  File         : LAN-LAG-MIB   -- Trunk mib
------------------------------------------------------------------------------
    LAN-LAG-MIB DEFINITIONS ::= BEGIN

    IMPORTS
        MODULE-IDENTITY, OBJECT-TYPE,
        Integer32                               FROM SNMPv2-SMI
        
        lanGeneric                              FROM WRS-MASTER-MIB
                     
        dot1dBasePortEntry                      FROM BRIDGE-MIB;       

	
--	lanGeneric  OBJECT IDENTIFIER ::= { zxLan 3 }

    lanComLagMib         OBJECT IDENTIFIER  ::= { lanGeneric 2 }
    lagStatic               OBJECT IDENTIFIER ::= {lanComLagMib 1}
    
    dot8023adPortTable OBJECT-TYPE
        SYNTAX      SEQUENCE OF Dot8023adPortEntry
        MAX-ACCESS  not-accessible
        STATUS      current
        DESCRIPTION
          "A table containing per port control and status
           information for port configuration in the device."
        ::= { lagStatic 1 }

    dot8023adPortEntry OBJECT-TYPE
        SYNTAX      Dot8023adPortEntry
        MAX-ACCESS  not-accessible
        STATUS      current
        DESCRIPTION
        "Information controlling Aggregator configuration for a port
        on the device.  This is indexed by dot1dBasePort."
        AUGMENTS { dot1dBasePortEntry }
        ::= { dot8023adPortTable 1 }

    Dot8023adPortEntry ::=
        SEQUENCE {
           dot8023adAggNo  Integer32
        }

    dot8023adAggNo OBJECT-TYPE
        SYNTAX      Integer32
        MAX-ACCESS  read-write
        STATUS      current
        DESCRIPTION
          "The aggIndex  assigned to this port."
        REFERENCE
          "IEEE 802.3ad"
        ::= { dot8023adPortEntry 1 }
END



   HDSL2-SHDSL-LINE-MIB DEFINITIONS ::= BEGIN

   IMPORTS
   MODULE-IDENTITY,
   OBJECT-TYPE,
   Counter32,
   Gauge32,
   NOTIFICATION-TYPE,
   Integer32,                    
   transmission                  FROM SNMPv2-SMI
   RowStatus,
   TEXTUAL-CONVENTION            FROM SNMPv2-TC
   ifIndex                       FROM IF-MIB
   PerfCurrentCount,
   PerfIntervalCount             FROM PerfHist-TC-MIB
   SnmpAdminString               FROM SNMP-FRAMEWORK-MIB
   MODULE-COMPLIANCE,
   OBJECT-GROUP,
   NOTIFICATION-GROUP            FROM SNMPv2-CONF;

   hdsl2ShdslMIB MODULE-IDENTITY
       LAST-UPDATED "200201030000Z" -- January 3, 2002
       ORGANIZATION "ADSLMIB Working Group"
       CONTACT-INFO "WG-email:  XDSLMIB@LISTSERV.ECIRALEIGH.COM 
                  Subscribe: LISTSERV@LISTSERV.ECIRALEIGH.COM 
                             In Body: subscribe/signoff XDSLMIB 
                             Archive: index XDSLMIB/get <archivename> 

                  Chair:     Mike Sneed
                             ECI Telecom
                  Postal:    1017 Main Campus Drive
                             Raleigh NC 27606 USA
                  Email:     Mike.Sneed@go.ecitele.com
                  Phone:     +1 919 513 1435

                  Co-editor: Bob Ray
                             Verilink Corporation
                  Postal:    950 Explorer Blvd
                             Huntsville, AL 35806 USA
                  Email:     bray@verilink.com
                  Phone:     +1 256 327 2380

                  Co-editor: Rajesh Abbi
                             Alcatel USA
                  Postal:    2912 Wake Forest Road
                             Raleigh, NC 27609-7860 USA
                  Email:     Rajesh.Abbi@usa.alcatel.com
                  Phone:     +1 919 850 6194
                 "

   DESCRIPTION
        "This MIB module defines a collection of objects for managing
         HDSL2/SHDSL lines.  An agent may reside at either end of the
         line, however the MIB is designed to require no management
         communication between the modems beyond that inherent in the
         low-level EOC line protocol as defined in ANSI T1E1.4/2000-006
         (for HDSL2 lines), or in ITU G.991.2 (for SHDSL lines)."
    REVISION "200201030000Z" -- January 3, 2001
    DESCRIPTION "Initial version, published as internet draft."

    ::= { transmission 169 } -- to be assigned by IANA

   hdsl2ShdslMibObjects OBJECT IDENTIFIER ::= { hdsl2ShdslMIB 1 }

   -- Textual Conventions used in this MIB
   --

   Hdsl2ShdslPerfCurrDayCount ::= TEXTUAL-CONVENTION
      STATUS    current
      DESCRIPTION
        "A gauge associated with interface performance measurements in
         a current 1-day (24 hour) measurement interval.

         The value of this gauge starts at zero at the beginning of an
         interval and is increased when associated events occur, until
         the end of the 1-day interval.  At that time the value of the
         gauge is stored in the previous 1-day history interval, as
         defined in a companion object of type 
         Hdsl2Shdsl1DayIntevalCount, and the current interval gauge
         is restarted at zero.

         In the case where the agent has no valid data available for 
         this interval the corresponding object instance is not 
         available and upon a retrieval request a corresponding error 
         message shall be returned to indicate that this instance does
         not exist.  Please note that zero is a valid value."
      SYNTAX  Gauge32

   Hdsl2Shdsl1DayIntervalCount ::= TEXTUAL-CONVENTION
      STATUS    current
      DESCRIPTION
        "A counter associated with interface performance measurements
         during the most previous 1-day (24 hour) measurement interval.
         The value of this gauge is equal to the value of the current
         day gauge, as defined in a companion object of type
         Hdsl2ShdslPerfCurrDayCount, at the end of its most recent 
         interval.
         In the case where the agent has no valid data available for 
         this interval the corresponding object instance is not 
         available and upon a retrieval request a corresponding error
         message shall be returned to indicate that this instance does
         not exist."
      SYNTAX  Gauge32

   Hdsl2ShdslPerfTimeElapsed ::= TEXTUAL-CONVENTION
      STATUS    current
      DESCRIPTION
        "The number of seconds that have elapsed since the beginning of
         the current measurement period.  If, for some reason, such as
         an adjustment in the system's time-of-day clock or the addition
         of a leap second, the current interval exceeds the maximum 
         value, the agent will return the maximum value.

         For 15 minute intervals, the range is limited to (0..899).
         For 24 hour intervals, the range is limited to (0..86399)."
      SYNTAX    INTEGER(0..86399)

   Hdsl2ShdslPerfIntervalThreshold ::= TEXTUAL-CONVENTION
      STATUS    current
      DESCRIPTION
        "This convention defines a range of values that may be set in 
         a fault threshold alarm control.  As the number of seconds in
         a 15-minute interval numbers at most 900, objects of this type
         may have a range of 0...900, where the value of 0 disables the
         alarm."
      SYNTAX    INTEGER(0..900)

   Hdsl2ShdslUnitId ::= TEXTUAL-CONVENTION
      STATUS    current
      DESCRIPTION
        "This is the unique identification for all units in a 
         HDSL2/SHDSL Span.  It is based on the EOC unit addressing 
         scheme with reference to the xtuC."
      SYNTAX    INTEGER
              {
              xtuC(1),
              xtuR(2),
              xru1(3),
              xru2(4),
              xru3(5),
              xru4(6),
              xru5(7),
              xru6(8),
              xru7(9),
              xru8(10)
              }

   Hdsl2ShdslUnitSide ::= TEXTUAL-CONVENTION
      STATUS    current
      DESCRIPTION
        "This is the referenced side of a HDSL2/SHDSL unit - Network 
         or Customer side.  The side facing the Network is the Network 
         side, while the side facing the Customer is the Customer side."
      SYNTAX    INTEGER
              {
              networkSide(1),
              customerSide(2)
              }

   Hdsl2ShdslWirePair ::= TEXTUAL-CONVENTION
      STATUS    current
      DESCRIPTION
        "This is the referenced pair of wires in a HDSL2/SHDSL Segment.
         HDSL2 only supports a single pair (wirePair1), while SHDSL
         supports an optional second pair (wirePair2)."
      SYNTAX    INTEGER
              {
              wirePair1(1),
              wirePair2(2)
              }

   Hdsl2ShdslTransmissionModeType ::= TEXTUAL-CONVENTION
      STATUS    current
      DESCRIPTION
        "Contains the regional setting of the HDSL2/SHDSL span,
        represented as a bit-map of possible settings. The various 
        bit positions are:

        Bit   Meaning      Description
        1     region 1     Indicates ITU-T G.991.2 Annex A.
        2     region 2     Indicates ITU-T G.991.2 Annex B."
      SYNTAX      BITS
              {
              region1(0),
              region2(1)
              }

   Hdsl2ShdslClockReferenceType ::= TEXTUAL-CONVENTION
      STATUS    current
      DESCRIPTION
        "The various STU-C symbol clock references for the
        HDSL2/SHDSL span, represented as an enumeration."
      SYNTAX    INTEGER
             {
             localClk(1),          -- Mode-1 per G991.2
             networkClk(2),        -- Mode-2 per G991.2
             dataOrNetworkClk(3),  -- Mode-3a per G991.2
             dataClk(4)            -- Mode-3b per G991.2
             }

   -- Span Configuration Group

   --

   hdsl2ShdslSpanConfTable OBJECT-TYPE
      SYNTAX     SEQUENCE OF Hdsl2ShdslSpanConfEntry
      MAX-ACCESS not-accessible
      STATUS     current
      DESCRIPTION
        "This table supports overall configuration of HDSL2/SHDSL
         Spans.  Entries in this table MUST be maintained in a
         persistent manner."
      ::= { hdsl2ShdslMibObjects 1 }

   hdsl2ShdslSpanConfEntry OBJECT-TYPE
      SYNTAX      Hdsl2ShdslSpanConfEntry
      MAX-ACCESS  not-accessible
      STATUS      current
      DESCRIPTION
        "An entry in the hdsl2ShdslSpanConfTable.  Each entry 
         represents the complete Span in a single HDSL2/SHDSL line.
         It is indexed by the ifIndex of the associated HDSL2/SHDSL
         line."
      INDEX { ifIndex }
      ::= { hdsl2ShdslSpanConfTable 1 }

   Hdsl2ShdslSpanConfEntry ::=
      SEQUENCE
      {
--      hdsl2ShdslSpanConfNumRepeaters          INTEGER,
      hdsl2ShdslSpanConfProfile               SnmpAdminString,
      hdsl2ShdslSpanConfAlarmProfile          SnmpAdminString
      }

--   hdsl2ShdslSpanConfNumRepeaters OBJECT-TYPE
--      SYNTAX      INTEGER(0..8)
--      UNITS       "repeaters"
--      MAX-ACCESS  read-write
--      STATUS      current
--      DESCRIPTION
--        "This object provisions the number of repeaters/regenerators 
--        in this HDSL2/SHDSL Span."
--      ::= { hdsl2ShdslSpanConfEntry 1 }

   hdsl2ShdslSpanConfProfile OBJECT-TYPE
      SYNTAX      SnmpAdminString (SIZE(1..32))
      MAX-ACCESS  read-write
      STATUS      current
      DESCRIPTION
        "This object is a pointer to a span configuration profile in 
        the hdsl2ShdslSpanConfProfileTable, which applies to this span.
        The value of this object is the index of the referenced profile
        in the hdsl2ShdslSpanConfProfileTable.  Note that span 
        configuration profiles are only applicable to SHDSL lines.  
        HDSL2 lines MUST reference the default profile, 'DEFVAL'.
        By default, this object will have the value 'DEFVAL' (the index 
        of the default profile).

        Any attempt to set this object to a value that is not the value
        of the index for an active entry in the profile table,
        hdsl2ShdslSpanConfProfileTable, MUST be rejected."
      ::= { hdsl2ShdslSpanConfEntry 2 }

   hdsl2ShdslSpanConfAlarmProfile OBJECT-TYPE
      SYNTAX      SnmpAdminString (SIZE(1..32))
      MAX-ACCESS  read-write
      STATUS      current
      DESCRIPTION
        "This object is a pointer to an Alarm configuration profile in
        the hdsl2ShdslEndpointAlarmConfProfileTable.  The value of this
        object is the index of the referenced profile in the
        hdsl2ShdslEndpointAlarmConfProfileTable.  The alarm threshold 
        configuration in the referenced profile will be used by default 
        for all segment endpoints in this span.  Individual endpoints 
        may override this profile by explicitly specifying some other 
        profile in the hdsl2ShdslEndpointConfTable.  By default, this 
        object will have the value 'DEFVAL' (the index of the default 
        profile).

        Any attempt to set this object to a value that is not the value
        of the index for an active entry in the profile table,
        hdsl2ShdslEndpointAlarmConfProfileTable, MUST be rejected."
      ::= { hdsl2ShdslSpanConfEntry 3 }

   -- Span Status Group
   -- 

   hdsl2ShdslSpanStatusTable OBJECT-TYPE
      SYNTAX     SEQUENCE OF Hdsl2ShdslSpanStatusEntry
      MAX-ACCESS not-accessible
      STATUS     current
      DESCRIPTION
        "This table provides overall status information of 
         HDSL2/SHDSL spans.  This table contains live data from
         equipment.  As such, it is NOT persistent."
      ::= { hdsl2ShdslMibObjects 2 }

   hdsl2ShdslSpanStatusEntry OBJECT-TYPE
      SYNTAX      Hdsl2ShdslSpanStatusEntry
      MAX-ACCESS  not-accessible
      STATUS      current
      DESCRIPTION
        "An entry in the hdsl2ShdslSpanStatusTable.  Each entry 
         represents the complete span in a single HDSL2/SHDSL line.  
         It is indexed by the ifIndex of the associated HDSL2/SHDSL
         line."
      INDEX { ifIndex }
      ::= { hdsl2ShdslSpanStatusTable 1 }

   Hdsl2ShdslSpanStatusEntry ::=
      SEQUENCE
      {
--      hdsl2ShdslStatusNumAvailRepeaters        INTEGER,
      hdsl2ShdslStatusMaxAttainableLineRate    INTEGER,
      hdsl2ShdslStatusActualLineRate           INTEGER,
      hdsl2ShdslStatusTransmissionModeCurrent     
                Hdsl2ShdslTransmissionModeType
      }

--   hdsl2ShdslStatusNumAvailRepeaters OBJECT-TYPE
--      SYNTAX      INTEGER(0..8)
--      MAX-ACCESS  read-only
--      STATUS      current
--      DESCRIPTION
--        "Contains the actual number of repeaters/regenerators 
--         discovered in this HDSL2/SHDSL span."
--      ::= { hdsl2ShdslSpanStatusEntry 1 }

   hdsl2ShdslStatusMaxAttainableLineRate OBJECT-TYPE
      SYNTAX      INTEGER(0..4112000)
      UNITS       "bps"
      MAX-ACCESS  read-only
      STATUS      current
      DESCRIPTION
        "Contains the maximum attainable line rate in this HDSL2/SHDSL 
         span.  This object provides the maximum rate the line is
         capable of achieving.  This is based upon measurements made
         during line probing."
      ::= { hdsl2ShdslSpanStatusEntry 2 }

   hdsl2ShdslStatusActualLineRate OBJECT-TYPE
      SYNTAX      INTEGER(0..4112000)
      UNITS       "bps"
      MAX-ACCESS  read-only
      STATUS      current
      DESCRIPTION
        "Contains the actual line rate in this HDSL2/SHDSL span.  This
        should equal ifSpeed."
      ::= { hdsl2ShdslSpanStatusEntry 3 }

   hdsl2ShdslStatusTransmissionModeCurrent OBJECT-TYPE
      SYNTAX      Hdsl2ShdslTransmissionModeType
      MAX-ACCESS  read-only
      STATUS      current
      DESCRIPTION
        "Contains the current Power Spectral Density (PSD) regional 
         setting of the HDSL2/SHDSL span."
      ::= { hdsl2ShdslSpanStatusEntry 4 }


   -- Unit Inventory Group
   --

   hdsl2ShdslInventoryTable OBJECT-TYPE
      SYNTAX     SEQUENCE OF Hdsl2ShdslInventoryEntry
      MAX-ACCESS not-accessible
      STATUS     current
      DESCRIPTION
        "This table supports retrieval of unit inventory information
         available via the EOC from units in a HDSL2/SHDSL line.  
         
         Entries in this table are dynamically created during the
         line discovery process.  The life cycle for these entries
         is as follows:

            - xtu discovers a device, either a far-end xtu or an xru
            - an inventory table entry is created for the device
            - the line goes down for whatever reason
            - inventory table entries for unreachable devices are
              destroyed.

         As these entries are created/destroyed dynamically, they 
         are NOT persistent."
      ::= { hdsl2ShdslMibObjects 3 }

   hdsl2ShdslInventoryEntry OBJECT-TYPE
      SYNTAX      Hdsl2ShdslInventoryEntry
      MAX-ACCESS  not-accessible
      STATUS      current
      DESCRIPTION
        "An entry in the hdsl2ShdslInventoryTable.  Each entry 
         represents inventory information for a single unit in a 
         HDSL2/SHDSL line.  It is indexed by the ifIndex of the 
         HDSL2/SHDSL line and the Hdsl2ShdslUnitId of the 
         associated unit."
      INDEX { ifIndex, hdsl2ShdslInvIndex }
      ::= { hdsl2ShdslInventoryTable 1 }

   Hdsl2ShdslInventoryEntry ::=
      SEQUENCE
      {
      hdsl2ShdslInvIndex                      Hdsl2ShdslUnitId,
      hdsl2ShdslInvVendorID                   OCTET STRING,
      hdsl2ShdslInvVendorModelNumber          OCTET STRING,
      hdsl2ShdslInvVendorSerialNumber         OCTET STRING,
      hdsl2ShdslInvVendorEOCSoftwareVersion   Integer32,
      hdsl2ShdslInvStandardVersion            Integer32,
      hdsl2ShdslInvVendorListNumber           OCTET STRING,
      hdsl2ShdslInvVendorIssueNumber          OCTET STRING,
      hdsl2ShdslInvVendorSoftwareVersion      OCTET STRING,
      hdsl2ShdslInvEquipmentCode              OCTET STRING,
      hdsl2ShdslInvVendorOther                OCTET STRING,
      hdsl2ShdslInvTransmissionModeCapability  
                            Hdsl2ShdslTransmissionModeType
      }

   hdsl2ShdslInvIndex OBJECT-TYPE
      SYNTAX      Hdsl2ShdslUnitId
      MAX-ACCESS  read-only
      STATUS      current
      DESCRIPTION
         "Each entry in this table corresponds to a physical element
         in a HDSL2/SHDSL Span.  It is based on the EOC unit addressing
         scheme with reference to the xtuC."
      ::= { hdsl2ShdslInventoryEntry 1 }

   hdsl2ShdslInvVendorID OBJECT-TYPE
      SYNTAX      OCTET STRING(SIZE(8))
      MAX-ACCESS  read-only
      STATUS      current
      DESCRIPTION
        "Vendor ID as reported in an Inventory Response message."
      ::= { hdsl2ShdslInventoryEntry 2 }

   hdsl2ShdslInvVendorModelNumber OBJECT-TYPE
      SYNTAX      OCTET STRING(SIZE(12))
      MAX-ACCESS  read-only
      STATUS      current
      DESCRIPTION
        "Vendor model number as reported in an Inventory Response 
         message."
      ::= { hdsl2ShdslInventoryEntry 3 }

   hdsl2ShdslInvVendorSerialNumber OBJECT-TYPE
      SYNTAX      OCTET STRING(SIZE(12))
      MAX-ACCESS  read-only
      STATUS      current
      DESCRIPTION
        "Vendor serial number as reported in an Inventory Response 
         message."
      ::= { hdsl2ShdslInventoryEntry 4 }

   hdsl2ShdslInvVendorEOCSoftwareVersion OBJECT-TYPE
      SYNTAX      Integer32
      MAX-ACCESS  read-only
      STATUS      current
      DESCRIPTION
        "Vendor EOC version as reported in a Discovery Response 
         message."
      ::= { hdsl2ShdslInventoryEntry 5 }

   hdsl2ShdslInvStandardVersion OBJECT-TYPE
      SYNTAX      Integer32
      MAX-ACCESS  read-only
      STATUS      current
      DESCRIPTION
        "Version of the HDSL2/SHDSL standard implemented, as reported
         in an Inventory Response message."
      ::= { hdsl2ShdslInventoryEntry 6 }

   hdsl2ShdslInvVendorListNumber OBJECT-TYPE
      SYNTAX      OCTET STRING(SIZE(3))
      MAX-ACCESS  read-only
      STATUS      current
      DESCRIPTION
        "Vendor list number as reported in an Inventory Response 
         message."
      ::= { hdsl2ShdslInventoryEntry 7 }

   hdsl2ShdslInvVendorIssueNumber OBJECT-TYPE
      SYNTAX      OCTET STRING(SIZE(2))
      MAX-ACCESS  read-only
      STATUS      current
      DESCRIPTION
        "Vendor issue number as reported in an Inventory Response 
         message."
      ::= { hdsl2ShdslInventoryEntry 8 }

   hdsl2ShdslInvVendorSoftwareVersion OBJECT-TYPE
      SYNTAX      OCTET STRING(SIZE(6))
      MAX-ACCESS  read-only
      STATUS      current
      DESCRIPTION
        "Vendor software version as reported in an Inventory Response 
         message."
      ::= { hdsl2ShdslInventoryEntry 9 }

   hdsl2ShdslInvEquipmentCode OBJECT-TYPE
      SYNTAX      OCTET STRING(SIZE(10))
      MAX-ACCESS  read-only
      STATUS      current
      DESCRIPTION
        "Equipment code conforming to ANSI T1.213, Coded Identification
         of Equipment Entities."
      ::= { hdsl2ShdslInventoryEntry 10 }

   hdsl2ShdslInvVendorOther OBJECT-TYPE
      SYNTAX      OCTET STRING(SIZE(12))
      MAX-ACCESS  read-only
      STATUS      current
      DESCRIPTION
        "Other vendor information as reported in an Inventory Response 
         message."
      ::= { hdsl2ShdslInventoryEntry 11 }



   hdsl2ShdslInvTransmissionModeCapability OBJECT-TYPE
      SYNTAX      Hdsl2ShdslTransmissionModeType
      MAX-ACCESS  read-only
      STATUS      current
      DESCRIPTION
        "Contains the transmission mode capability of the SHDSL unit."
      ::= { hdsl2ShdslInventoryEntry 12 }

   -- Segment Endpoint Configuration Group
   --

   hdsl2ShdslEndpointConfTable OBJECT-TYPE
      SYNTAX      SEQUENCE OF Hdsl2ShdslEndpointConfEntry
      MAX-ACCESS  not-accessible
      STATUS      current
      DESCRIPTION
        "This table supports configuration parameters for segment 
         endpoints in a HDSL2/SHDSL line.  As this table is indexed
         by ifIndex, it MUST be maintained in a persistent manner."
      ::= { hdsl2ShdslMibObjects 4 }

   hdsl2ShdslEndpointConfEntry OBJECT-TYPE
      SYNTAX      Hdsl2ShdslEndpointConfEntry
      MAX-ACCESS  not-accessible
      STATUS      current
      DESCRIPTION
        "An entry in the hdsl2ShdslEndpointConfTable.  Each entry
         represents a single segment endpoint in a HDSL2/SHDSL line.
         It is indexed by the ifIndex of the HDSL2/SHDSL line, the
         UnitId of the associated unit, the side of the unit, and the
         wire-pair of the associated modem."  
      INDEX { ifIndex, hdsl2ShdslInvIndex}
--      INDEX { ifIndex, hdsl2ShdslInvIndex, hdsl2ShdslEndpointSide, 
--              hdsl2ShdslEndpointWirePair}
      ::= { hdsl2ShdslEndpointConfTable 1 }

   Hdsl2ShdslEndpointConfEntry ::=
      SEQUENCE
      {
--      hdsl2ShdslEndpointSide                   Hdsl2ShdslUnitSide,
--      hdsl2ShdslEndpointWirePair               Hdsl2ShdslWirePair,
      hdsl2ShdslEndpointAlarmConfProfile       SnmpAdminString
      }

--   hdsl2ShdslEndpointSide OBJECT-TYPE
--      SYNTAX      Hdsl2ShdslUnitSide
--      MAX-ACCESS  read-only
--      STATUS      current
--      DESCRIPTION
--        "The side of the unit associated with this segment endpoint -
--         Network/Customer side - as per the Hdsl2ShdslUnitSide textual
--         convention."
--      ::= { hdsl2ShdslEndpointConfEntry 1 }



--   hdsl2ShdslEndpointWirePair OBJECT-TYPE
--      SYNTAX      Hdsl2ShdslWirePair
--      MAX-ACCESS  read-only
--      STATUS      current
--      DESCRIPTION
--        "The wire-pair of the modem associated with this segment 
--         endpoint as per the Hdsl2ShdslWirePair textual convention."
--      ::= { hdsl2ShdslEndpointConfEntry 2 }

   hdsl2ShdslEndpointAlarmConfProfile OBJECT-TYPE
      SYNTAX      SnmpAdminString (SIZE(0..32))
      MAX-ACCESS  read-write
      STATUS      current
      DESCRIPTION
        "This object configures the alarm threshold values to be used
         for this segment endpoint.  The values are obtained from the 
         alarm configuration profile referenced by this object.  The 
         value of this object is the index of the referenced profile in 
         the hdsl2ShdslEndpointAlarmConfProfileTable, or NULL (a zero-
         length SnmpAdminString).  If the value is a zero-length 
         SnmpAdminString, the endpoint uses the default Alarm 
         Configuration Profile for the associated span as per the 
         hdsl2ShdslSpanConfAlarmProfile object in the 
         hdsl2ShdslSpanConfTable.  The default value of this object is 
         a zero-length SnmpAdminString.

         Any attempt to set this object to a value that is not the value
         of the index for an active entry in the profile table,
         hdsl2ShdslEndpointAlarmConfProfileTable, MUST be rejected."
      ::= { hdsl2ShdslEndpointConfEntry 3 }

   -- Segment Endpoint Current Status/Performance Group
   --

   hdsl2ShdslEndpointCurrTable OBJECT-TYPE
      SYNTAX      SEQUENCE OF Hdsl2ShdslEndpointCurrEntry
      MAX-ACCESS  not-accessible
      STATUS      current
      DESCRIPTION
        "This table contains current status and performance information
         for segment endpoints in HDSL2/SHDSL Lines.  As with other 
         tables in this MIB indexed by ifIndex, entries in this table 
         MUST be maintained in a persistent manner."
      ::= { hdsl2ShdslMibObjects 5 }

   hdsl2ShdslEndpointCurrEntry OBJECT-TYPE
      SYNTAX      Hdsl2ShdslEndpointCurrEntry
      MAX-ACCESS  not-accessible
      STATUS      current
      DESCRIPTION
        "An entry in the hdsl2ShdslEndpointCurrTable.  Each entry 
        contains status and performance information relating to a 
        single segment endpoint.  It is indexed by the ifIndex of the
        HDSL2/SHDSL line, the UnitId of the associated unit, the side
        of the unit, and the wire-pair of the associated modem."
      INDEX { ifIndex, hdsl2ShdslInvIndex}        
--      INDEX { ifIndex, hdsl2ShdslInvIndex, hdsl2ShdslEndpointSide, 
--              hdsl2ShdslEndpointWirePair }
      ::= { hdsl2ShdslEndpointCurrTable 1 }

   Hdsl2ShdslEndpointCurrEntry ::=
      SEQUENCE
      {
      hdsl2ShdslEndpointCurrAtn                INTEGER,
      hdsl2ShdslEndpointCurrSnrMgn             INTEGER,
      hdsl2ShdslEndpointCurrStatus             BITS,
      hdsl2ShdslEndpointES                     Counter32,
      hdsl2ShdslEndpointSES                    Counter32,
      hdsl2ShdslEndpointCRCanomalies           Counter32,
      hdsl2ShdslEndpointLOSWS                  Counter32,
      hdsl2ShdslEndpointUAS                    Counter32,
      hdsl2ShdslEndpointCurr15MinTimeElapsed   
                                Hdsl2ShdslPerfTimeElapsed,
      hdsl2ShdslEndpointCurr15MinES            PerfCurrentCount,
      hdsl2ShdslEndpointCurr15MinSES           PerfCurrentCount,
      hdsl2ShdslEndpointCurr15MinCRCanomalies  PerfCurrentCount,
      hdsl2ShdslEndpointCurr15MinLOSWS         PerfCurrentCount,
      hdsl2ShdslEndpointCurr15MinUAS           PerfCurrentCount,
      hdsl2ShdslEndpointCurr1DayTimeElapsed   
                                Hdsl2ShdslPerfTimeElapsed
--      hdsl2ShdslEndpointCurr1DayES            
--                                Hdsl2ShdslPerfCurrDayCount,
--      hdsl2ShdslEndpointCurr1DaySES            
--                                Hdsl2ShdslPerfCurrDayCount,
--      hdsl2ShdslEndpointCurr1DayCRCanomalies   
--                                Hdsl2ShdslPerfCurrDayCount,
--      hdsl2ShdslEndpointCurr1DayLOSWS          
--                                Hdsl2ShdslPerfCurrDayCount,
--      hdsl2ShdslEndpointCurr1DayUAS            
--                                Hdsl2ShdslPerfCurrDayCount
      }

   hdsl2ShdslEndpointCurrAtn OBJECT-TYPE
      SYNTAX      INTEGER(-127..128)
      UNITS       "dB"
      MAX-ACCESS  read-only
      STATUS      current
      DESCRIPTION
        "The current loop attenuation for this endpoint as reported in
         a Network or Customer Side Performance Status message."
      REFERENCE   "HDSL2 Section 7.5.3.7; SHDSL Section 9.5.5.7"
      ::= { hdsl2ShdslEndpointCurrEntry 1 }

   hdsl2ShdslEndpointCurrSnrMgn OBJECT-TYPE



      SYNTAX      INTEGER(-127..128)
      UNITS       "dB"
      MAX-ACCESS  read-only
      STATUS      current
      DESCRIPTION
        "The current SNR margin for this endpoint as reported in a 
         Status Response/SNR message."
      REFERENCE   "HDSL2 Section 7.5.3.7; SHDSL Section 9.5.5.7"
      ::= { hdsl2ShdslEndpointCurrEntry 2 }

   hdsl2ShdslEndpointCurrStatus OBJECT-TYPE
      SYNTAX      BITS
                  {
                  noDefect(0),
                  powerBackoff(1),
                  deviceFault(2),
                  dcContinuityFault(3),
                  snrMarginAlarm(4),
                  loopAttenuationAlarm(5),
                  loswFailureAlarm(6),
                  configInitFailure(7),
                  protocolInitFailure(8),
                  noNeighborPresent(9),
                  loopbackActive(10)
                  }
      MAX-ACCESS  read-only
      STATUS      current
      DESCRIPTION
        "Contains the current state of the endpoint.  This is a
        bitmap of possible conditions. The various bit positions
        are:

        noDefect               There no defects on the line.
        
        powerBackoff           Indicates enhanced Power Backoff.

        deviceFault            Indicates a vendor-dependent
                               diagnostic or self-test fault
                               has been detected.

        dcContinuityFault      Indicates vendor-dependent
                               conditions that interfere with
                               span powering such as short and
                               open circuits.

        snrMarginAlarm         Indicates that the SNR margin
                               has dropped below the alarm threshold.

        loopAttenuationAlarm   Indicates that the loop attenuation
                               exceeds the alarm threshold.

        loswFailureAlarm       Indicates a forward LOSW alarm.



        configInitFailure      Endpoint failure during initialization
                               due to paired endpoint not able to
                               support requested configuration.

        protocolInitFailure    Endpoint failure during initialization
                               due to incompatible protocol used by
                               the paired endpoint.

        noNeighborPresent      Endpoint failure during initialization
                               due to no activation sequence detected
                               from paired endpoint.

        loopbackActive         A loopback is currently active at this
                               Segment Endpoint.

        This is intended to supplement ifOperStatus.  Note that there 
        is a 1-1 relationship between the status bits defined in this
        object and the notification thresholds defined elsewhere in 
        this MIB."
      REFERENCE   "HDSL2 Section 7.5.3.7; SHDSL Section 9.5.5.7"
      ::= { hdsl2ShdslEndpointCurrEntry 3 }

   hdsl2ShdslEndpointES OBJECT-TYPE
      SYNTAX      Counter32
      UNITS       "seconds"
      MAX-ACCESS  read-only
      STATUS      current
      DESCRIPTION
        "Count of Errored Seconds (ES) on this endpoint since the xU 
         was last restarted."
      REFERENCE   "HDSL2 Section 7.5.3.7; SHDSL Section 9.5.5.7"
      ::= { hdsl2ShdslEndpointCurrEntry 4 }

   hdsl2ShdslEndpointSES OBJECT-TYPE
      SYNTAX       Counter32
      UNITS        "seconds"
      MAX-ACCESS   read-only
      STATUS       current
      DESCRIPTION
        "Count of Severely Errored Seconds (SES) on this endpoint 
         since the xU was last restarted."
      REFERENCE   "HDSL2 Section 7.5.3.7; SHDSL Section 9.5.5.7"
      ::= { hdsl2ShdslEndpointCurrEntry 5 }

   hdsl2ShdslEndpointCRCanomalies OBJECT-TYPE
      SYNTAX       Counter32
      UNITS        "detected CRC Anomalies"
      MAX-ACCESS   read-only
      STATUS       current
      DESCRIPTION
        "Count of CRC anomalies on this endpoint since the xU was
         last restarted."
      REFERENCE   "HDSL2 Section 7.5.3.7; SHDSL Section 9.5.5.7"
      ::= { hdsl2ShdslEndpointCurrEntry 6 }

   hdsl2ShdslEndpointLOSWS OBJECT-TYPE
      SYNTAX       Counter32
      UNITS        "seconds"
      MAX-ACCESS   read-only
      STATUS       current
      DESCRIPTION
        "Count of Loss of Sync Word (LOSW) Seconds on this endpoint
         since the xU was last restarted."
      REFERENCE   "HDSL2 Section 7.5.3.7; SHDSL Section 9.5.5.7"
      ::= { hdsl2ShdslEndpointCurrEntry 7 }

   hdsl2ShdslEndpointUAS OBJECT-TYPE
      SYNTAX       Counter32
      UNITS        "seconds"
      MAX-ACCESS   read-only
      STATUS       current
      DESCRIPTION
        "Count of Unavailable Seconds (UAS) on this endpoint since
         the xU was last restarted."
      REFERENCE   "HDSL2 Section 7.5.3.7; SHDSL Section 9.5.5.7"
      ::= { hdsl2ShdslEndpointCurrEntry 8 }

   hdsl2ShdslEndpointCurr15MinTimeElapsed OBJECT-TYPE
      SYNTAX       Hdsl2ShdslPerfTimeElapsed
      UNITS        "seconds"
      MAX-ACCESS   read-only
      STATUS       current
      DESCRIPTION
        "Total elapsed seconds in the current 15-minute interval."
      ::= { hdsl2ShdslEndpointCurrEntry 9 }

   hdsl2ShdslEndpointCurr15MinES OBJECT-TYPE
      SYNTAX       PerfCurrentCount
      UNITS        "seconds"
      MAX-ACCESS   read-only
      STATUS       current
      DESCRIPTION
        "Count of Errored Seconds (ES) in the current 15-minute 
         interval."
      REFERENCE   "HDSL2 Section 7.5.3.7; SHDSL Section 9.5.5.7"
      ::= { hdsl2ShdslEndpointCurrEntry 10 }

   hdsl2ShdslEndpointCurr15MinSES OBJECT-TYPE
      SYNTAX       PerfCurrentCount
      UNITS        "seconds"
      MAX-ACCESS   read-only
      STATUS       current
      DESCRIPTION
        "Count of Severely Errored Seconds (SES) in the current 
         15-minute interval."
      REFERENCE   "HDSL2 Section 7.5.3.7; SHDSL Section 9.5.5.7"
      ::= { hdsl2ShdslEndpointCurrEntry 11 }

   hdsl2ShdslEndpointCurr15MinCRCanomalies OBJECT-TYPE
      SYNTAX       PerfCurrentCount
      UNITS        "detected CRC Anomalies"
      MAX-ACCESS   read-only
      STATUS       current
      DESCRIPTION
        "Count of CRC anomalies in the current 15-minute interval."
      REFERENCE   "HDSL2 Section 7.5.3.7; SHDSL Section 9.5.5.7"
      ::= { hdsl2ShdslEndpointCurrEntry 12 }

   hdsl2ShdslEndpointCurr15MinLOSWS OBJECT-TYPE
      SYNTAX       PerfCurrentCount
      UNITS        "seconds"
      MAX-ACCESS   read-only
      STATUS       current
      DESCRIPTION
        "Count of Loss of Sync Word (LOSW) Seconds in the current 
         15-minute interval."
      REFERENCE   "HDSL2 Section 7.5.3.7; SHDSL Section 9.5.5.7"
      ::= { hdsl2ShdslEndpointCurrEntry 13 }

   hdsl2ShdslEndpointCurr15MinUAS OBJECT-TYPE
      SYNTAX       PerfCurrentCount
      UNITS        "seconds"
      MAX-ACCESS   read-only
      STATUS       current
      DESCRIPTION
        "Count of Unavailable Seconds (UAS) in the current 15-minute 
         interval."
      REFERENCE   "HDSL2 Section 7.5.3.7; SHDSL Section 9.5.5.7"
      ::= { hdsl2ShdslEndpointCurrEntry 14 }

   hdsl2ShdslEndpointCurr1DayTimeElapsed OBJECT-TYPE
      SYNTAX       Hdsl2ShdslPerfTimeElapsed
      UNITS        "seconds"
      MAX-ACCESS   read-only
      STATUS       current
      DESCRIPTION
        "Number of seconds that have elapsed since the beginning of 
         the current 1-day interval."
      ::= { hdsl2ShdslEndpointCurrEntry 15 }

--   hdsl2ShdslEndpointCurr1DayES OBJECT-TYPE
--      SYNTAX       Hdsl2ShdslPerfCurrDayCount
--      UNITS        "seconds"
--      MAX-ACCESS   read-only
--      STATUS       current
--
--      DESCRIPTION
--        "Count of Errored Seconds (ES) during the current day as 
--         measured by hdsl2ShdslEndpointCurr1DayTimeElapsed."
--      REFERENCE   "HDSL2 Section 7.5.3.7; SHDSL Section 9.5.5.7"
--      ::= { hdsl2ShdslEndpointCurrEntry 16 }
--
--   hdsl2ShdslEndpointCurr1DaySES OBJECT-TYPE
--      SYNTAX       Hdsl2ShdslPerfCurrDayCount
--      UNITS        "seconds"
--      MAX-ACCESS   read-only
--      STATUS       current
--      DESCRIPTION
--        "Count of Severely Errored Seconds (SES) during the current 
--         day as measured by hdsl2ShdslEndpointCurr1DayTimeElapsed."
--      REFERENCE   "HDSL2 Section 7.5.3.7; SHDSL Section 9.5.5.7"
--      ::= { hdsl2ShdslEndpointCurrEntry 17 }
--
--   hdsl2ShdslEndpointCurr1DayCRCanomalies OBJECT-TYPE
--      SYNTAX       Hdsl2ShdslPerfCurrDayCount
--      UNITS        "detected CRC Anomalies"
--      MAX-ACCESS   read-only
--      STATUS       current
--      DESCRIPTION
--        "Count of CRC anomalies during the current day as measured 
--         by hdsl2ShdslEndpointCurr1DayTimeElapsed."
--      REFERENCE   "HDSL2 Section 7.5.3.7; SHDSL Section 9.5.5.7"
--      ::= { hdsl2ShdslEndpointCurrEntry 18 }
--
--   hdsl2ShdslEndpointCurr1DayLOSWS OBJECT-TYPE
--      SYNTAX       Hdsl2ShdslPerfCurrDayCount
--      UNITS        "seconds"
--      MAX-ACCESS   read-only
--      STATUS       current
--      DESCRIPTION
--        "Count of Loss of Sync Word (LOSW) Seconds during the current
--         day as measured by hdsl2ShdslEndpointCurr1DayTimeElapsed."
--      REFERENCE   "HDSL2 Section 7.5.3.7; SHDSL Section 9.5.5.7"
--      ::= { hdsl2ShdslEndpointCurrEntry 19 }
--
--   hdsl2ShdslEndpointCurr1DayUAS OBJECT-TYPE
--      SYNTAX       Hdsl2ShdslPerfCurrDayCount
--      UNITS        "seconds"
--      MAX-ACCESS   read-only
--      STATUS       current
--      DESCRIPTION
--        "Count of Unavailable Seconds (UAS) during the current day as
--         measured by hdsl2ShdslEndpointCurr1DayTimeElapsed."
--      REFERENCE   "HDSL2 Section 7.5.3.7; SHDSL Section 9.5.5.7"      ::= { hdsl2ShdslEndpointCurrEntry 20 }

   -- Segment Endpoint 15-Minute Interval Status/Performance Group
   --



--   hdsl2Shdsl15MinIntervalTable OBJECT-TYPE
--      SYNTAX      SEQUENCE OF Hdsl2Shdsl15MinIntervalEntry
--      MAX-ACCESS  not-accessible
--      STATUS      current
--      DESCRIPTION
--        "This table provides one row for each HDSL2/SHDSL endpoint
--         performance data collection interval.  This table contains 
--         live data from equipment.  As such, it is NOT persistent."
--      ::= { hdsl2ShdslMibObjects 6 }
--
--   hdsl2Shdsl15MinIntervalEntry OBJECT-TYPE
--      SYNTAX      Hdsl2Shdsl15MinIntervalEntry
--      MAX-ACCESS  not-accessible
--      STATUS      current
--      DESCRIPTION
--        "An entry in the hdsl2Shdsl15MinIntervalTable."
--      INDEX { ifIndex, hdsl2ShdslInvIndex, hdsl2ShdslEndpointSide}        
--      INDEX { ifIndex, hdsl2ShdslInvIndex, hdsl2ShdslEndpointSide,
--              hdsl2ShdslEndpointWirePair, hdsl2Shdsl15MinIntervalNumber}
--      ::= { hdsl2Shdsl15MinIntervalTable 1 }
--
--   Hdsl2Shdsl15MinIntervalEntry ::=
--      SEQUENCE
--      {
--      hdsl2Shdsl15MinIntervalNumber         INTEGER,
--      hdsl2Shdsl15MinIntervalES             PerfIntervalCount,
--      hdsl2Shdsl15MinIntervalSES            PerfIntervalCount,
--      hdsl2Shdsl15MinIntervalCRCanomalies   PerfIntervalCount,
--      hdsl2Shdsl15MinIntervalLOSWS          PerfIntervalCount,
--      hdsl2Shdsl15MinIntervalUAS            PerfIntervalCount
--      }
--
--   hdsl2Shdsl15MinIntervalNumber OBJECT-TYPE
--      SYNTAX      INTEGER(1..96)
--      MAX-ACCESS  not-accessible
--      STATUS      current
--      DESCRIPTION
--        "Performance Data Interval number. 1 is the the most recent 
--         previous interval; interval 96 is 24 hours ago. Intervals 
--         2..96 are optional."
--      ::= { hdsl2Shdsl15MinIntervalEntry 1 }
--
--   hdsl2Shdsl15MinIntervalES OBJECT-TYPE
--      SYNTAX      PerfIntervalCount
--      UNITS       "seconds"
--      MAX-ACCESS  read-only
--      STATUS      current
--      DESCRIPTION
--        "Count of Errored Seconds (ES) during the interval."
--      REFERENCE   "HDSL2 Section 7.5.3.7; SHDSL Section 9.5.5.7"
--      ::= { hdsl2Shdsl15MinIntervalEntry 2 }
--
--
--
--
--   hdsl2Shdsl15MinIntervalSES OBJECT-TYPE
--      SYNTAX      PerfIntervalCount
--      UNITS       "seconds"
--      MAX-ACCESS  read-only
--      STATUS      current
--      DESCRIPTION
--        "Count of Severely Errored Seconds (SES) during the interval."
--      REFERENCE   "HDSL2 Section 7.5.3.7; SHDSL Section 9.5.5.7"
--      ::= { hdsl2Shdsl15MinIntervalEntry 3 }
--
--   hdsl2Shdsl15MinIntervalCRCanomalies OBJECT-TYPE
--      SYNTAX      PerfIntervalCount
--      UNITS       "detected CRC Anomalies"
--      MAX-ACCESS  read-only
--      STATUS      current
--      DESCRIPTION
--        "Count of CRC anomalies during the interval."
--      REFERENCE   "HDSL2 Section 7.5.3.7; SHDSL Section 9.5.5.7"
--      ::= { hdsl2Shdsl15MinIntervalEntry 4 }
--
--   hdsl2Shdsl15MinIntervalLOSWS OBJECT-TYPE
--      SYNTAX      PerfIntervalCount
--      UNITS       "seconds"
--      MAX-ACCESS  read-only
--      STATUS      current
--      DESCRIPTION
--        "Count of Loss of Sync Word (LOSW) Seconds during the 
--         interval."
--      REFERENCE   "HDSL2 Section 7.5.3.7; SHDSL Section 9.5.5.7"
--      ::= { hdsl2Shdsl15MinIntervalEntry 5 }
--
--   hdsl2Shdsl15MinIntervalUAS OBJECT-TYPE
--      SYNTAX      PerfIntervalCount
--      UNITS       "seconds"
--      MAX-ACCESS  read-only
--      STATUS      current
--      DESCRIPTION
--        "Count of Unavailable Seconds (UAS) during the interval."
--      REFERENCE   "HDSL2 Section 7.5.3.7; SHDSL Section 9.5.5.7"
--      ::= { hdsl2Shdsl15MinIntervalEntry 6 }
--
--   -- Segment Endpoint 1-Day Interval Status/Performance Group
--   --
--
--   hdsl2Shdsl1DayIntervalTable OBJECT-TYPE
--      SYNTAX      SEQUENCE OF Hdsl2Shdsl1DayIntervalEntry
--      MAX-ACCESS  not-accessible
--      STATUS      current
--      DESCRIPTION
--        "This table provides one row for each HDSL2/SHDSL endpoint
--         performance data collection interval.  This table contains 
--         live data from equipment.  As such, it is NOT persistent."
--      ::= { hdsl2ShdslMibObjects 7 }
--
--   hdsl2Shdsl1DayIntervalEntry OBJECT-TYPE
--      SYNTAX      Hdsl2Shdsl1DayIntervalEntry
--      MAX-ACCESS  not-accessible
--      STATUS      current
--      DESCRIPTION
--        "An entry in the hdsl2Shdsl1DayIntervalTable."
--      INDEX { ifIndex, hdsl2ShdslInvIndex, hdsl2ShdslEndpointSide}        
--      INDEX { ifIndex, hdsl2ShdslInvIndex, hdsl2ShdslEndpointSide,
--              hdsl2ShdslEndpointWirePair, hdsl2Shdsl1DayIntervalNumber }
--      ::= { hdsl2Shdsl1DayIntervalTable 1 }
--
--   Hdsl2Shdsl1DayIntervalEntry ::=
--      SEQUENCE
--      {
--      hdsl2Shdsl1DayIntervalNumber         INTEGER,
--      hdsl2Shdsl1DayIntervalMoniSecs       Hdsl2ShdslPerfTimeElapsed,
--      hdsl2Shdsl1DayIntervalES             Hdsl2Shdsl1DayIntervalCount,
--      hdsl2Shdsl1DayIntervalSES            Hdsl2Shdsl1DayIntervalCount,
--      hdsl2Shdsl1DayIntervalCRCanomalies   Hdsl2Shdsl1DayIntervalCount,
--      hdsl2Shdsl1DayIntervalLOSWS          Hdsl2Shdsl1DayIntervalCount,
--      hdsl2Shdsl1DayIntervalUAS            Hdsl2Shdsl1DayIntervalCount
--      }
--
--   hdsl2Shdsl1DayIntervalNumber OBJECT-TYPE
--      SYNTAX      INTEGER(1..30)
--      MAX-ACCESS  not-accessible
--      STATUS      current
--      DESCRIPTION
--        "History Data Interval number. Interval 1 is the the most 
--         recent previous day; interval 30 is 30 days ago. Intervals 
--         2..30 are optional."
--      ::= { hdsl2Shdsl1DayIntervalEntry 1 }
--
--   hdsl2Shdsl1DayIntervalMoniSecs OBJECT-TYPE
--      SYNTAX       Hdsl2ShdslPerfTimeElapsed
--      UNITS        "seconds"
--      MAX-ACCESS   read-only
--      STATUS       current
--      DESCRIPTION
--        "The amount of time in the 1-day interval over which the 
--         performance monitoring information is actually counted.  
--         This value will be the same as the interval duration except 
--         in a situation where performance monitoring data could not 
--         be collected for any reason."
--      ::= { hdsl2Shdsl1DayIntervalEntry 2 }
--
--   hdsl2Shdsl1DayIntervalES OBJECT-TYPE
--      SYNTAX       Hdsl2Shdsl1DayIntervalCount
--      UNITS        "seconds"
--      MAX-ACCESS   read-only
--      STATUS       current
--
--      DESCRIPTION
--        "Count of Errored Seconds (ES) during the 1-day interval as 
--         measured by hdsl2Shdsl1DayIntervalMoniSecs."
--      REFERENCE   "HDSL2 Section 7.5.3.7; SHDSL Section 9.5.5.7"
--      ::= { hdsl2Shdsl1DayIntervalEntry 3 }
--
--   hdsl2Shdsl1DayIntervalSES OBJECT-TYPE
--      SYNTAX       Hdsl2Shdsl1DayIntervalCount
--      UNITS        "seconds"
--      MAX-ACCESS   read-only
--      STATUS       current
--      DESCRIPTION
--        "Count of Severely Errored Seconds (SES) during the 1-day
--         interval as measured by hdsl2Shdsl1DayIntervalMoniSecs."
--      REFERENCE   "HDSL2 Section 7.5.3.7; SHDSL Section 9.5.5.7"
--      ::= { hdsl2Shdsl1DayIntervalEntry 4 }
--
--   hdsl2Shdsl1DayIntervalCRCanomalies OBJECT-TYPE
--      SYNTAX       Hdsl2Shdsl1DayIntervalCount
--      UNITS        "detected CRC Anomalies"
--      MAX-ACCESS   read-only
--      STATUS       current
--      DESCRIPTION
--        "Count of CRC anomalies during the 1-day interval as
--         measured by hdsl2Shdsl1DayIntervalMoniSecs."
--      REFERENCE   "HDSL2 Section 7.5.3.7; SHDSL Section 9.5.5.7"
--      ::= { hdsl2Shdsl1DayIntervalEntry 5 }
--
--   hdsl2Shdsl1DayIntervalLOSWS OBJECT-TYPE
--      SYNTAX       Hdsl2Shdsl1DayIntervalCount
--      UNITS        "seconds"
--      MAX-ACCESS   read-only
--      STATUS       current
--      DESCRIPTION
--        "Count of Loss of Sync Word (LOSW) Seconds during the 1-day 
--         interval as measured by hdsl2Shdsl1DayIntervalMoniSecs."
--      REFERENCE   "HDSL2 Section 7.5.3.7; SHDSL Section 9.5.5.7"
--      ::= { hdsl2Shdsl1DayIntervalEntry 6 }
--
--   hdsl2Shdsl1DayIntervalUAS OBJECT-TYPE
--      SYNTAX       Hdsl2Shdsl1DayIntervalCount
--      UNITS        "seconds"
--      MAX-ACCESS   read-only
--      STATUS       current
--      DESCRIPTION
--        "Count of Unavailable Seconds (UAS) during the 1-day interval
--         as measured by hdsl2Shdsl1DayIntervalMoniSecs."
--      REFERENCE   "HDSL2 Section 7.5.3.7; SHDSL Section 9.5.5.7"
--      ::= { hdsl2Shdsl1DayIntervalEntry 7 }

   -- Maintenance Group
   --



--   hdsl2ShdslEndpointMaintTable OBJECT-TYPE
--      SYNTAX      SEQUENCE OF Hdsl2ShdslEndpointMaintEntry
--      MAX-ACCESS  not-accessible
--      STATUS      current
--      DESCRIPTION
--        "This table supports maintenance operations (eg. loopbacks)
--         to be performed on HDSL2/SHDSL segment endpoints.  This table
--         contains live data from equipment.  As such, it is NOT 
--         persistent."
--      ::= { hdsl2ShdslMibObjects 8 }

--   hdsl2ShdslEndpointMaintEntry OBJECT-TYPE
--      SYNTAX      Hdsl2ShdslEndpointMaintEntry
--      MAX-ACCESS  not-accessible
--      STATUS      current
--      DESCRIPTION
--        "An entry in the hdsl2ShdslEndpointMaintTable.  Each entry
--         corresponds to a single segment endpoint, and is indexed by the
--         ifIndex of the HDSL2/SHDSL line, the UnitId of the associated
--         unit and the side of the unit."
--      INDEX { ifIndex, hdsl2ShdslInvIndex, hdsl2ShdslEndpointSide }
--      ::= { hdsl2ShdslEndpointMaintTable 1 }
--
--   Hdsl2ShdslEndpointMaintEntry ::=
--      SEQUENCE
--      {
--      hdsl2ShdslMaintLoopbackConfig      INTEGER,
--      hdsl2ShdslMaintTipRingReversal     INTEGER,
--      hdsl2ShdslMaintPowerBackOff        INTEGER,
--      hdsl2ShdslMaintSoftRestart         INTEGER
--      }
--
--   hdsl2ShdslMaintLoopbackConfig OBJECT-TYPE
--      SYNTAX      INTEGER
--                  {
--                  noLoopback(1),
--                  normalLoopback(2),
--                  specialLoopback(3)
--                  }
--      MAX-ACCESS  read-write
--      STATUS      current
--      DESCRIPTION
--        "This object controls configuration of loopbacks for the
--         associated segment endpoint.  The status of the loopback
--         is obtained via the hdsl2ShdslEndpointCurrStatus object."
--      ::= { hdsl2ShdslEndpointMaintEntry 1 }
--
--   hdsl2ShdslMaintTipRingReversal OBJECT-TYPE
--      SYNTAX      INTEGER
--                  {
--                  normal(1),
--                  reversed(2)
--                  }
--      MAX-ACCESS  read-only
--      STATUS      current
--      DESCRIPTION
--        "This object indicates the state of the tip/ring pair at the 
--         associated segment endpoint."
--      ::= { hdsl2ShdslEndpointMaintEntry 2 }
--
--   hdsl2ShdslMaintPowerBackOff OBJECT-TYPE
--      SYNTAX      INTEGER
--                  {
--                  default(1),
--                  enhanced(2)
--                  }
--      MAX-ACCESS  read-write
--      STATUS      current
--      DESCRIPTION
--        "This object configures the receiver at the associated
--         segment endpoint to operate in default or enhanced power
--         backoff mode."
--      ::= { hdsl2ShdslEndpointMaintEntry 3 }
--
--   hdsl2ShdslMaintSoftRestart OBJECT-TYPE
--      SYNTAX      INTEGER
--                  {
--                  ready(1),
--                  restart(2)
--                  }
--      MAX-ACCESS  read-write
--      STATUS      current
--      DESCRIPTION
--        "This object enables the manager to trigger a soft restart
--         of the modem at the associated segment endpoint.  The manager
--         may only set this object to the 'restart(2)' value, which
--         initiates a restart.  The agent will perform a restart after 
--         approximately 5 seconds.  Following the 5 second period, the
--         agent will restore the object to the 'ready(1)' state."
--      ::= { hdsl2ShdslEndpointMaintEntry 4 }
--
--   hdsl2ShdslUnitMaintTable OBJECT-TYPE
--      SYNTAX      SEQUENCE OF Hdsl2ShdslUnitMaintEntry
--      MAX-ACCESS  not-accessible
--      STATUS      current
--      DESCRIPTION
--        "This table supports maintenance operations for units in a
--         HDSL2/SHDSL line.  Entries in this table MUST be maintained
--         in a persistent manner."
--      ::= { hdsl2ShdslMibObjects 9 }

--   hdsl2ShdslUnitMaintEntry OBJECT-TYPE
--      SYNTAX      Hdsl2ShdslUnitMaintEntry
--      MAX-ACCESS  not-accessible
--      STATUS      current
--      DESCRIPTION
--        "An entry in the hdsl2ShdslUnitMaintTable.  Each entry
--         corresponds to a single unit, and is indexed by the ifIndex
--         of the HDSL2/SHDSL line and the UnitId of the associated 
--         unit."
--      INDEX { ifIndex, hdsl2ShdslInvIndex  }
--      ::= { hdsl2ShdslUnitMaintTable 1 }
--
--   Hdsl2ShdslUnitMaintEntry ::=
--      SEQUENCE
--      {
--      hdsl2ShdslMaintLoopbackTimeout     Integer32,
--      hdsl2ShdslMaintUnitPowerSource     INTEGER
--      }
--
--   hdsl2ShdslMaintLoopbackTimeout OBJECT-TYPE
--      SYNTAX      Integer32(0..4095)
--      UNITS       "minutes"
--      MAX-ACCESS  read-write
--      STATUS      current
--      DESCRIPTION
--        "This object configures the timeout value for loopbacks
--         initiated at segments endpoints contained in the associated
--         unit.  A value of 0 disables the timeout."
--      ::= { hdsl2ShdslUnitMaintEntry 1 }
--
--   hdsl2ShdslMaintUnitPowerSource OBJECT-TYPE
--      SYNTAX      INTEGER
--                  {
--                  local(1),
--                  span(2)
--                  }
--      MAX-ACCESS  read-only
--      STATUS      current
--      DESCRIPTION
--        "This object indicates the DC power source being used by the
--         associated unit."
--      ::= { hdsl2ShdslUnitMaintEntry 2 }

   -- Span Configuration Profile Group
   --

   hdsl2ShdslSpanConfProfileTable OBJECT-TYPE
      SYNTAX      SEQUENCE OF Hdsl2ShdslSpanConfProfileEntry
      MAX-ACCESS  not-accessible
      STATUS      current
      DESCRIPTION
        "This table supports definitions of span configuration
         profiles for SHDSL lines.  HDSL2 does not support these 
         configuration options.  This table MUST be maintained
         in a persistent manner."
      ::= { hdsl2ShdslMibObjects 10 }

   hdsl2ShdslSpanConfProfileEntry OBJECT-TYPE
      SYNTAX      Hdsl2ShdslSpanConfProfileEntry
      MAX-ACCESS  not-accessible
      STATUS      current
      DESCRIPTION
        "Each entry corresponds to a single span configuration
         profile.  Each profile contains a set of span configuration
         parameters.  The configuration parameters in a profile are
         applied to those lines referencing that profile (see the 
         hdsl2ShdslSpanConfProfile object).  Profiles may be 
         created/deleted using the row creation/deletion mechanism 
         via hdsl2ShdslSpanConfProfileRowStatus.  If an active
         entry is referenced in hdsl2ShdslSpanConfProfile, the 
         entry MUST remain active until all references are removed."
      INDEX { IMPLIED hdsl2ShdslSpanConfProfileName }
      ::= { hdsl2ShdslSpanConfProfileTable 1 }

   Hdsl2ShdslSpanConfProfileEntry ::=
      SEQUENCE
      {
      hdsl2ShdslSpanConfProfileName               SnmpAdminString,
--      hdsl2ShdslSpanConfWireInterface             INTEGER,
      hdsl2ShdslSpanConfMinLineRate               INTEGER,
      hdsl2ShdslSpanConfMaxLineRate               INTEGER,
--      hdsl2ShdslSpanConfPSD                       INTEGER,
      hdsl2ShdslSpanConfTransmissionMode          
                                      Hdsl2ShdslTransmissionModeType,
--      hdsl2ShdslSpanConfRemoteEnabled             INTEGER,
      hdsl2ShdslSpanConfPowerFeeding              INTEGER,
--      hdsl2ShdslSpanConfCurrCondTargetMarginDown  INTEGER,
--      hdsl2ShdslSpanConfWorstCaseTargetMarginDown INTEGER,
--      hdsl2ShdslSpanConfCurrCondTargetMarginUp    INTEGER
--      hdsl2ShdslSpanConfWorstCaseTargetMarginUp   INTEGER,
--      hdsl2ShdslSpanConfUsedTargetMargins         BITS,
--      hdsl2ShdslSpanConfReferenceClock 
--                                      Hdsl2ShdslClockReferenceType,
--      hdsl2ShdslSpanConfLineProbeEnable           INTEGER,
      hdsl2ShdslSpanConfProfileRowStatus          RowStatus
      }

   hdsl2ShdslSpanConfProfileName OBJECT-TYPE
      SYNTAX      SnmpAdminString (SIZE(1..32))
      MAX-ACCESS  not-accessible
      STATUS      current
      DESCRIPTION
        "This object is the unique index associated with this profile.
         Entries in this table are referenced via the object
         hdsl2ShdslSpanConfProfile in Hdsl2ShdslSpanConfEntry."
      ::= { hdsl2ShdslSpanConfProfileEntry 1 }



--   hdsl2ShdslSpanConfWireInterface OBJECT-TYPE
--      SYNTAX      INTEGER
--                  {
--                  twoWire(1),
--                  fourWire(2)
--                  }
--      MAX-ACCESS  read-create
--      STATUS      current
--      DESCRIPTION
--        "This object configures the two-wire or optional four-wire
--         operation for SHDSL Lines."
--      DEFVAL      { twoWire }
--      ::= { hdsl2ShdslSpanConfProfileEntry 2 }

   hdsl2ShdslSpanConfMinLineRate OBJECT-TYPE
      SYNTAX      INTEGER(0..4112000)
      UNITS       "bps"
      MAX-ACCESS  read-create
      STATUS      current
      DESCRIPTION
        "This object configures the minimum transmission rate for 
         the associated SHDSL Line in bits-per-second (bps).  If
         the minimum line rate equals the maximum line rate
         (hdsl2ShdslSpanMaxLineRate), the line rate is considered 
         'fixed'.  If the minimum line rate is less than the maximum 
         line rate, the line rate is considered 'rate-adaptive'."
      DEFVAL      { 1552000 }
      ::= { hdsl2ShdslSpanConfProfileEntry 3 }

   hdsl2ShdslSpanConfMaxLineRate OBJECT-TYPE
      SYNTAX      INTEGER(0..4112000)
      UNITS       "bps"
      MAX-ACCESS  read-create
      STATUS      current
      DESCRIPTION
        "This object configures the maximum transmission rate for 
         the associated SHDSL Line in bits-per-second (bps).  If
         the minimum line rate equals the maximum line rate
         (hdsl2ShdslSpanMaxLineRate), the line rate is considered 
         'fixed'.  If the minimum line rate is less than the maximum 
         line rate, the line rate is considered 'rate-adaptive'."
      DEFVAL      { 1552000 }
      ::= { hdsl2ShdslSpanConfProfileEntry 4 }

--   hdsl2ShdslSpanConfPSD OBJECT-TYPE
--      SYNTAX      INTEGER
--                  {
--                  symmetric(1),
--                  asymmetric(2)
--                  }
--      MAX-ACCESS  read-create
--      STATUS      current
--      DESCRIPTION
--        "This object configures use of symmetric/asymmetric PSD (Power
--         Spectral Density) Mask for the associated SHDSL Line.  Support
--         for symmetric PSD is mandatory for all supported data rates.
--         Support for asymmetric PSD is optional."
--      DEFVAL      { symmetric }
--      ::= { hdsl2ShdslSpanConfProfileEntry 5 }

   hdsl2ShdslSpanConfTransmissionMode OBJECT-TYPE
      SYNTAX      Hdsl2ShdslTransmissionModeType
      MAX-ACCESS  read-create
      STATUS      current
      DESCRIPTION
        "This object specifies the regional setting for the SHDSL
         line."
      DEFVAL      { { region1 } }
      ::= { hdsl2ShdslSpanConfProfileEntry 6 }

--   hdsl2ShdslSpanConfRemoteEnabled OBJECT-TYPE
--      SYNTAX      INTEGER
--                  {
--                  enabled(1),
--                  disabled(2)
--                  }
--      MAX-ACCESS  read-create
--      STATUS      current
--      DESCRIPTION
--        "This object enables/disables support for remote management
--         of the units in a SHDSL line from the STU-R via the EOC."
--      DEFVAL      { enabled }
--      ::= { hdsl2ShdslSpanConfProfileEntry 7 }

   hdsl2ShdslSpanConfPowerFeeding OBJECT-TYPE
      SYNTAX      INTEGER
                  {
                  noPower(1),
                  powerFeed(2),
                  wettingCurrent(3)
                  }
      MAX-ACCESS  read-create
      STATUS      current
      DESCRIPTION
        "This object enables/disables support for optional power
         feeding in a SHDSL line."
      DEFVAL      { noPower }
      ::= { hdsl2ShdslSpanConfProfileEntry 8 } 

--   hdsl2ShdslSpanConfCurrCondTargetMarginDown OBJECT-TYPE
--      SYNTAX      INTEGER(-10..21)
--      UNITS       "dB"
--      MAX-ACCESS  read-create
--      STATUS      current
--      DESCRIPTION
--        "This object specifies the downstream current condition target
--         SNR margin for a SHDSL line.  The SNR margin is the difference
--         between the desired SNR and the actual SNR.  Target SNR margin
--         is the desired SNR margin for a unit."
--      DEFVAL      { 0 }
--      ::= { hdsl2ShdslSpanConfProfileEntry 9 } 

--   hdsl2ShdslSpanConfWorstCaseTargetMarginDown OBJECT-TYPE
--      SYNTAX      INTEGER(-10..21)
--      UNITS       "dB"
--      MAX-ACCESS  read-create
--      STATUS      current
--      DESCRIPTION
--        "This object specifies the downstream worst case target SNR 
--         margin for a SHDSL line.  The SNR margin is the difference 
--         between the desired SNR and the actual SNR.  Target SNR 
--         margin is the desired SNR margin for a unit."
--      DEFVAL      { 0 }
--      ::= { hdsl2ShdslSpanConfProfileEntry 10 } 

--   hdsl2ShdslSpanConfCurrCondTargetMarginUp OBJECT-TYPE
--      SYNTAX      INTEGER(-10..21)
--      UNITS       "dB"
--      MAX-ACCESS  read-create
--      STATUS      current
--      DESCRIPTION
--        "This object specifies the upstream current condition target 
--         SNR margin for a SHDSL line.  The SNR margin is the difference
--         between the desired SNR and the actual SNR.  Target SNR margin
--         is the desired SNR margin for a unit."
--      DEFVAL      { 0 }
--      ::= { hdsl2ShdslSpanConfProfileEntry 11 } 

--   hdsl2ShdslSpanConfWorstCaseTargetMarginUp OBJECT-TYPE
--      SYNTAX      INTEGER(-10..21)
--      UNITS       "dB"
--      MAX-ACCESS  read-create
--      STATUS      current
--      DESCRIPTION
--        "This object specifies the upstream worst case target SNR
--         margin for a SHDSL line.  The SNR margin is the difference 
--         between the desired SNR and the actual SNR.  Target SNR margin
--         is the desired SNR margin for a unit."
--      DEFVAL      { 0 }
--      ::= { hdsl2ShdslSpanConfProfileEntry 12 } 

--   hdsl2ShdslSpanConfUsedTargetMargins OBJECT-TYPE
--      SYNTAX      BITS
--                  {    
--                  currCondDown(0),
--                  worstCaseDown(1),
--                  currCondUp(2),
--                  worstCaseUp(3)
--                  }
--      MAX-ACCESS  read-create
--      STATUS      current
--      DESCRIPTION
--        "Contains indicates whether a target SNR margin is enabled or 
--         disabled.  This is a bit-map of possible settings.  The 
--         various bit positions are:
--
--         currCondDown     current condition downstream target SNR  
--                          margin enabled
--
--         worstCaseDown    worst case downstream target SNR margin 
--                          enabled
--
--         currCondUp       current condition upstream target SNR 
--                          margin enabled
--
--         worstCaseUp      worst case upstream target SNR margin 
--                          enabled."
--      DEFVAL      { { currCondDown } }
--      ::= { hdsl2ShdslSpanConfProfileEntry 13 } 
--
--   hdsl2ShdslSpanConfReferenceClock OBJECT-TYPE
--      SYNTAX      Hdsl2ShdslClockReferenceType
--      MAX-ACCESS  read-create
--      STATUS      current
--      DESCRIPTION
--        "This object configures the clock reference for the STU-C 
--        in a SHDSL Line."
--      DEFVAL      { localClk }
--      ::= { hdsl2ShdslSpanConfProfileEntry 14 }
--
--   hdsl2ShdslSpanConfLineProbeEnable OBJECT-TYPE
--      SYNTAX      INTEGER
--                  {
--                  disable(1),
--                  enable(2)
--                  }
--      MAX-ACCESS  read-create
--      STATUS      current
--      DESCRIPTION
--        "This object enables/disables support for Line Probe of
--        the units in a SHDSL line.  When Line Probe is enabled, the 
--        system performs Line Probing to find the best possible
--        rate.  If Line probe is disabled, the rate adaptation phase 
--        is skipped to shorten set up time."
--      DEFVAL      { disable }
--      ::= { hdsl2ShdslSpanConfProfileEntry 15 }




   hdsl2ShdslSpanConfProfileRowStatus OBJECT-TYPE
      SYNTAX      RowStatus
      MAX-ACCESS  read-create
      STATUS      current
      DESCRIPTION
        "This object controls creation/deletion of the associated
         entry in this table per the semantics of RowStatus.  If an 
         active entry is referenced in hdsl2ShdslSpanConfProfile, the 
         entry MUST remain active until all references are removed."
      ::= { hdsl2ShdslSpanConfProfileEntry 16 }

   -- Segment Endpoint Alarm Configuration Profile group
   --

   hdsl2ShdslEndpointAlarmConfProfileTable OBJECT-TYPE
      SYNTAX      SEQUENCE OF Hdsl2ShdslEndpointAlarmConfProfileEntry
      MAX-ACCESS  not-accessible
      STATUS      current
      DESCRIPTION
        "This table supports definitions of alarm configuration
         profiles for HDSL2/SHDSL segment endpoints.  This table
         MUST be maintained in a persistent manner."
      ::= { hdsl2ShdslMibObjects 11 }

   hdsl2ShdslEndpointAlarmConfProfileEntry OBJECT-TYPE
      SYNTAX      Hdsl2ShdslEndpointAlarmConfProfileEntry
      MAX-ACCESS  not-accessible
      STATUS      current
      DESCRIPTION
        "Each entry corresponds to a single alarm configuration profile.
         Each profile contains a set of parameters for setting alarm 
         thresholds for various performance attributes monitored at 
         HDSL2/SHDSL segment endpoints.  Profiles may be created/deleted
         using the row creation/deletion mechanism via 
         hdsl2ShdslEndpointAlarmConfProfileRowStatus.  If an active
         entry is referenced in either hdsl2ShdslSpanConfAlarmProfile 
         or hdsl2ShdslEndpointAlarmConfProfile, the entry MUST remain
         active until all references are removed."
      INDEX { IMPLIED hdsl2ShdslEndpointAlarmConfProfileName }
      ::= { hdsl2ShdslEndpointAlarmConfProfileTable 1 }

   Hdsl2ShdslEndpointAlarmConfProfileEntry ::=
      SEQUENCE
      {
      hdsl2ShdslEndpointAlarmConfProfileName       SnmpAdminString,
      hdsl2ShdslEndpointThreshLoopAttenuation      INTEGER,
      hdsl2ShdslEndpointThreshSNRMargin            INTEGER,
      hdsl2ShdslEndpointThreshES                   
                  Hdsl2ShdslPerfIntervalThreshold,
      hdsl2ShdslEndpointThreshSES                  
                  Hdsl2ShdslPerfIntervalThreshold,
      hdsl2ShdslEndpointThreshCRCanomalies         Integer32,

      hdsl2ShdslEndpointThreshLOSWS                
                  Hdsl2ShdslPerfIntervalThreshold,
      hdsl2ShdslEndpointThreshUAS                  
                  Hdsl2ShdslPerfIntervalThreshold,
      hdsl2ShdslEndpointAlarmConfProfileRowStatus  RowStatus
      }

   hdsl2ShdslEndpointAlarmConfProfileName OBJECT-TYPE
      SYNTAX      SnmpAdminString (SIZE(1..32))
      MAX-ACCESS  not-accessible
      STATUS      current
      DESCRIPTION
        "This object is the unique index associated with this profile."
      ::= { hdsl2ShdslEndpointAlarmConfProfileEntry 1 }

   hdsl2ShdslEndpointThreshLoopAttenuation OBJECT-TYPE
      SYNTAX      INTEGER(-127..128)
      UNITS       "dB"
      MAX-ACCESS  read-create
      STATUS      current
      DESCRIPTION
        "This object configures the loop attenuation alarm threshold.
         When the current value of hdsl2ShdslEndpointCurrAtn reaches 
         or exceeds this threshold, a hdsl2ShdslLoopAttenCrossing 
         MAY be generated."
      DEFVAL      { 0 }
      ::= { hdsl2ShdslEndpointAlarmConfProfileEntry 2 }

   hdsl2ShdslEndpointThreshSNRMargin OBJECT-TYPE
      SYNTAX      INTEGER(-127..128)
      UNITS       "dB"
      MAX-ACCESS  read-create
      STATUS      current
      DESCRIPTION
        "This object configures the SNR margin alarm threshold.
         When the current value of hdsl2ShdslEndpointCurrSnrMgn 
         reaches or drops below this threshold, a 
         hdsl2ShdslSNRMarginCrossing MAY be generated."
      DEFVAL      { 0 }
      ::= { hdsl2ShdslEndpointAlarmConfProfileEntry 3 }

   hdsl2ShdslEndpointThreshES OBJECT-TYPE
      SYNTAX      Hdsl2ShdslPerfIntervalThreshold
      UNITS       "seconds"
      MAX-ACCESS  read-create
      STATUS      current
      DESCRIPTION
        "This object configures the threshold for the number of
         errored seconds (ES) within any given 15-minute performance
         data collection interval.  If the value of errored seconds 
         in a particular 15-minute collection interval reaches/
         exceeds this value, a hdsl2ShdslPerfESThresh MAY be 
         generated.  At most one notification will be sent per 
         interval per endpoint."
      DEFVAL      { 0 }
      ::= { hdsl2ShdslEndpointAlarmConfProfileEntry 4 }

   hdsl2ShdslEndpointThreshSES OBJECT-TYPE
      SYNTAX      Hdsl2ShdslPerfIntervalThreshold 
      UNITS       "seconds"
      MAX-ACCESS  read-create
      STATUS      current
      DESCRIPTION
        "This object configures the threshold for the number of
         severely errored seconds (SES) within any given 15-minute
         performance data collection interval.  If the value of 
         severely errored seconds in a particular 15-minute collection
         interval reaches/exceeds this value, a hdsl2ShdslPerfSESThresh
         MAY be generated.  At most one notification will be sent per 
         interval per endpoint."
      DEFVAL      { 0 }
      ::= { hdsl2ShdslEndpointAlarmConfProfileEntry 5 }

   hdsl2ShdslEndpointThreshCRCanomalies OBJECT-TYPE
      SYNTAX      Integer32
      UNITS       "detected CRC Anomalies"
      MAX-ACCESS  read-create
      STATUS      current
      DESCRIPTION
        "This object configures the threshold for the number of
         CRC anomalies within any given 15-minute performance data
         collection interval.  If the value of CRC anomalies in a 
         particular 15-minute collection interval reaches/exceeds 
         this value, a hdsl2ShdslPerfCRCanomaliesThresh MAY be 
         generated.  At most one notification will be sent per 
         interval per endpoint."
      DEFVAL      { 0 }
      ::= { hdsl2ShdslEndpointAlarmConfProfileEntry 6 }

   hdsl2ShdslEndpointThreshLOSWS OBJECT-TYPE
      SYNTAX      Hdsl2ShdslPerfIntervalThreshold 
      UNITS       "seconds"
      MAX-ACCESS  read-create
      STATUS      current
      DESCRIPTION
        "This object configures the threshold for the number of
         Loss of Sync Word (LOSW) Seconds within any given 15-minute
         performance data collection interval.  If the value of LOSW
         in a particular 15-minute collection interval reaches/exceeds
         this value, a hdsl2ShdslPerfLOSWSThresh MAY be generated.
         At most one notification will be sent per interval per 
         endpoint."
      DEFVAL      { 0 }
      ::= { hdsl2ShdslEndpointAlarmConfProfileEntry 7 }




   hdsl2ShdslEndpointThreshUAS OBJECT-TYPE
      SYNTAX      Hdsl2ShdslPerfIntervalThreshold 
      UNITS       "seconds"
      MAX-ACCESS  read-create
      STATUS      current
      DESCRIPTION
        "This object configures the threshold for the number of
         unavailable seconds (UAS) within any given 15-minute
         performance data collection interval.  If the value of UAS
         in a particular 15-minute collection interval reaches/exceeds 
         this value, a hdsl2ShdslPerfUASThresh MAY be generated.
         At most one notification will be sent per interval per 
         endpoint."
      DEFVAL      { 0 }
      ::= { hdsl2ShdslEndpointAlarmConfProfileEntry 8 }

   hdsl2ShdslEndpointAlarmConfProfileRowStatus OBJECT-TYPE
      SYNTAX      RowStatus
      MAX-ACCESS  read-create
      STATUS      current
      DESCRIPTION
        "This object controls creation/deletion of the associated
         entry in this table as per the semantics of RowStatus.
         If an active entry is referenced in either 
         hdsl2ShdslSpanConfAlarmProfile or 
         hdsl2ShdslEndpointAlarmConfProfile, the entry MUST remain
         active until all references are removed."
      ::= { hdsl2ShdslEndpointAlarmConfProfileEntry 9 }

   -- Notifications Group
   --

   hdsl2ShdslNotifications OBJECT IDENTIFIER ::= { hdsl2ShdslMIB 0 }

   hdsl2ShdslLoopAttenCrossing NOTIFICATION-TYPE
      OBJECTS
      {
      hdsl2ShdslEndpointCurrAtn,
      hdsl2ShdslEndpointThreshLoopAttenuation
      }
      STATUS     current
      DESCRIPTION
        "This notification indicates that the loop attenuation 
         threshold (as per the hdsl2ShdslEndpointThreshLoopAttenuation
         value) has been reached/exceeded for the HDSL2/SHDSL segment
         endpoint."
      ::= { hdsl2ShdslNotifications 1 }

   hdsl2ShdslSNRMarginCrossing NOTIFICATION-TYPE
      OBJECTS
      {
      hdsl2ShdslEndpointCurrSnrMgn,
      hdsl2ShdslEndpointThreshSNRMargin
      }
      STATUS     current
      DESCRIPTION
        "This notification indicates that the SNR margin threshold (as
         per the hdsl2ShdslEndpointThreshSNRMargin value) has been 
         reached/exceeded for the HDSL2/SHDSL segment endpoint."
      ::= { hdsl2ShdslNotifications 2 }

   hdsl2ShdslPerfESThresh NOTIFICATION-TYPE
      OBJECTS
      {
      hdsl2ShdslEndpointCurr15MinES,
      hdsl2ShdslEndpointThreshES
      }
      STATUS     current
      DESCRIPTION
        "This notification indicates that the errored seconds threshold
         (as per the hdsl2ShdslEndpointThreshES value) has been reached/
         exceeded for the HDSL2/SHDSL segment endpoint." 
      ::= { hdsl2ShdslNotifications 3 }

   hdsl2ShdslPerfSESThresh NOTIFICATION-TYPE
      OBJECTS
      {
      hdsl2ShdslEndpointCurr15MinSES,
      hdsl2ShdslEndpointThreshSES
      }
      STATUS     current
      DESCRIPTION
        "This notification indicates that the severely errored seconds 
         threshold (as per the hdsl2ShdslEndpointThreshSES value) has 
         been reached/exceeded for the HDSL2/SHDSL Segment Endpoint."
      ::= { hdsl2ShdslNotifications 4 }

   hdsl2ShdslPerfCRCanomaliesThresh NOTIFICATION-TYPE
      OBJECTS
      {
      hdsl2ShdslEndpointCurr15MinCRCanomalies,
      hdsl2ShdslEndpointThreshCRCanomalies
      }
      STATUS    current
      DESCRIPTION
        "This notification indicates that the CRC anomalies threshold 
         (as per the hdsl2ShdslEndpointThreshCRCanomalies value) has 
         been reached/exceeded for the HDSL2/SHDSL Segment Endpoint."
      ::= { hdsl2ShdslNotifications 5 }

   hdsl2ShdslPerfLOSWSThresh NOTIFICATION-TYPE
      OBJECTS
      {
      hdsl2ShdslEndpointCurr15MinLOSWS,
      hdsl2ShdslEndpointThreshLOSWS
      }
      STATUS     current
      DESCRIPTION
        "This notification indicates that the LOSW seconds threshold
         (as per the hdsl2ShdslEndpointThreshLOSWS value) has been 
         reached/exceeded for the HDSL2/SHDSL segment endpoint."
      ::= { hdsl2ShdslNotifications 6 }

   hdsl2ShdslPerfUASThresh NOTIFICATION-TYPE
      OBJECTS
      {
      hdsl2ShdslEndpointCurr15MinUAS,
      hdsl2ShdslEndpointThreshUAS
      }
      STATUS     current
      DESCRIPTION
        "This notification indicates that the unavailable seconds 
         threshold (as per the hdsl2ShdslEndpointThreshUAS value) has 
         been reached/exceeded for the HDSL2/SHDSL segment endpoint."
      ::= { hdsl2ShdslNotifications 7 }

--   hdsl2ShdslSpanInvalidNumRepeaters NOTIFICATION-TYPE
--      OBJECTS
--      {
--      hdsl2ShdslSpanConfNumRepeaters              
--      }
--      STATUS     current
--      DESCRIPTION
--        "This notification indicates that a mismatch has been detected
--         between the number of repeater/regenerator units configured
--         for a HDSL2/SHDSL line via the hdsl2ShdslSpanConfNumRepeaters
--         object and the actual number of repeater/regenerator units
--         discovered via the EOC."
--      ::= { hdsl2ShdslNotifications 8 }

--   hdsl2ShdslLoopbackFailure NOTIFICATION-TYPE
--      OBJECTS                              
--      {                                    
--      hdsl2ShdslMaintLoopbackConfig        
--      }                                    
--      STATUS     current                   
--      DESCRIPTION                          
--        "This notification indicates that an endpoint maintenance
--         loopback command failed for an HDSL2/SHDSL segment."
--      ::= { hdsl2ShdslNotifications 9 }    

--   hdsl2ShdslpowerBackoff NOTIFICATION-TYPE
--      OBJECTS
--      {
--      hdsl2ShdslEndpointCurrStatus
--
--      }
--      STATUS    current
--      DESCRIPTION
--        "This notification indicates that the bit setting for 
--         powerBackoff in the hdsl2ShdslEndpointCurrStatus object for 
--         this endpoint has changed."
--      ::= { hdsl2ShdslNotifications 10 }

--   hdsl2ShdsldeviceFault NOTIFICATION-TYPE
--      OBJECTS
--      {
--      hdsl2ShdslEndpointCurrStatus
--      }
--      STATUS    current
--      DESCRIPTION
--        "This notification indicates that the bit setting for 
--         deviceFault in the hdsl2ShdslEndpointCurrStatus object for 
--         this endpoint has changed."
--      ::= { hdsl2ShdslNotifications 11 }

--   hdsl2ShdsldcContinuityFault NOTIFICATION-TYPE
--      OBJECTS
--      {
--      hdsl2ShdslEndpointCurrStatus
--      }
--      STATUS    current
--      DESCRIPTION
--        "This notification indicates that the bit setting for 
--         dcContinuityFault in the hdsl2ShdslEndpointCurrStatus object 
--         for this endpoint has changed."
--      ::= { hdsl2ShdslNotifications 12 }

--   hdsl2ShdslconfigInitFailure NOTIFICATION-TYPE
--      OBJECTS
--      {
--      hdsl2ShdslEndpointCurrStatus
--      }
--      STATUS    current
--      DESCRIPTION
--        "This notification indicates that the bit setting for 
--         configInitFailure in the hdsl2ShdslEndpointCurrStatus object 
--         for this endpoint has changed."
--      ::= { hdsl2ShdslNotifications 13 }

--   hdsl2ShdslprotocolInitFailure NOTIFICATION-TYPE
--      OBJECTS
--      {
--      hdsl2ShdslEndpointCurrStatus
--      }
--      STATUS    current
--      DESCRIPTION
--        "This notification indicates that the bit setting for 
--         protocolInitFailure in the hdsl2ShdslEndpointCurrStatus
--         object for this endpoint has changed."
--      ::= { hdsl2ShdslNotifications 14 }
--
--   hdsl2ShdslnoNeighborPresent NOTIFICATION-TYPE
--      OBJECTS
--      {
--      hdsl2ShdslEndpointCurrStatus
--      }
--      STATUS    current
--      DESCRIPTION
--        "This notification indicates that the bit setting for 
--         noNeighborPresent in the hdsl2ShdslEndpointCurrStatus object 
--         for this endpoint has changed."
--      ::= { hdsl2ShdslNotifications 15 }
-- 
--   hdsl2ShdslLocalPowerLoss NOTIFICATION-TYPE
--      OBJECTS
--      {
--      ifIndex, 
--      hdsl2ShdslInvIndex
--      }
--      STATUS    current
--      DESCRIPTION
--        "This notification indicates impending unit failure due to
--         loss of local power (last gasp)."
--      ::= { hdsl2ShdslNotifications 16 }

   -- conformance information
   END



------------------------------------------------------------------------------
------------------------------------------------------------------------------
--
--  File         : lanSbridge.mib
--  Description  : ZTE lan MIB  
--
------------------------------------------------------------------------------
------------------------------------------------------------------------------

LANSBRIDGE-MIB DEFINITIONS ::= BEGIN

	IMPORTS
			MODULE-IDENTITY, OBJECT-TYPE,
--			enterprises					FROM SNMPv2-SMI
            zxLan                       FROM WRS-MASTER-MIB

			MODULE-COMPLIANCE, OBJECT-GROUP			FROM SNMPv2-CONF;

------------------------------------------------------------------------------
------------------------------------------------------------------------------

--    zte MODULE-IDENTITY
--        LAST-UPDATED    "0008290000Z"  -- August 29, 2000
--        ORGANIZATION    "Wind River Systems, Inc."
--        CONTACT-INFO    "Wind River Systems, Inc.
--                         E-mail: support@windriver.com"
--
--        DESCRIPTION     "WRS Master MIB OID defines and documentation."
--
--        REVISION        "0008290000Z"  -- August 29, 2000
--        DESCRIPTION     "Initial MIB creation."
--
--        ::= { enterprises 3902 }
    
-- DSL Products
--	zxDsl	OBJECT IDENTIFIER ::= { zte 1004 }
--	zxDslam OBJECT IDENTIFIER ::= { zxDsl 1 }
--	zxLan	OBJECT IDENTIFIER ::= { zxDslam 10 }
------------------------------------------------------------------------------
------------------------------------------------------------------------------

	lanSBridge	OBJECT IDENTIFIER ::= { zxLan 6 }
------------------------------------------------------------------------------
------------------------------------------------------------------------------

    sBridgeIgmpSnoopEnabled  OBJECT-TYPE
        SYNTAX TruthValue
        MAX-ACCESS read-write
        STATUS current
        DESCRIPTION
            "DURABLE: { false }
             Setting this object to true(1) enables IGMP Snooping.  Setting
             it to false(2) disables IGMP Snooping.
             
             Note that IGMP Snooping can function with or without GVRP and
             GMRP enabled."
        ::= { lanSBridge 1 }

    sBridgeIgmpSnoopAging  OBJECT-TYPE
        SYNTAX Integer32 (30..3600)
        MAX-ACCESS read-write
        STATUS current
        DESCRIPTION
            "DURABLE: { 300 }
             The timeout period in seconds for aging out Multicast Groups
             dynamically learned with IGMP Snooping.  Note that aging operates
             on a per interface per VLAN per multicast group basis."
        ::= { lanSBridge 2 }

-- END of LAN-MIB                
END


------------------------------------------------------------------------------
------------------------------------------------------------------------------
--
--  File         : IMAB.mib
--  Description  : ZTE IMAB MIB  
--
------------------------------------------------------------------------------
------------------------------------------------------------------------------
IMAB-GROUP-MIB DEFINITIONS ::= BEGIN

IMPORTS
           MODULE-IDENTITY, OBJECT-TYPE, Integer32, Counter32, Gauge32,
           NOTIFICATION-TYPE, enterprises
              FROM SNMPv2-SMI
           MODULE-COMPLIANCE, OBJECT-GROUP, NOTIFICATION-GROUP
              FROM SNMPv2-CONF
           TEXTUAL-CONVENTION, DateAndTime, RowStatus
              FROM SNMPv2-TC
           InterfaceIndex, InterfaceIndexOrZero, ifIndex
              FROM IF-MIB;
              
zxImabGroupMib MODULE-IDENTITY
           LAST-UPDATED "9902111830Z"
           ORGANIZATION "The ATM Forum"
           CONTACT-INFO
              "ATM Forum
              World Headquarters
              2570 West El Camino Real
              Suite 304
              Mountain View, CA 94040-1313
              USA
              Phone: +1 415 949 6700
              Fax: +1 415 949 6705
              email: info@ atmforum. com"
           DESCRIPTION
              "The MIB module for managing ATM Forum Inverse Multiplexing
              for ATM (IMA) interfaces."
           REVISION          "9902111830Z"
           DESCRIPTION
              "Updated and repaired version of the IMA-MIB released with the
              IMA v1.1 specification (af-phy-0086.001)."
           REVISION          "9701092245Z"
           DESCRIPTION
              "Initial incomplete version of the IMA-MIB as published in the
              IMA v1.0 specification (af-phy-0086.000)."
           ::= { zxIma 5 }

zte OBJECT IDENTIFIER ::= { enterprises 3902 }
zxDsl OBJECT IDENTIFIER ::= { zte 1004 }
zxDslam OBJECT IDENTIFIER ::= { zxDsl 1 }
zxIma	OBJECT IDENTIFIER ::= { zxDslam 11 }

zxImabGroupMibObjects OBJECT IDENTIFIER ::= { zxImabGroupMib 1 }

zxImabGroupMibConformance OBJECT IDENTIFIER ::= { zxImabGroupMib 2 }
zxImabGroupMibGroups OBJECT IDENTIFIER ::= { zxImabGroupMibConformance 1 }
zxImabGroupMibCompliances OBJECT IDENTIFIER ::= { zxImabGroupMibConformance 2 }


--Textual conventions

MilliSeconds ::= TEXTUAL-CONVENTION
           STATUS           current
           DESCRIPTION
              "Time in milliseconds"
           SYNTAX           Integer32

ImaGroupState ::= TEXTUAL-CONVENTION
           STATUS           current
           DESCRIPTION
              "State of the IMA group."
           REFERENCE
              "ATM Forum IMA v1.1, Section 10.2.1 on page 55"
           SYNTAX            INTEGER {
              notConfigured(1),
              startUp(2),
              startUpAck(3),
              configAbortUnsupportedM(4),
              configAbortIncompatibleSymmetry(5),
              configAbortOther(6),
              insufficientLinks(7),
              blocked(8),
              operational(9),
              configAbortUnsupportedImaVersion(10) }

ImaGroupFailureStatus ::= TEXTUAL-CONVENTION
           STATUS           current
           DESCRIPTION
              "Failure reason of an IMA group."
           REFERENCE
              "ATM Forum IMA v1.1, Section 10.2.1, page 55"
           SYNTAX            INTEGER {
              noFailure( 1), --unit is up
              startUpNe( 2),
              startUpFe( 3),
              invalidMValueNe( 4),
              invalidMValueFe( 5),
              failedAssymetricNe( 6),
              failedAssymetricFe( 7),
              insufficientLinksNe( 8),
              insufficientLinksFe( 9),
              blockedNe( 10),
              blockedFe( 11),
              otherFailure( 12),
              invalidImaVersionNe( 13),
              invalidImaVersionFe( 14) }

ImaGroupTxClkMode ::= TEXTUAL-CONVENTION
           STATUS           current
           DESCRIPTION
              "Indicate the transmit clock mode of the IMA group.
              There are two possible modes: the Common Transmit
              Clock (CTC) and the Independent Transmit Clock (ITC).
              The CTC mode corresponds to the case when the transmit clock
              of all IMA links are derived from the same source.    The ITC
              configuration corresponds to the case where there is at least
              one IMA link whose transmit clock is derived from a source
              different than at least another link transmit clock."
           REFERENCE
              "ATM Forum IMA v1.1, Section 7 on page 38"
           SYNTAX            INTEGER {
              ctc( 1),
              itc( 2) }

ImaGroupSymmetry ::= TEXTUAL-CONVENTION
           STATUS           current
           DESCRIPTION
              "The group symmetry mode adjusted during the group start-up."
           REFERENCE
              "ATM Forum IMA v1.1, Section 5.2.2.7 on page 35"
           SYNTAX            INTEGER {
              symmetricOperation( 1),
              asymmetricOperation( 2),
              asymmetricConfiguration( 3) }

ImaFrameLength ::= TEXTUAL-CONVENTION
           STATUS           current
           DESCRIPTION
              "Length of the IMA frames."
           REFERENCE
              "ATM Forum IMA v1.1, Section 5.2.2.4.2 on page 34"
           SYNTAX            INTEGER {
              m32( 32),
              m64( 64),
              m128( 128),
              m256( 256) }

ImaTestProcStatus ::= TEXTUAL-CONVENTION
           STATUS           current
           DESCRIPTION
              "States of the Test Pattern Procedure."
           REFERENCE
              "ATM Forum IMA v1.1, Section 13 on page 81"
           SYNTAX            INTEGER {
              disabled( 1),
              operating( 2),
              linkFail( 3) }

--
--The IMA Group subtree
--
--The IMA Group subtree consists of the number of IMA groups and a
--table of IMA groups.    Each entry in the table of IMA groups contains
--information (configuration and status) specific to each group.
--

imabGroupNumber OBJECT-TYPE
           SYNTAX            INTEGER (0.. 2147483647)
           MAX-ACCESS    read-only
           STATUS           current
           DESCRIPTION
              "The number of active IMA groups configured on this system."
           ::= { zxImabGroupMibObjects 1 }

imabGroupTable OBJECT-TYPE
           SYNTAX           SEQUENCE OF ImabGroupEntry
           MAX-ACCESS    not-accessible
           STATUS           current
           DESCRIPTION
              "The IMA Group Configuration table."
           ::= { zxImabGroupMibObjects 2 }

imabGroupEntry OBJECT-TYPE
           SYNTAX           ImabGroupEntry
           MAX-ACCESS    not-accessible
           STATUS           current
           DESCRIPTION
              "An entry in the IMA Group table."
           INDEX             { imabGroupIndex }
           ::= { imabGroupTable 1 }

ImabGroupEntry ::= SEQUENCE {
           imabGroupIndex                            INTEGER (1..2147483647),
           imabGroupRowStatus                     RowStatus,
--           imabGroupIfIndex                        InterfaceIndex,
--           imabGroupNeState                        ImaGroupState,
--           imabGroupFeState                        ImaGroupState,
--           imabGroupFailureStatus             ImaGroupFailureStatus,
           imabGroupSymmetry                      ImaGroupSymmetry,
           imabGroupMinNumTxLinks             INTEGER (1.. 32),
           imabGroupMinNumRxLinks             INTEGER (1.. 32),
           imabGroupNeTxClkMode                 ImaGroupTxClkMode,
--           imabGroupFeTxClkMode                 ImaGroupTxClkMode,
--           imabGroupTxTimingRefLink          InterfaceIndexOrZero,
--           imabGroupRxTimingRefLink          InterfaceIndexOrZero,
--           imabGroupLastChange                   DateAndTime,
--           imabGroupTxImaId                        INTEGER (0.. 255),
--           imabGroupRxImaId                        INTEGER (0.. 255),
           imabGroupTxFrameLength             ImaFrameLength,
--           imabGroupRxFrameLength             ImaFrameLength,
           imabGroupDiffDelayMax               MilliSeconds,
--           imabGroupLeastDelayLink            InterfaceIndexOrZero,
--           imabGroupDiffDelayMaxObs          MilliSeconds,
           imabGroupAlphaValue                   INTEGER (1.. 2),
           imabGroupBetaValue                     INTEGER (1.. 5),
           imabGroupGammaValue                   INTEGER (1.. 5),
--           imabGroupRunningSecs                 Gauge32,
--           imabGroupUnavailSecs                 Counter32,
--           imabGroupNeNumFailures             Counter32,
--           imabGroupFeNumFailures             Counter32,
--           imabGroupTxAvailCellRate          Gauge32,
--           imabGroupRxAvailCellRate          Gauge32,
--           imabGroupNumTxCfgLinks             Gauge32,
--           imabGroupNumRxCfgLinks             Gauge32,
--           imabGroupNumTxActLinks             Gauge32,
--           imabGroupNumRxActLinks             Gauge32,
--           imabGroupTestLinkIfIndex          InterfaceIndexOrZero,
           imabGroupTestPattern                 INTEGER (-1.. 255),
           imabGroupTestProcStatus            ImaTestProcStatus,
--           imabGroupValidIntervals            INTEGER (0.. 96),
--           imabGroupInvalidIntervals        INTEGER (0.. 96),
--           imabGroupTimeElapsed                 INTEGER (0.. 899),
           imabGroupTxOamLabelValue          INTEGER (1.. 255),
--           imabGroupRxOamLabelValue          INTEGER (0.. 255),
	   imabGroupCLKMode		    INTEGER }

imabGroupIndex OBJECT-TYPE
           SYNTAX            INTEGER (1.. 2147483647)
           MAX-ACCESS    not-accessible
           STATUS           current
           DESCRIPTION
              "A unique value for the IMA Group."
           ::= { imabGroupEntry 1 }

imabGroupRowStatus OBJECT-TYPE
           SYNTAX           RowStatus
           MAX-ACCESS    read-create
           STATUS           current
           DESCRIPTION
              "The imaGroupRowStatus object allows create, change, and delete
              operations on imaGroupTable entries.

              To create a new conceptual row (or instance) of the imaGroupTable,
              imaGroupRowStatus must be set to 'createAndWait' or 'createAndGo'.
              If settable, a successful set of the following objects must be
              performed before the imaGroupRowStatus of a new conceptual row can
              be set to 'active':

                  imaGroupMinNumTxLinks
                  imaGroupMinNumRxLinks
                  imaGroupTxImaId

              Some objects in the imaGroupTable control settings which can only
              be established or changed at group start-up time.    These objects
              include:

                  imaGroupTxImaId
                  imaGroupSymmetry
                  imaGroupTxFrameLength

              To change (modify) the imaGroupTxImaId object, the manager must
              first set imaGroupRowStatus to 'notInService'.    However, changes
              to the following two objects can be optionally allowed while the
              imaGroupRowStatus is 'active':

                  imaGroupSymmetry
                  imaGroupTxFrameLength

              These two objects can be changed when the imaGroupRowStatus is
              'active' in order to allow the far-end to recover from its
              Config-Aborted state without having to force the near-end Group
              State machine to go to the 'Not Configured' state.    Changing
              these object values after group start-up has completed causes a
              restart of the IMA group.

              Alternatively, as noted above, the agent implementation may
              simply require the imaGroupRowStatus object to first be set to
              'notInService' before allowing changes to either of these two
              objects.

              To remove (delete) an imaGroupTable entry from this table, set
              imaGroupRowStatus to 'destroy'.

              Setting the imaGroupRowStatus to 'active' has the effect of
              activating the Group Startup Procedure.    The Group Startup
              Procedure uses provisioned links that have imaLinkRowStatus set
              to 'active' and imaLinkGroupIndex set to the imaGroupIndex in
              this conceptual row.

              When the imaGroupRowStatus is not in 'active' state, the Group
              State machine is in its 'Not Configured' state."
           ::= { imabGroupEntry 2 }

--imabGroupIfIndex OBJECT-TYPE
--           SYNTAX           InterfaceIndex
--           MAX-ACCESS    read-only
--           STATUS           current
--           DESCRIPTION
--              "This object identifies the logical interface number ('ifIndex')
--              assigned to this IMA group, and is used to identify corresponding
--              rows in the Interfaces MIB.
--
--              Note that re-initialization of the management agent may cause
--              a client's 'imaGroupIfIndex' to change."
--           ::= { imabGroupEntry 3 }

--imabGroupNeState OBJECT-TYPE
--           SYNTAX           ImaGroupState
--           MAX-ACCESS    read-only
--           STATUS           current
--           DESCRIPTION
--              "The current operational state of the near-end IMA Group State
--              Machine."
--           REFERENCE
--              "ATM Forum IMA v1.1, Section 10.2.1 on page 55"
--           ::= { imabGroupEntry 4 }

--imabGroupFeState OBJECT-TYPE
--           SYNTAX           ImaGroupState
--           MAX-ACCESS    read-only
--           STATUS           current
--           DESCRIPTION
--              "The current operational state of the far-end IMA Group State
--              Machine."
--           REFERENCE
--              "ATM Forum IMA v1.1, Section 10.2.1 on page 55"
--           ::= { imabGroupEntry 5 }

--imabGroupFailureStatus OBJECT-TYPE
--           SYNTAX           ImaGroupFailureStatus
--           MAX-ACCESS    read-only
--           STATUS           current
--           DESCRIPTION
--              "The current failure status of the IMA group (the reason why
--              the GTSM is in the down state)."
--           REFERENCE
--              "ATM Forum IMA v1.1, Section 10.2.1 on page 55"
--           ::= { imabGroupEntry 6 }

imabGroupSymmetry OBJECT-TYPE
           SYNTAX           ImaGroupSymmetry
           MAX-ACCESS    read-create
           STATUS           current
           DESCRIPTION
              "Symmetry of the IMA group."
           REFERENCE
              "ATM Forum IMA v1.1, Section 5.2.2.7 on page 35"
           DEFVAL { symmetricOperation }
           ::= { imabGroupEntry 7 }

imabGroupMinNumTxLinks OBJECT-TYPE
           SYNTAX            INTEGER (1.. 32)
           MAX-ACCESS    read-create
           STATUS           current
           DESCRIPTION
              "Minimum number of transmit links required to be Active for
              the IMA group to be in the Operational state."
           REFERENCE
              "ATM Forum IMA v1.1, Section 10.2.1.1 on page 55"
           ::= { imabGroupEntry 8 }

imabGroupMinNumRxLinks OBJECT-TYPE
           SYNTAX            INTEGER (1.. 32)
           MAX-ACCESS    read-create
           STATUS           current
           DESCRIPTION
              "Minimum number of receive links required to be Active for
              the IMA group to be in the Operational state."
           REFERENCE
              "ATM Forum IMA v1.1, Section 10.2.1.1 on page 55"
           ::= { imabGroupEntry 9 }

imabGroupNeTxClkMode OBJECT-TYPE
           SYNTAX           ImaGroupTxClkMode
           MAX-ACCESS    read-create
           STATUS           current
           DESCRIPTION
              "Transmit clocking mode used by the near-end IMA group."
           REFERENCE
              "ATM Forum IMA v1.1, Section 7 on page 38"
           DEFVAL { ctc }
           ::= { imabGroupEntry 10 }

--imabGroupFeTxClkMode OBJECT-TYPE
--           SYNTAX           ImaGroupTxClkMode
--           MAX-ACCESS    read-only
--           STATUS           current
--           DESCRIPTION
--              "Transmit clocking mode used by the far-end IMA group."
--           REFERENCE
--              "ATM Forum IMA v1.1, Section 7 on page 38"
--           ::= { imabGroupEntry 11 }

--imabGroupTxTimingRefLink OBJECT-TYPE
--           SYNTAX           InterfaceIndexOrZero
--           MAX-ACCESS    read-only
--           STATUS           current
--           DESCRIPTION
--              "The ifIndex of the transmit timing reference link to be
--              used by the near-end for IMA data cell clock recovery from
--              the ATM layer.    The distinguished value of zero may be used
--              if no link has been configured in the IMA group, or if the
--              transmit timing reference link has not yet been selected."
--           REFERENCE
--              "ATM Forum IMA v1.1, Section 8.1.1 on page 41"
--           ::= { imabGroupEntry 12 }

--imabGroupRxTimingRefLink OBJECT-TYPE
--           SYNTAX           InterfaceIndexOrZero
--           MAX-ACCESS    read-only
--           STATUS           current
--           DESCRIPTION
--              "The ifIndex of the receive timing reference link to be
--              used by near-end for IMA data cell clock recovery toward
--              the ATM layer.    The distinguished value of zero may be used
--              if no link has been configured in the IMA group, or if the
--              receive timing reference link has not yet been detected."
--           REFERENCE
--              "ATM Forum IMA v1.1, Section 8.1.1 on page 41"
--           ::= { imabGroupEntry 13 }

--imabGroupLastChange OBJECT-TYPE
--           SYNTAX           DateAndTime
--           MAX-ACCESS    read-only
--           STATUS           current
--           DESCRIPTION
--              "The time-of-day the IMA group last changed operational
--              state (i. e., value of imaGroupNeState changed)."
--           ::= { imabGroupEntry 14 }

--imabGroupTxImaId OBJECT-TYPE
--           SYNTAX           INTEGER (0.. 255)
--           MAX-ACCESS    read-only
--           STATUS           current
--           DESCRIPTION
--              "The IMA ID currently in use by the near-end IMA function."
--           REFERENCE
--              "ATM Forum IMA v1.1, Section 5.2.2.6 on page 35"
--           ::= { imabGroupEntry 15 }

--imabGroupRxImaId OBJECT-TYPE
--           SYNTAX           INTEGER (0.. 255)
--           MAX-ACCESS    read-only
--           STATUS           current
--           DESCRIPTION
--              "The IMA ID currently in use by the far-end IMA function."
--           REFERENCE
--              "ATM Forum IMA v1.1, Section 5.2.2.6 on page 35"
--           ::= { imabGroupEntry 16 }

imabGroupTxFrameLength OBJECT-TYPE
           SYNTAX           ImaFrameLength
           MAX-ACCESS    read-create
           STATUS           current
           DESCRIPTION
              "The frame length to be used by the IMA group in the transmit
              direction.    Can only be set when the IMA group is startup."
           REFERENCE
              "ATM Forum IMA v1.1, Section 5.2.2.4.2 on page 34"
           DEFVAL { m128 }
           ::= { imabGroupEntry 17 }

--imabGroupRxFrameLength OBJECT-TYPE
--           SYNTAX           ImaFrameLength
--           MAX-ACCESS    read-only
--           STATUS           current
--           DESCRIPTION
--              "Value of IMA frame length as received from remote IMA function."
--           REFERENCE
--              "ATM Forum IMA v1.1, Section 5.2.2.4.2 on page 34"
--           ::= { imabGroupEntry 18 }

imabGroupDiffDelayMax OBJECT-TYPE
           SYNTAX           MilliSeconds
           MAX-ACCESS    read-create
           STATUS           current
           DESCRIPTION
              "The maximum number of milliseconds of differential delay among
              the links that will be tolerated on this interface."
           REFERENCE
              "ATM Forum IMA v1.1, Section 9.2 on page 45"
           DEFVAL { 25 }
           ::= { imabGroupEntry 19 }

--imabGroupLeastDelayLink OBJECT-TYPE
--           SYNTAX           InterfaceIndexOrZero
--           MAX-ACCESS    read-only
--           STATUS           current
--           DESCRIPTION
--              "The ifIndex of the link configured in the IMA group which has
--              the smallest link propagation delay.    The distinguished value of
--              zero may be used if no link has been configured in the IMA group,
--              or if the link with the smallest link propagation delay has not
--              yet been determined."
--           REFERENCE
--              "ATM Forum IMA v1.1, Section 9.2 on page 45"
--           ::= { imabGroupEntry 20 }

--imabGroupDiffDelayMaxObs OBJECT-TYPE
--           SYNTAX           MilliSeconds
--           MAX-ACCESS    read-only
--           STATUS           current
--           DESCRIPTION
--              "The latest maximum differential delay observed (in milliseconds)
--              between the links having the least and most link propagation delay,
--              among the receive links that are currently configured in the IMA
--              group."
--           REFERENCE
--              "ATM Forum IMA v1.1, Section 9.2 on page 45"
--           ::= { imabGroupEntry 21 }

imabGroupAlphaValue OBJECT-TYPE
           SYNTAX           INTEGER (1.. 2)
           MAX-ACCESS    read-create
           STATUS           current
           DESCRIPTION
              "This indicates the 'alpha' value used to specify the number
              of consecutive invalid ICP cells to be detected before moving
              to the IMA Hunt state from the IMA Sync state."
           REFERENCE
              "ATM Forum IMA v1.1, Section 11 on page 68"
           DEFVAL { 2 }
           ::= { imabGroupEntry 22 }

imabGroupBetaValue OBJECT-TYPE
           SYNTAX           INTEGER (1.. 5)
           MAX-ACCESS    read-create
           STATUS           current
           DESCRIPTION
              "This indicates the 'beta' value used to specify the number
              of consecutive errored ICP cells to be detected before moving
              to the IMA Hunt state from the IMA Sync state."
           REFERENCE
              "ATM Forum IMA v1.1, Section 11 on page 68"
           DEFVAL { 2 }
           ::= { imabGroupEntry 23 }

imabGroupGammaValue OBJECT-TYPE
           SYNTAX           INTEGER (1.. 5)
           MAX-ACCESS    read-create
           STATUS           current
           DESCRIPTION
              "This indicates the 'gamma' value used to specify the number
              of consecutive valid ICP cells to be detected before moving
              to the IMA Sync state from the IMA PreSync state."
           REFERENCE
              "ATM Forum IMA v1.1, Section 11 on page 68"
           DEFVAL { 1 }
           ::= { imabGroupEntry 24 }

--imabGroupRunningSecs OBJECT-TYPE
--           SYNTAX           Gauge32
--           MAX-ACCESS    read-only
--           STATUS           current
--           DESCRIPTION
--              "The amount of time (in seconds) since this IMA group has
--              been in the Operational state."
--           REFERENCE
--              "ATM Forum IMA v1.1, Section 10.2.1 on page 55"
--           ::= { imabGroupEntry 25 }

--imabGroupUnavailSecs OBJECT-TYPE
--           SYNTAX           Counter32
--           MAX-ACCESS    read-only
--           STATUS           current
--           DESCRIPTION
--              "Count of one second intervals where the IMA Group Traffic
--              State Machine is Down."
--           REFERENCE
--              "ATM Forum IMA v1.1, Section 10.2.1 on page 55 and (R-136) in Section
--              12.2.2.2 on page 77"
--           ::= { imabGroupEntry 26 }

--imabGroupNeNumFailures OBJECT-TYPE
--           SYNTAX           Counter32
--           MAX-ACCESS    read-only
--           STATUS           current
--           DESCRIPTION
--              "The number of times a near-end group failure (Config-Aborted,
--              Insufficient-Links) has been reported since power-up or reboot."
--           REFERENCE
--              "ATM Forum IMA v1.1, (R-137) in Section 12.2.2.2 on page 77"
--           ::= { imabGroupEntry 27 }

--imabGroupFeNumFailures OBJECT-TYPE
--           SYNTAX           Counter32
--           MAX-ACCESS    read-only
--           STATUS           current
--           DESCRIPTION
--              "The number of times a far-end group failure (Config-Aborted-FE,
--              Insufficient-Links-FE, Blocked-FE) has been reported since
--              power-up or reboot.    This is an optional attribute."
--           REFERENCE
--              "ATM Forum IMA v1.1, (O-25) in Section 12.2.2.2 on page 77"
--           ::= { imabGroupEntry 28 }

--imabGroupTxAvailCellRate OBJECT-TYPE
--           SYNTAX           Gauge32
--           MAX-ACCESS    read-only
--           STATUS           current
--           DESCRIPTION
--              "The current cell rate (truncated value in cells per second)
--              provided by this IMA group in the transmit direction,
--              considering all the transmit links in the Active state."
--           ::= { imabGroupEntry 29 }

--imabGroupRxAvailCellRate OBJECT-TYPE
--           SYNTAX           Gauge32
--           MAX-ACCESS    read-only
--           STATUS           current
--           DESCRIPTION
--              "The current cell rate (truncated value in cells per second)
--              provided by this IMA group in the receive direction,
--              considering all the receive links in the Active state."
--           ::= { imabGroupEntry 30 }

--imaGroupNumTxCfgLinks is used by a network operator to tell how many
--links are configured for transmit in the IMA group.

--imabGroupNumTxCfgLinks OBJECT-TYPE
--           SYNTAX           Gauge32
--           MAX-ACCESS    read-only
--           STATUS           current
--           DESCRIPTION
--              "The number of links that are configured to transmit in this IMA
--              group. This attribute overwrites the value of the
--              imaGroupNumRxActLinks attribute when the IMA group is configured
--              in the Symmetrical Configuration group symmetry mode."
--           ::= { imabGroupEntry 31 }

--imaGroupNumRxCfgLinks is used by a network operator to tell how many
--links are configured for receive in the IMA group.

--imabGroupNumRxCfgLinks OBJECT-TYPE
--           SYNTAX           Gauge32
--           MAX-ACCESS    read-only
--           STATUS           current
--           DESCRIPTION
--              "The number of links that are configured to receive in this IMA
--              group. This attribute is overwritten by the value of the
--              imaGroupNumTxActLinks attribute when the IMA group is configured
--              in the Symmetrical Configuration group symmetry mode."
--           ::= { imabGroupEntry 32 }

--imaGroupNumTxActLinks is used by a network operator to tell how many
--links which are configured for transmit are also Active.

--imabGroupNumTxActLinks OBJECT-TYPE
--           SYNTAX           Gauge32
--           MAX-ACCESS    read-only
--           STATUS           current
--           DESCRIPTION
--              "The number of links which are configured to transmit and are
--              currently Active in this IMA group."
--           ::= { imabGroupEntry 33 }

--imaGroupNumRxActLinks is used by a network operator to tell how many
--links which are configured for receive are also Active.

--imabGroupNumRxActLinks OBJECT-TYPE
--           SYNTAX           Gauge32
--           MAX-ACCESS    read-only
--           STATUS           current
--           DESCRIPTION
--              "The number of links which are configured to receive and are
--              currently Active in this IMA group."
--           ::= { imabGroupEntry 34 }

--
--Test Pattern Procedure control objects.    These objects are implemented
--if the IMA implements the Test Pattern Procedure.    In this case all
--test pattern procedure related objects must be implemented.    Specifically,
--these objects are:
--
--     imaGroupTestLinkIfIndex
--     imaGroupTestPattern
--     imaGroupTestProcStatus
--     imaLinkRxTestPattern
--     imaLinkTestProcStatus
--

--imabGroupTestLinkIfIndex OBJECT-TYPE
--           SYNTAX           InterfaceIndexOrZero
--           MAX-ACCESS    read-create
--           STATUS           current
--           DESCRIPTION
--              "This object is used to designate an interface as the test link
--              for use in the Test Pattern Procedure.    The distinguished value of
--              zero specifies that the implementation may choose the Test Link,
--              in which case, the implementation may also choose the value of
--              'imaGroupTestPattern'.    The value zero may also be used if no link
--              has yet been added to the group.
--
--              Note that this value is NOT the same as the Tx LID value, but
--              instead either identifies the ifIndex value of the test link to be
--              used by the Test Pattern Procedure (i. e., the link whose LID value
--              is inserted in the Tx LID field of the transmitted ICP cells),
--              or identifies that the implementation may choose the test link (if
--              the value is zero)."
--           REFERENCE
--              "ATM Forum IMA v1.1, Section 13 on page 81"
--           DEFVAL { 0 }
--           ::= { imabGroupEntry 35 }

imabGroupTestPattern OBJECT-TYPE
           SYNTAX            INTEGER (-1.. 255)
           MAX-ACCESS    read-create
           STATUS           current
           DESCRIPTION
              "The value of this object is used to specify the Tx Test Pattern
              in an IMA group loopback operation.    A value in the range 0 to
              255 designates a specific pattern.    The distinguished value of
              -1 specifies that the implementation may choose the value.    In
              this case, the implementation may also choose the value of
              'imaGroupTestLinkIfIndex'.

              It is recommended that the specific value 255 not be used for
              testing, since by (R-137) the IMA interface is required to
              transmit 0xFF (i. e., 255) when the incoming test command is
              inactive or the test link is not detected, and thus it cannot
              be established for certain whether 255 was received due to an
              actual loopback operation or due to the normal operation of an
              IMA that is not performing (or else cannot perform) the test
              pattern procedure."
           REFERENCE
              "ATM Forum IMA v1.1, Section 13 on page 81"
           DEFVAL { -1 }
           ::= { imabGroupEntry 36 }

imabGroupTestProcStatus OBJECT-TYPE
           SYNTAX           ImaTestProcStatus
           MAX-ACCESS    read-create
           STATUS           current
           DESCRIPTION
              "This object is used to enable or disable the
              Test Pattern Procedure, and to note whether at least one
              link failed the test.

              The test is started by setting operating( 2) status.    If any
              link should fail the test, the IMA will set the status to
              linkFail( 3).    The linkFail( 3) state will persist until
              either the disabled( 1) state is set or until no instance
              of imaLinkTestProcStatus has the value linkFail( 3).

              Only the values disabled( 1) and operating( 2) may be written.
              Writing the operating( 2) value will not cause clearing of
              the linkFail( 3) state."
           REFERENCE
              "ATM Forum IMA v1.1, Section 13 on page 81"
           DEFVAL { disabled }
           ::= { imabGroupEntry 37 }

--
--Objects for use with the IMA Group Current Table, the IMA Group
--Interval Table, and the IMA Group Total Table.
--
--Implementation of these objects is optional, dependent on whether
--the tables mentioned above are implemented.
--

--imabGroupValidIntervals OBJECT-TYPE
--           SYNTAX            INTEGER (0.. 96)
--           MAX-ACCESS    read-only
--           STATUS           current
--           DESCRIPTION
--              "The number of previous 15 minute intervals for which valid data
--              was collected.    The value will be 96 unless the IMA group table
--              entry was created within the last 24 hours, in which case the value
--              will be the number of complete 15 minute intervals since the IMA
--              group table entry was created.    In the case where the agent is a
--              proxy, it is possible that some intervals are unavailable.    In this
--              case, this value is the maximum interval number for which valid
--              data is available.    This attribute is only mandatory when the IMA
--              Group Interval Statistics and/ or IMA Group Total Statistics objects
--              are implemented."
--           REFERENCE
--              "ATM Forum IMA v1.1, (O-26) in Section 12.2.2.2 on page 77"
--           ::= { imabGroupEntry 38 }
--
--imabGroupInvalidIntervals OBJECT-TYPE
--           SYNTAX            INTEGER (0.. 96)
--           MAX-ACCESS    read-only
--           STATUS           current
--           DESCRIPTION
--              "The number of intervals for which no valid data is available.
--              This attribute is only mandatory when the IMA Group Interval
--              Statistics and/ or IMA Group Total Statistics objects are
--              implemented."
--           REFERENCE
--              "ATM Forum IMA v1.1, (O-26) in Section 12.2.2.2 on page 77"
--           ::= { imabGroupEntry 39 }

--imabGroupTimeElapsed OBJECT-TYPE
--           SYNTAX           INTEGER (0.. 899)
--           MAX-ACCESS    read-only
--           STATUS           current
--           DESCRIPTION
--              "The number of seconds that have elapsed since the beginning of
--              the current measurement period.    This attribute is only mandatory
--              when the IMA Group Current Statistics are implemented."
--           REFERENCE
--              "ATM Forum IMA v1.1, (O-26) in Section 12.2.2.2 on page 77"
--           ::= { imabGroupEntry 40 }

--
--Objects to report the IMA OAM Label values transmitted and
--received by the IMA group.
--

imabGroupTxOamLabelValue OBJECT-TYPE
           SYNTAX           INTEGER (1.. 255)
           MAX-ACCESS    read-create
           STATUS           current
           DESCRIPTION
              "IMA OAM Label value transmitted by the NE IMA unit."
           REFERENCE
              "ATM Forum IMA v1.1, Section 5.2.2.3 on page 32"
           ::= { imabGroupEntry 41 }

--imabGroupRxOamLabelValue OBJECT-TYPE
--           SYNTAX           INTEGER (0.. 255)
--           MAX-ACCESS    read-only
--           STATUS           current
--           DESCRIPTION
--              "IMA OAM Label value transmitted by the FE IMA unit.    The value 0
--              likely means that the IMA unit has not received an OAM Label
--              from the FE IMA unit at this time."
--           REFERENCE
--              "ATM Forum IMA v1.1, Section 5.2.2.3 on page 32"
--           ::= { imabGroupEntry 42 }

imabGroupCLKMode   OBJECT-TYPE
	SYNTAX     INTEGER{
			master(0),
			 slave(1)
	}
	MAX-ACCESS read-create
	STATUS current
	DESCRIPTION
		"The clock mode of the Group "
	::= { imabGroupEntry 43 }


--
--The IMA Group Current Statistics subtree
--
--the IMA Group Current Table.    This table contains various statistics
--collected by each IMA group for the current 15 minute interval.
--
--Implementation of IMA Group Current Table is optional.
--

imabGroupCurrentTable OBJECT-TYPE
           SYNTAX           SEQUENCE OF imabGroupCurrentEntry
           MAX-ACCESS    not-accessible
           STATUS           current
           DESCRIPTION
              "The IMA Group Current table."
           ::= { zxImabGroupMibObjects 3 }

imabGroupCurrentEntry OBJECT-TYPE
           SYNTAX           imabGroupCurrentEntry
           MAX-ACCESS    not-accessible
           STATUS           current
           DESCRIPTION
              "An entry in the IMA Group Current table."
           INDEX             { imabGroupIndex }
           ::= { imabGroupCurrentTable 1 }

imabGroupCurrentEntry ::= SEQUENCE {
           imabGroupCurrentUnavailSecs          Gauge32,
           imabGroupCurrentNeNumFailures      Gauge32,
           imabGroupCurrentFeNumFailures      Gauge32 }

imabGroupCurrentUnavailSecs OBJECT-TYPE
           SYNTAX           Gauge32
           MAX-ACCESS    read-only
           STATUS           current
           DESCRIPTION
              "Count of one second intervals where the IMA Group Traffic
              State Machine is Down in the current 15 minutes interval."
           REFERENCE
              "ATM Forum IMA v1.1, Section 10.2.1 on page 55, (R-136) and
              (O-26) in Section 12.2.2.2 on page 77"
           ::= { imabGroupCurrentEntry 1 }

imabGroupCurrentNeNumFailures OBJECT-TYPE
           SYNTAX           Gauge32
           MAX-ACCESS    read-only
           STATUS           current
           DESCRIPTION
              "The number of times a near-end group failure (Config-Aborted,
              Insufficient-Links) has been reported in the current 15
              minutes interval."
           REFERENCE
              "ATM Forum IMA v1.1, (R-137) and (O-26) in Section 12.2.2.2
              on page 77"
           ::= { imabGroupCurrentEntry 2 }

imabGroupCurrentFeNumFailures OBJECT-TYPE
           SYNTAX           Gauge32
           MAX-ACCESS    read-only
           STATUS           current
           DESCRIPTION
              "The number of times a far-end group failure (Config-Aborted-FE,
              Insufficient-Links-FE, Blocked-FE) has been reported in the
              current 15 minutes interval.    This is an optional attribute."
           REFERENCE
              "ATM Forum IMA v1.1, (O-25) and (O-26) in Section 12.2.2.2
              on page 77"
           ::= { imabGroupCurrentEntry 3 }

--
--The IMA Group Interval Statistics subtree
--
--The IMA Group Interval Statistics subtree consists of a single table:
--the IMA Group Interval Table.    This table contains various statistics
--collected by each IMA group over the previous 24 hours of operation.
--The past 24 hours are broken into 96 completed 15 minute intervals.
--
--Implementation of IMA Group Interval Table is optional.
--

imabGroupIntervalTable OBJECT-TYPE
           SYNTAX           SEQUENCE OF imabGroupIntervalEntry
           MAX-ACCESS    not-accessible
           STATUS           current
           DESCRIPTION
              "The IMA Group Interval table."
           ::= { zxImabGroupMibObjects 4 }

imabGroupIntervalEntry OBJECT-TYPE
           SYNTAX           imabGroupIntervalEntry
           MAX-ACCESS    not-accessible
           STATUS           current
           DESCRIPTION
              "An entry in the IMA Group Interval table."
           INDEX             { imabGroupIndex, imabGroupIntervalNumber }
           ::= { imabGroupIntervalTable 1 }

imabGroupIntervalEntry ::= SEQUENCE {
           imabGroupIntervalNumber                   INTEGER (1.. 96),
           imabGroupIntervalUnavailSecs          Gauge32,
           imabGroupIntervalNeNumFailures      Gauge32,
           imabGroupIntervalFeNumFailures      Gauge32 }

imabGroupIntervalNumber OBJECT-TYPE
           SYNTAX            INTEGER (1.. 96)
           MAX-ACCESS    not-accessible
           STATUS           current
           DESCRIPTION
              "A number between 1 and 96, where 1 is the most
                recently completed 15 minute interval and 96 is the least
                recently completed 15 minutes interval (assuming that all
                96 intervals are valid)."
           ::= { imabGroupIntervalEntry 1 }

imabGroupIntervalUnavailSecs OBJECT-TYPE
           SYNTAX           Gauge32
           MAX-ACCESS    read-only
           STATUS           current
           DESCRIPTION
              "Count of one second intervals where the IMA Group Traffic
              State Machine is Down in one of the previous 96, individual 15
              minute, intervals."
           REFERENCE
              "ATM Forum IMA v1.1, Section 10.2.1 on page 55, (R-136) and
              (O-26) in Section 12.2.2.2 on page 77"
           ::= { imabGroupIntervalEntry 2 }

imabGroupIntervalNeNumFailures OBJECT-TYPE
           SYNTAX           Gauge32
           MAX-ACCESS    read-only
           STATUS           current
           DESCRIPTION
              "The number of times a near-end group failure (Config-Aborted,
              Insufficient-Links) has been reported in one of the previous
              96, individual 15 minute, intervals."
           REFERENCE
              "ATM Forum IMA v1.1, (R-137) and (O-26) in Section 12.2.2.2
              on page 77"
           ::= { imabGroupIntervalEntry 3 }

imabGroupIntervalFeNumFailures OBJECT-TYPE
           SYNTAX           Gauge32
           MAX-ACCESS    read-only
           STATUS           current
           DESCRIPTION
              "The number of times a far-end group failure (Config-Aborted-FE,
              Insufficient-Links-FE, Blocked-FE) has been reported in one of
              the previous 96, individual 15 minute, intervals.    This is an
              optional attribute."
           REFERENCE
              "ATM Forum IMA v1.1, (O-25) and (O-26) in Section 12.2.2.2
              on page 77"
           ::= { imabGroupIntervalEntry 4 }

--
--The IMA Group Total Statistics subtree
--
--The IMA Group Total Statistics subtree consists of a single table:
--the IMA Group Total Table.    This table contains the cumulative sum
--of the various statistics collected by each IMA group for the 24 hour
--period preceding the current interval.
--
--Implementation of IMA Group Total Table is optional.
--

imabGroupTotalTable OBJECT-TYPE
           SYNTAX           SEQUENCE OF imabGroupTotalEntry
           MAX-ACCESS    not-accessible
           STATUS           current
           DESCRIPTION
              "The IMA Group Total table."
           ::= { zxImabGroupMibObjects 5 }

imabGroupTotalEntry OBJECT-TYPE
           SYNTAX           imabGroupTotalEntry
           MAX-ACCESS    not-accessible
           STATUS           current
           DESCRIPTION
              "An entry in the IMA Group Total table."
           INDEX             { imabGroupIndex }
           ::= { imabGroupTotalTable 1 }

imabGroupTotalEntry ::= SEQUENCE {
           imabGroupTotalUnavailSecs          Gauge32,
           imabGroupTotalNeNumFailures      Gauge32,
           imabGroupTotalFeNumFailures      Gauge32 }

imabGroupTotalUnavailSecs OBJECT-TYPE
           SYNTAX           Gauge32
           MAX-ACCESS    read-only
           STATUS           current
           DESCRIPTION
              "Count of one second intervals where the IMA Group Traffic
              State Machine is Down in the previous 24 hour interval.
              Invalid 15 minute intervals count as 0."
           REFERENCE
              "ATM Forum IMA v1.1, Section 10.2.1 on page 55, (R-136) and
              (O-27) in Section 12.2.2.2 on page 77"
           ::= { imabGroupTotalEntry 1 }

imabGroupTotalNeNumFailures OBJECT-TYPE
           SYNTAX           Gauge32
           MAX-ACCESS    read-only
           STATUS           current
           DESCRIPTION
              "The number of times a near-end group failure (Config-Aborted,
              Insufficient-Links) has been reported in the previous 24 hour
              interval.    Invalid 15 minute intervals count as 0."
           REFERENCE
              "ATM Forum IMA v1.1, (R-137) and (O-27) in Section 12.2.2.2
              on page 77"
           ::= { imabGroupTotalEntry 2 }

imabGroupTotalFeNumFailures OBJECT-TYPE
           SYNTAX           Gauge32
           MAX-ACCESS    read-only
           STATUS           current
           DESCRIPTION
              "The number of times a far-end group failure (Config-Aborted-FE,
              Insufficient-Links-FE, Blocked-FE) has been reported in the
              previous 24 hour interval.    Invalid 15 minute intervals count
              as 0.    This is an optional attribute."
           REFERENCE
              "ATM Forum IMA v1.1, (O-25) and (O-27) in Section 12.2.2.2
              on page 77"
           ::= { imabGroupTotalEntry 3 }

--Conformance Information
--Compliance Statements


--Units of Conformance
imabGroupNumberGroup OBJECT-GROUP
  OBJECTS{
     imabGroupNumber
  }
 STATUS  current
 DESCRIPTION 
       "imabGroupNumber group"
 ::={zxImabGroupMibGroups 1}

imabGroupGroup OBJECT-GROUP
           OBJECTS {
           imabGroupIndex ,
           imabGroupRowStatus ,
           imabGroupIfIndex ,
           imabGroupNeState ,
           imabGroupFeState ,
           imabGroupFailureStatus ,
           imabGroupSymmetry ,
           imabGroupMinNumTxLinks ,
           imabGroupMinNumRxLinks ,
           imabGroupNeTxClkMode ,
           imabGroupFeTxClkMode ,
           imabGroupTxTimingRefLink ,
           imabGroupRxTimingRefLink ,
           imabGroupLastChange ,
           imabGroupTxImaId ,
           imabGroupRxImaId ,
           imabGroupTxFrameLength ,
           imabGroupRxFrameLength ,
           imabGroupDiffDelayMax ,
           imabGroupLeastDelayLink ,
           imabGroupDiffDelayMaxObs ,
           imabGroupAlphaValue ,
           imabGroupBetaValue ,
           imabGroupGammaValue ,
           imabGroupRunningSecs ,
           imabGroupUnavailSecs ,
           imabGroupNeNumFailures ,
           imabGroupFeNumFailures ,
           imabGroupTxAvailCellRate ,
           imabGroupRxAvailCellRate ,
           imabGroupNumTxCfgLinks ,
           imabGroupNumRxCfgLinks ,
           imabGroupNumTxActLinks ,
           imabGroupNumRxActLinks ,
           imabGroupTestLinkIfIndex ,
           imabGroupTestPattern ,
           imabGroupTestProcStatus ,
           imabGroupValidIntervals ,
           imabGroupInvalidIntervals ,
           imabGroupTimeElapsed ,
           imabGroupTxOamLabelValue ,
           imabGroupRxOamLabelValue ,
	   imabGroupCLKMode         }
           STATUS          current
           DESCRIPTION
              "A set of objects providing configuration and status information for
              an IMA group definition."
           ::= { zxImabGroupMibGroups 2 }

 imabGroupTestPatternGroup OBJECT-GROUP
           OBJECTS {
              imabGroupTestLinkIfIndex,
              imabGroupTestPattern,
              imabGroupTestProcStatus}
           STATUS          current
           DESCRIPTION
              "Objects in the imaGroupTable and imaLinkTable which control and
              report on the Test Pattern Procedure.    These objects must be
              implemented if the IMA Test Pattern Procedure is supported."
           ::= { zxImabGroupMibGroups 3 }


imabGroupIntervalGroup OBJECT-GROUP
           OBJECTS {
              imabGroupValidIntervals,
              imabGroupInvalidIntervals,
              imabGroupTimeElapsed,
              imabGroupCurrentUnavailSecs,
              imabGroupCurrentNeNumFailures,
              imabGroupCurrentFeNumFailures,
              imabGroupIntervalUnavailSecs,
              imabGroupIntervalNeNumFailures,
              imabGroupIntervalFeNumFailures,
              imabGroupTotalUnavailSecs,
              imabGroupTotalNeNumFailures,
              imabGroupTotalFeNumFailures }
           STATUS          current
           DESCRIPTION
              "Objects containing interval statistics for an IMA group."
           ::= { zxImabGroupMibGroups 4 }

zxImabGroupMibCompliance MODULE-COMPLIANCE
    STATUS  current
    DESCRIPTION
           "The compliance statement."
    MODULE  -- this module
    MANDATORY-GROUPS{
            imabGroupNumberGroup,
            imabGroupGroup,
            imabGroupTestPatternGroup,
            imabGroupIntervalGroup
            }
        ::= { zxImabGroupMibCompliances 1 }

END

IMAB-LINK-MIB DEFINITIONS ::= BEGIN

IMPORTS
           MODULE-IDENTITY, OBJECT-TYPE, Integer32, Counter32, Gauge32,
           NOTIFICATION-TYPE, enterprises
              FROM SNMPv2-SMI
           MODULE-COMPLIANCE, OBJECT-GROUP, NOTIFICATION-GROUP
              FROM SNMPv2-CONF
           TEXTUAL-CONVENTION, DateAndTime, RowStatus
              FROM SNMPv2-TC
           InterfaceIndex, InterfaceIndexOrZero, ifIndex
              FROM IF-MIB;
              
zxImabLinkMib MODULE-IDENTITY
           LAST-UPDATED "9902111830Z"
           ORGANIZATION "The ATM Forum"
           CONTACT-INFO
              "ATM Forum
              World Headquarters
              2570 West El Camino Real
              Suite 304
              Mountain View, CA 94040-1313
              USA
              Phone: +1 415 949 6700
              Fax: +1 415 949 6705
              email: info@ atmforum. com"
           DESCRIPTION
              "The MIB module for managing ATM Forum Inverse Multiplexing
              for ATM (IMA) interfaces."
           REVISION          "9902111830Z"
           DESCRIPTION
              "Updated and repaired version of the IMA-MIB released with the
              IMA v1.1 specification (af-phy-0086.001)."
           REVISION          "9701092245Z"
           DESCRIPTION
              "Initial incomplete version of the IMA-MIB as published in the
              IMA v1.0 specification (af-phy-0086.000)."
           ::= { zxIma 6 }

zte OBJECT IDENTIFIER ::= { enterprises 3902 }
zxDsl OBJECT IDENTIFIER ::= { zte 1004 }
zxDslam OBJECT IDENTIFIER ::= { zxDsl 1 }
zxIma	OBJECT IDENTIFIER ::= { zxDslam 11 }

zxImabLinkMibObjects OBJECT IDENTIFIER ::= { zxImabLinkMib 1 }

zxImabLinkMibConformance OBJECT IDENTIFIER ::= { zxImabLinkMib 2 }
zxImabLinkMibGroups OBJECT IDENTIFIER ::= { zxImabLinkMibConformance 1 }
zxImabLinkMibCompliances OBJECT IDENTIFIER ::= { zxImabLinkMibConformance 2 }


--Textual conventions

MilliSeconds ::= TEXTUAL-CONVENTION
           STATUS           current
           DESCRIPTION
              "Time in milliseconds"
           SYNTAX           Integer32

ImaLinkState ::= TEXTUAL-CONVENTION
           STATUS           current
           DESCRIPTION
              "State of a link belonging to an IMA group."
           REFERENCE
              "ATM Forum IMA v1.1, Section 10.1.2 on page 48"
           SYNTAX            INTEGER {
              notInGroup( 1),
              unusableNoGivenReason( 2),
              unusableFault( 3),
              unusableMisconnected( 4),
              unusableInhibited( 5),
              unusableFailed( 6),
              usable( 7),
              active( 8) }

ImaLinkFailureStatus ::= TEXTUAL-CONVENTION
           STATUS           current
           DESCRIPTION
              "Local failure status of a link belonging to an IMA group."
           REFERENCE
              "ATM Forum IMA v1.1, Section 10.1.2 on page 48"
           SYNTAX            INTEGER {
              noFailure( 1),
              imaLinkFailure( 2),
              lifFailure( 3),
              lodsFailure( 4),
              misConnected( 5),
              blocked( 6),
              fault( 7),
              farEndTxLinkUnusable( 8),
              farEndRxLinkUnusable( 9) }

ImaTestProcStatus ::= TEXTUAL-CONVENTION
           STATUS           current
           DESCRIPTION
              "States of the Test Pattern Procedure."
           REFERENCE
              "ATM Forum IMA v1.1, Section 13 on page 81"
           SYNTAX            INTEGER {
              disabled( 1),
              operating( 2),
              linkFail( 3) }

--
--The IMA Link subtree
--
--The IMA Link subtree consists of a table of IMA links.    Each entry
--in the table contains status information about a link which is part
--of an IMA group, and also contains a configuration object to select
--to which IMA group the link belongs.
--

imabLinkTable OBJECT-TYPE
           SYNTAX           SEQUENCE OF ImabLinkEntry
           MAX-ACCESS    not-accessible
           STATUS           current
           DESCRIPTION
              "The IMA group Link Status and Configuration table."
           ::= { zxImabLinkMibObjects 1 }

imabLinkEntry OBJECT-TYPE
           SYNTAX           ImabLinkEntry
           MAX-ACCESS    not-accessible
           STATUS           current
           DESCRIPTION
              "An entry in the IMA Group Link table."
           INDEX             { imabLinkIfIndex }
           ::= { imabLinkTable 1 }

ImabLinkEntry ::= SEQUENCE {
           imabLinkIfIndex                          InterfaceIndex,
           imabLinkRowStatus                      RowStatus,
           imabLinkGroupIndex                     Integer32,
--           imabLinkNeTxState                      ImaLinkState,
--           imabLinkNeRxState                      ImaLinkState,
--           imabLinkFeTxState                      ImaLinkState,
--           imabLinkFeRxState                      ImaLinkState,
--           imabLinkNeRxFailureStatus        ImaLinkFailureStatus,
--           imabLinkFeRxFailureStatus        ImaLinkFailureStatus,
--           imabLinkTxLid                              INTEGER (0.. 31),
--           imabLinkRxLid                              INTEGER (0.. 31),
--           imabLinkRelDelay                        MilliSeconds,
--           imabLinkImaViolations               Counter32,
--           imabLinkOifAnomalies                 Counter32,
--           imabLinkNeSevErroredSecs          Counter32,
--           imabLinkFeSevErroredSecs          Counter32,
--           imabLinkNeUnavailSecs               Counter32,
--           imabLinkFeUnavailSecs               Counter32,
--           imabLinkNeTxUnusableSecs          Counter32,
--           imabLinkNeRxUnusableSecs          Counter32,
--           imabLinkFeTxUnusableSecs          Counter32,
--           imabLinkFeRxUnusableSecs          Counter32,
--           imabLinkNeTxNumFailures            Counter32,
--           imabLinkNeRxNumFailures            Counter32,
--           imabLinkFeTxNumFailures            Counter32,
--           imabLinkFeRxNumFailures            Counter32,
--           imabLinkTxStuffs                        Counter32,
--           imabLinkRxStuffs                        Counter32,
--           imabLinkRxTestPattern               INTEGER (0.. 255),
--           imabLinkTestProcStatus             ImaTestProcStatus,
--           imabLinkValidIntervals             INTEGER (0.. 96),
--           imabLinkInvalidIntervals          INTEGER (0.. 96),
--           imabLinkTimeElapsed                   INTEGER (0.. 899),
	   imabLinkScramble			 INTEGER}

imabLinkIfIndex OBJECT-TYPE
           SYNTAX           InterfaceIndex
           MAX-ACCESS    not-accessible
           STATUS           current
           DESCRIPTION
              "This corresponds to the 'ifIndex' of the MIB-II interface
              on which this link is established.    This object also
              corresponds to the logical number ('ifIndex') assigned to
              this IMA link."
           ::= { imabLinkEntry 1 }

imabLinkRowStatus OBJECT-TYPE
           SYNTAX           RowStatus
           MAX-ACCESS    read-create
           STATUS           current
           DESCRIPTION
              "The imaLinkRowStatus object allows create, change, and delete
              operations on imaLinkTable entries.

              To create a new conceptual row (or instance) of the imaLinkTable,
              imaLinkRowStatus must be set to 'createAndWait' or 'createAndGo'.
              A successful set of the imaLinkGroupIndex object must be performed
              before the imaLinkRowStatus of a new conceptual row can be set to
              'active'.

              To change (modify) the imaLinkGroupIndex in an imaLinkTable entry,
              the imaLinkRowStatus object must first be set to 'notInService'.
              Only then can this object in the conceptual row be modified.
              This is due to the fact that the imaLinkGroupIndex object provides
              the association between a physical IMA link and the IMA group to
              which it belongs, and setting the imaLinkGroupIndex object to a
              different value has the effect of changing the association between
              a physical IMA link and an IMA group.    To place the link 'in group',
              the imaLinkRowStatus object is set to 'active'.    While the row is
              not in 'active' state, both the Transmit and Receive IMA link state
              machines are in the 'Not In Group' state.

              To remove (delete) an imaLinkTable entry from this table, set
              this object to 'destroy'."
           ::= { imabLinkEntry 2 }

imabLinkGroupIndex OBJECT-TYPE
           SYNTAX           Integer32
           MAX-ACCESS    read-create
           STATUS           current
           DESCRIPTION
              "The value which identifies the IMA group (imaGroupIndex)
              of which this link is a member."
           ::= { imabLinkEntry 3 }

--imabLinkNeTxState OBJECT-TYPE
--           SYNTAX           ImaLinkState
--           MAX-ACCESS    read-only
--           STATUS           current
--           DESCRIPTION
--              "The current state of the near-end transmit link."
--           REFERENCE
--              "ATM Forum IMA v1.1, Section 10.1.2 on page 48"
--           ::= { imabLinkEntry 4 }

--imabLinkNeRxState OBJECT-TYPE
--           SYNTAX           ImaLinkState
--           MAX-ACCESS    read-only
--           STATUS           current
--           DESCRIPTION
--              "The current state of the near-end receive link."
--           REFERENCE
--              "ATM Forum IMA v1.1, Section 10.1.2 on page 48"
--           ::= { imabLinkEntry 5 }

--imabLinkFeTxState OBJECT-TYPE
--           SYNTAX           ImaLinkState
--           MAX-ACCESS    read-only
--           STATUS           current
--           DESCRIPTION
--              "The current state of the far-end transmit link as reported
--              via ICP cells."
--           REFERENCE
--              "ATM Forum IMA v1.1, Section 10.1.2 on page 48"
--           ::= { imabLinkEntry 6 }

--imabLinkFeRxState OBJECT-TYPE
--           SYNTAX           ImaLinkState
--           MAX-ACCESS    read-only
--           STATUS           current
--           DESCRIPTION
--              "The current state of the far-end receive link as reported
--              via ICP cells."
--           REFERENCE
--              "ATM Forum IMA v1.1, Section 10.1.2 on page 48"
--           ::= { imabLinkEntry 7 }

--imabLinkNeRxFailureStatus OBJECT-TYPE
--           SYNTAX           ImaLinkFailureStatus
--           MAX-ACCESS    read-only
--           STATUS           current
--           DESCRIPTION
--              "The current link failure status of the near-end receive link."
--           REFERENCE
--              "ATM Forum IMA v1.1, Section 10.1.2 on page 48"
--           ::= { imabLinkEntry 8 }

--imabLinkFeRxFailureStatus OBJECT-TYPE
--           SYNTAX           ImaLinkFailureStatus
--           MAX-ACCESS    read-only
--           STATUS           current
--           DESCRIPTION
--              "The current link failure status of the far-end receive link
--              as reported via ICP cells."
--           REFERENCE
--              "ATM Forum IMA v1.1, Section 10.1.2 on page 48"
--           ::= { imabLinkEntry 9 }

--imabLinkTxLid OBJECT-TYPE
--           SYNTAX            INTEGER (0.. 31)
--           MAX-ACCESS    read-only
--           STATUS           current
--           DESCRIPTION
--              "The outgoing LID used currently on the link by the local end.
--              This value has meaning only if the link belongs to an IMA group."
--           REFERENCE
--              "ATM Forum IMA v1.1, Section 5.2.2.1 on page 26"
--           ::= { imabLinkEntry 10 }
--
--imabLinkRxLid OBJECT-TYPE
--           SYNTAX            INTEGER (0.. 31)
--           MAX-ACCESS    read-only
--           STATUS           current
--           DESCRIPTION
--              "The incoming LID used currently on the link by the remote
--              end as reported via ICP cells.    This value has meaning only
--              if the link belongs to an IMA group."
--           REFERENCE
--              "ATM Forum IMA v1.1, Section 5.2.2.1 on page 26"
--           ::= { imabLinkEntry 11 }
--
--imabLinkRelDelay OBJECT-TYPE
--           SYNTAX           MilliSeconds
--           MAX-ACCESS    read-only
--           STATUS           current
--           DESCRIPTION
--              "The latest measured delay on this link relative to the link, in
--              the same IMA group, with the least delay."
--           REFERENCE
--              "ATM Forum IMA v1.1, Section 9.2 on page 45"
--           ::= { imabLinkEntry 12 }
--
--imabLinkImaViolations OBJECT-TYPE
--           SYNTAX           Counter32
--           MAX-ACCESS    read-only
--           STATUS           current
--           DESCRIPTION
--              "ICP violations: count of errored, invalid or missing ICP cells,
--              except during SES-IMA or UAS-IMA conditions."
--           REFERENCE
--              "ATM Forum IMA v1.1, (R-125) in Section 12.2.2.2 on page 77"
--           ::= { imabLinkEntry 13 }
--
--imabLinkOifAnomalies OBJECT-TYPE
--           SYNTAX           Counter32
--           MAX-ACCESS    read-only
--           STATUS           current
--           DESCRIPTION
--              "The number of OIF anomalies, except during SES-IMA or UAS-IMA
--              conditions, at the near-end.    This is an optional attribute."
--           REFERENCE
--              "ATM Forum IMA v1.1, (O-20) in Section 12.2.2.2 on page 77"
--           ::= { imabLinkEntry 14 }
--
--imabLinkNeSevErroredSecs OBJECT-TYPE
--           SYNTAX           Counter32
--           MAX-ACCESS    read-only
--           STATUS           current
--           DESCRIPTION
--              "Count of one second intervals containing >= 30% of the ICP cells
--              counted as IV-IMAs, or one or more link defects (e. g., LOS, OOF/ LOF,
--              AIS, or LCD), LIF defects, or LODS defects, except during UAS-IMA
--              condition."
--           REFERENCE
--              "ATM Forum IMA v1.1, (R-126) in Section 12.2.2.2 on page 77"
--           ::= { imabLinkEntry 15 }
--
--imabLinkFeSevErroredSecs OBJECT-TYPE
--           SYNTAX           Counter32
--           MAX-ACCESS    read-only
--           STATUS           current
--           DESCRIPTION
--              "Count of one second intervals containing one or more RDI-IMA
--              defects, except during UAS-IMA-FE condition."
--           REFERENCE
--              "ATM Forum IMA v1.1, (R-127) in Section 12.2.2.2 on page 77"
--           ::= { imabLinkEntry 16 }
--
--imabLinkNeUnavailSecs OBJECT-TYPE
--           SYNTAX           Counter32
--           MAX-ACCESS    read-only
--           STATUS           current
--           DESCRIPTION
--              "Count of unavailable seconds at near-end: unavailability begins
--              at the onset of 10 contiguous SES-IMA and ends at the onset
--              of 10 contiguous seconds with no SES-IMA."
--           REFERENCE
--              "ATM Forum IMA v1.1, (R-128) in Section 12.2.2.2 on page 77"
--           ::= { imabLinkEntry 17 }
--
--imabLinkFeUnavailSecs OBJECT-TYPE
--           SYNTAX           Counter32
--           MAX-ACCESS    read-only
--           STATUS           current
--           DESCRIPTION
--              "Count of unavailable seconds at far-end: unavailability begins
--              at the onset of 10 contiguous SES-IMA-FE and ends at the onset of
--              10 contiguous seconds with no SES-IMA-FE."
--           REFERENCE
--              "ATM Forum IMA v1.1, (R-129) in Section 12.2.2.2 on page 77"
--           ::= { imabLinkEntry 18 }
--
--imabLinkNeTxUnusableSecs OBJECT-TYPE
--           SYNTAX           Counter32
--           MAX-ACCESS    read-only
--           STATUS           current
--           DESCRIPTION
--              "Tx Unusable seconds: count of Tx Unusable seconds at the near-end
--              Tx LSM."
--           REFERENCE
--              "ATM Forum IMA v1.1, (R-130) in Section 12.2.2.2 on page 77"
--           ::= { imabLinkEntry 19 }
--
--imabLinkNeRxUnusableSecs OBJECT-TYPE
--           SYNTAX           Counter32
--           MAX-ACCESS    read-only
--           STATUS           current
--           DESCRIPTION
--              "Rx Unusable seconds: count of Rx Unusable seconds at the near-end
--              Rx LSM."
--           REFERENCE
--              "ATM Forum IMA v1.1, (R-131) in Section 12.2.2.2 on page 77"
--           ::= { imabLinkEntry 20 }
--
--imabLinkFeTxUnusableSecs OBJECT-TYPE
--           SYNTAX           Counter32
--           MAX-ACCESS    read-only
--           STATUS           current
--           DESCRIPTION
--              "Tx Unusable seconds at far-end: count of seconds with Tx Unusable
--              indications from the far-end Tx LSM."
--           REFERENCE
--              "ATM Forum IMA v1.1, (R-132) in Section 12.2.2.2 on page 77"
--           ::= { imabLinkEntry 21 }
--
--imabLinkFeRxUnusableSecs OBJECT-TYPE
--           SYNTAX           Counter32
--           MAX-ACCESS    read-only
--           STATUS           current
--           DESCRIPTION
--              "Rx Unusable seconds at far-end: count of seconds with Rx Unusable
--              indications from the far-end Rx LSM."
--           REFERENCE
--              "ATM Forum IMA v1.1, (R-133) in Section 12.2.2.2 on page 77"
--           ::= { imabLinkEntry 22 }
--
--imabLinkNeTxNumFailures OBJECT-TYPE
--           SYNTAX           Counter32
--           MAX-ACCESS    read-only
--           STATUS           current
--           DESCRIPTION
--              "The number of times a near-end transmit failure alarm condition
--              has been entered on this link (i. e., some form of implementation
--              specific transmit fault)."
--           REFERENCE
--              "ATM Forum IMA v1.1, (R-134) in Section 12.2.2.2 on page 77"
--           ::= { imabLinkEntry 23 }
--
--imabLinkNeRxNumFailures OBJECT-TYPE
--           SYNTAX           Counter32
--           MAX-ACCESS    read-only
--           STATUS           current
--           DESCRIPTION
--              "The number of times a near-end receive failure alarm condition
--              has been entered on this link (i. e., LIF, LODS,
--              RFI-IMA, Mis-Connected or some form of implementation specific receive
--              fault)."
--           REFERENCE
--              "ATM Forum IMA v1.1, (R-135) in Section 12.2.2.2 on page 77"
--           ::= { imabLinkEntry 24 }
--
--imabLinkFeTxNumFailures OBJECT-TYPE
--           SYNTAX           Counter32
--           MAX-ACCESS    read-only
--           STATUS           current
--           DESCRIPTION
--              "The number of times a far-end transmit failure alarm condition
--              has been entered on this link (i. e., Tx-Unusable-FE).    This is an
--              optional attribute."
--           REFERENCE
--              "ATM Forum IMA v1.1, (O-21) in Section 12.2.2.2 on page 77"
--           ::= { imabLinkEntry 25 }
--
--imabLinkFeRxNumFailures OBJECT-TYPE
--           SYNTAX           Counter32
--           MAX-ACCESS    read-only
--           STATUS           current
--           DESCRIPTION
--              "The number of times a far-end receive failure alarm condition
--              has been entered on this link (i. e., Rx-Unusable-FE).    This is an
--              optional attribute."
--           REFERENCE
--              "ATM Forum IMA v1.1, (O-22) in Section 12.2.2.2 on page 77"
--           ::= { imabLinkEntry 26 }
--
--imabLinkTxStuffs OBJECT-TYPE
--           SYNTAX           Counter32
--           MAX-ACCESS    read-only
--           STATUS           current
--           DESCRIPTION
--              "Count of stuff events inserted in the transmit direction.
--              This is an optional attribute."
--           REFERENCE
--              "ATM Forum IMA v1.1, (O-23) in Section 12.2.2.2 on page 77"
--           ::= { imabLinkEntry 27 }
--
--imabLinkRxStuffs OBJECT-TYPE
--           SYNTAX           Counter32
--           MAX-ACCESS    read-only
--           STATUS           current
--           DESCRIPTION
--              "Count of stuff events detected in the receive direction.
--              This is an optional attribute."
--           REFERENCE
--              "ATM Forum IMA v1.1, (O-24) in Section 12.2.2.2 on page 77"
--           ::= { imabLinkEntry 28 }
--

--Test Pattern Procedure control objects.    These objects are implemented
--if the IMA implements the Test Pattern Procedure.    In this case all
--test pattern procedure related objects must be implemented.    Specifically,
--these objects are:
--
--     imaGroupTestLinkIfIndex
--     imaGroupTestPattern
--     imaGroupTestProcStatus
--     imaLinkRxTestPattern
--     imaLinkTestProcStatus
--

--imabLinkRxTestPattern OBJECT-TYPE
--           SYNTAX           INTEGER (0.. 255)
--           MAX-ACCESS    read-only
--           STATUS           current
--           DESCRIPTION
--              "This object identifies the test pattern received in the
--              ICP Cell (octet 17) on the link during the IMA Test Pattern
--              Procedure.    This value may then be compared to the transmitted
--              test pattern."
--           ::= { imabLinkEntry 29 }
--
--imabLinkTestProcStatus OBJECT-TYPE
--           SYNTAX           ImaTestProcStatus
--           MAX-ACCESS    read-only
--           STATUS           current
--           DESCRIPTION
--              "This value indicates the current state of the Test Pattern
--              Procedure.    If the value is disabled( 1), the test is not
--              running.    A value of operating( 2) means the test is running
--              and no error has been found on this interface.    A value of
--              linkFail( 3) means an error has been detected on this link
--              during the test.
--
--              Once an error is detected, the linkFail( 3) value is latched until
--              either this object is read or until the imaGroupTestProcStatus
--              is moved to disabled( 1).    Once read, if the error no longer
--              persists, a subsequent read will report the value operating( 2)."
--           ::= { imabLinkEntry 30 }

--
--Objects for use with the IMA Link Current Table, the IMA Link
--Interval Table, and the IMA Link Total Table.
--
--Implementation of these objects is optional, dependent on whether
--the tables mentioned above are implemented.
--

--imabLinkValidIntervals OBJECT-TYPE
--           SYNTAX            INTEGER (0.. 96)
--           MAX-ACCESS    read-only
--           STATUS           current
--           DESCRIPTION
--              "The number of previous 15 minute intervals for which valid data
--              was collected.    The value will be 96 unless the IMA group table
--              entry was created within the last 24 hours, in which case the value
--              will be the number of complete 15 minute intervals since the IMA
--              group table entry was created.    In the case where the agent is a
--              proxy, it is possible that some intervals are unavailable.    In this
--              case, this value is the maximum interval number for which valid
--              data is available.    This attribute is only mandatory when the IMA
--              Link Interval Statistics and/ or IMA Link Total Statistics objects
--              are implemented."
--           REFERENCE
--              "ATM Forum IMA v1.1, (O-26) in Section 12.2.2.2 on page 77"
--           ::= { imabLinkEntry 31 }
--
--imabLinkInvalidIntervals OBJECT-TYPE
--           SYNTAX            INTEGER (0.. 96)
--           MAX-ACCESS    read-only
--           STATUS           current
--           DESCRIPTION
--              "The number of intervals for which no valid data is available.
--              This attribute is only mandatory when the IMA Link Interval
--              Statistics and/ or IMA Link Total Statistics objects are
--              implemented."
--           REFERENCE
--              "ATM Forum IMA v1.1, (O-26) in Section 12.2.2.2
--                on page 77"
--           ::= { imabLinkEntry 32 }
--
--imabLinkTimeElapsed OBJECT-TYPE
--           SYNTAX           INTEGER (0.. 899)
--           MAX-ACCESS    read-only
--           STATUS           current
--           DESCRIPTION
--              "The number of seconds that have elapsed since the beginning of
--              the current measurement period.    This attribute is only mandatory
--              when the IMA Link Current Statistics are implemented."
--           REFERENCE
--              "ATM Forum IMA v1.1, (O-26) in Section 12.2.2.2
--                on page 77"
--           ::= { imabLinkEntry 33 }

imabLinkScramble OBJECT-TYPE
	SYNTAX        INTEGER{
			disable(0),
			 enable(1)
	}
	MAX-ACCESS read-create
	STATUS current
	DESCRIPTION
		"enable/disable the scramble status of the link"
	::= { imabLinkEntry 34 }

--
--The IMA Link Current Statistics subtree
--
--The IMA Link Current Statistics subtree consists of a single table:
--the IMA Link Current Table.    This table contains various statistics
--collected by each IMA link for the current 15 minute interval.
--
--Implementation of IMA Link Current Table is optional.
--

imabLinkCurrentTable OBJECT-TYPE
           SYNTAX           SEQUENCE OF ImabLinkCurrentEntry
           MAX-ACCESS    not-accessible
           STATUS           current
           DESCRIPTION
              "The IMA Link Current table."
           ::= { zxImabLinkMibObjects 2 }

imabLinkCurrentEntry OBJECT-TYPE
           SYNTAX           ImabLinkCurrentEntry
           MAX-ACCESS    not-accessible
           STATUS           current
           DESCRIPTION
              "An entry in the IMA Link Current table."
           INDEX             { ifIndex }
           ::= { imabLinkCurrentTable 1 }

ImabLinkCurrentEntry ::= SEQUENCE {
           imabLinkCurrentImaViolations          Gauge32,
           imabLinkCurrentOifAnomalies            Gauge32,
           imabLinkCurrentNeSevErroredSecs    Gauge32,
           imabLinkCurrentFeSevErroredSecs    Gauge32,
           imabLinkCurrentNeUnavailSecs          Gauge32,
           imabLinkCurrentFeUnavailSecs          Gauge32,
           imabLinkCurrentNeTxUnusableSecs    Gauge32,
           imabLinkCurrentNeRxUnusableSecs    Gauge32,
           imabLinkCurrentFeTxUnusableSecs    Gauge32,
           imabLinkCurrentFeRxUnusableSecs    Gauge32,
           imabLinkCurrentNeTxNumFailures      Gauge32,
           imabLinkCurrentNeRxNumFailures      Gauge32,
           imabLinkCurrentFeTxNumFailures      Gauge32,
           imabLinkCurrentFeRxNumFailures      Gauge32,
           imabLinkCurrentTxStuffs                   Gauge32,
           imabLinkCurrentRxStuffs                   Gauge32 }

imabLinkCurrentImaViolations OBJECT-TYPE
           SYNTAX           Gauge32
           MAX-ACCESS    read-only
           STATUS           current
           DESCRIPTION
              "ICP violations: count of errored, invalid or missing ICP cells,
              except during SES-IMA or UAS-IMA conditions, in the current
              15 minute interval."
           REFERENCE
              "ATM Forum IMA v1.1, (R-125) and (O-26) in Section 12.2.2.2
              on page 77"
           ::= { imabLinkCurrentEntry 1 }

imabLinkCurrentOifAnomalies OBJECT-TYPE
           SYNTAX           Gauge32
           MAX-ACCESS    read-only
           STATUS           current
           DESCRIPTION
              "The number of OIF anomalies, except during SES-IMA or UAS-IMA
              conditions, at the near-end in the current 15 minute interval.
              This is an optional attribute."
           REFERENCE
              "ATM Forum IMA v1.1, (O-20) and (O-26) in Section 12.2.2.2
              on page 77"
           ::= { imabLinkCurrentEntry 2 }

imabLinkCurrentNeSevErroredSecs OBJECT-TYPE
           SYNTAX           Gauge32
           MAX-ACCESS    read-only
           STATUS           current
           DESCRIPTION
              "Count of one second intervals containing >= 30% of the ICP cells
              counted as IV-IMAs, or one or more link defects (e. g., LOS, OOF/ LOF,
              AIS, or LCD), LIF defects, or LODS defects, except during UAS-IMA
              condition, in the current 15 minute interval."
           REFERENCE
              "ATM Forum IMA v1.1, (R-126) and (O-26) in Section 12.2.2.2
              on page 77"
           ::= { imabLinkCurrentEntry 3 }

imabLinkCurrentFeSevErroredSecs OBJECT-TYPE
           SYNTAX           Gauge32
           MAX-ACCESS    read-only
           STATUS           current
           DESCRIPTION
              "Count of one second intervals containing one or more RDI-IMA
              defects, except during UAS-IMA-FE condition, in the current 15
              minute interval."
           REFERENCE
              "ATM Forum IMA v1.1, (R-127) and (O-26) in Section 12.2.2.2
              on page 77"
           ::= { imabLinkCurrentEntry 4 }

imabLinkCurrentNeUnavailSecs OBJECT-TYPE
           SYNTAX           Gauge32
           MAX-ACCESS    read-only
           STATUS           current
           DESCRIPTION
              "Count of unavailable seconds at near-end in the current 15 minute
              interval: unavailability begins at the onset of 10 contiguous
              SES-IMA and ends at the onset of 10 contiguous seconds with no
              SES-IMA."
           REFERENCE
              "ATM Forum IMA v1.1, (R-128) and (O-26) in Section 12.2.2.2
              on page 77"
           ::= { imabLinkCurrentEntry 5 }

imabLinkCurrentFeUnavailSecs OBJECT-TYPE
           SYNTAX           Gauge32
           MAX-ACCESS    read-only
           STATUS           current
           DESCRIPTION
              "Count of unavailable seconds at far-end in the current 15 minute
              interval: unavailability begins at the onset of 10 contiguous
              SES-IMA-FE and ends at the onset of 10 contiguous seconds with no
              SES-IMA-FE."
           REFERENCE
              "ATM Forum IMA v1.1, (R-129) and (O-26) in Section 12.2.2.2
              on page 77"
           ::= { imabLinkCurrentEntry 6 }

imabLinkCurrentNeTxUnusableSecs OBJECT-TYPE
           SYNTAX           Gauge32
           MAX-ACCESS    read-only
           STATUS           current
           DESCRIPTION
              "Tx Unusable seconds: count of Unusable seconds at the near-end
              Tx LSM in the current 15 minute interval."
           REFERENCE
              "ATM Forum IMA v1.1, (R-130) and (O-26) in Section 12.2.2.2
              on page 77"
           ::= { imabLinkCurrentEntry 7 }

imabLinkCurrentNeRxUnusableSecs OBJECT-TYPE
           SYNTAX           Gauge32
           MAX-ACCESS    read-only
           STATUS           current
           DESCRIPTION
              "Rx Unusable seconds: count of Unusable seconds at the near-end
              Rx LSM in the current 15 minute interval."
           REFERENCE
              "ATM Forum IMA v1.1, (R-131) and (O-26) in Section 12.2.2.2
              on page 77"
           ::= { imabLinkCurrentEntry 8 }

imabLinkCurrentFeTxUnusableSecs OBJECT-TYPE
           SYNTAX           Gauge32
           MAX-ACCESS    read-only
           STATUS           current
           DESCRIPTION
              "Tx Unusable seconds at far-end: count of seconds with Tx Unusable
              indications from the far-end Tx LSM in the current 15 minute
              interval."
           REFERENCE
              "ATM Forum IMA v1.1, (R-132) and (O-26) in Section 12.2.2.2
              on page 77"
           ::= { imabLinkCurrentEntry 9 }

imabLinkCurrentFeRxUnusableSecs OBJECT-TYPE
           SYNTAX           Gauge32
           MAX-ACCESS    read-only
           STATUS           current
           DESCRIPTION
              "Rx Unusable seconds at far-end: count of seconds with Rx Unusable
              indications from the far-end Rx LSM in the current 15 minute
              interval."
           REFERENCE
              "ATM Forum IMA v1.1, (R-133) and (O-26) in Section 12.2.2.2
              on page 77"
           ::= { imabLinkCurrentEntry 10 }

imabLinkCurrentNeTxNumFailures OBJECT-TYPE
           SYNTAX           Gauge32
           MAX-ACCESS    read-only
           STATUS           current
           DESCRIPTION
              "The number of times a near-end transmit failure alarm condition
              has been entered on this link (i. e., some form of implementation
              specific transmit fault) in the current 15 minute interval."
           REFERENCE
              "ATM Forum IMA v1.1, (R-134) and (O-26) in Section 12.2.2.2
              on page 77"
           ::= { imabLinkCurrentEntry 11 }

imabLinkCurrentNeRxNumFailures OBJECT-TYPE
           SYNTAX           Gauge32
           MAX-ACCESS    read-only
           STATUS           current
           DESCRIPTION
              "The number of times a near-end receive failure alarm condition
              has been entered on this link (i. e., LIF, LODS, RFI-IMA, Mis-Connected,
              or some form of implementation specific receive fault)
              in the current 15 minute interval."
           REFERENCE
              "ATM Forum IMA v1.1, (R-135) and (O-26) in Section 12.2.2.2
              on page 77"
           ::= { imabLinkCurrentEntry 12 }

imabLinkCurrentFeTxNumFailures OBJECT-TYPE
           SYNTAX           Gauge32
           MAX-ACCESS    read-only
           STATUS           current
           DESCRIPTION
              "The number of times a far-end transmit failure alarm condition
              has been entered on this link (i. e., Tx-Unusable-FE) in the
              current 15 minute interval.    This is an optional attribute."
           REFERENCE
              "ATM Forum IMA v1.1, (O-21) and (O-26) in Section 12.2.2.2
              on page 77"
           ::= { imabLinkCurrentEntry 13 }

imabLinkCurrentFeRxNumFailures OBJECT-TYPE
           SYNTAX           Gauge32
           MAX-ACCESS    read-only
           STATUS           current
           DESCRIPTION
              "The number of times a far-end receive failure alarm condition
              has been entered on this link (i. e., Rx-Unusable-FE) in the
              current 15 minute interval.    This is an optional attribute."
           REFERENCE
              "ATM Forum IMA v1.1, (O-22) and (O-26) in Section 12.2.2.2
              on page 77"
           ::= { imabLinkCurrentEntry 14 }

imabLinkCurrentTxStuffs OBJECT-TYPE
           SYNTAX           Gauge32
           MAX-ACCESS    read-only
           STATUS           current
           DESCRIPTION
              "Count of stuff events inserted in the transmit direction in
              the current 15 minute interval.    This is an optional attribute."
           REFERENCE
              "ATM Forum IMA v1.1, (O-23) and (O-26) in Section 12.2.2.2
              on page 77"
           ::= { imabLinkCurrentEntry 15 }

imabLinkCurrentRxStuffs OBJECT-TYPE
           SYNTAX           Gauge32
           MAX-ACCESS    read-only
           STATUS           current
           DESCRIPTION
              "Count of stuff events detected in the receive direction in
              the current 15 minute interval.    This is an optional attribute."
           REFERENCE
              "ATM Forum IMA v1.1, (O-24) and (O-26) in Section 12.2.2.2
              on page 77"
           ::= { imabLinkCurrentEntry 16 }

--
--The IMA Link Interval Statistics subtree
--
--The IMA Link Interval Statistics subtree consists of a single table:
--the IMA Link Interval Table.    This table contains various statistics
--collected by each IMA link over the previous 24 hours of operation.
--The past 24 hours are broken into 96 completed 15 minute intervals.
--
--Implementation of IMA Link Interval Table is optional.
--

imabLinkIntervalTable OBJECT-TYPE
           SYNTAX           SEQUENCE OF ImabLinkIntervalEntry
           MAX-ACCESS    not-accessible
           STATUS           current
           DESCRIPTION
              "The IMA Link Interval table."
           ::= { zxImabLinkMibObjects 3 }

imabLinkIntervalEntry OBJECT-TYPE
           SYNTAX           ImabLinkIntervalEntry
           MAX-ACCESS    not-accessible
           STATUS           current
           DESCRIPTION
              "An entry in the IMA Link Interval table."
           INDEX             { ifIndex, imabLinkIntervalNumber }
           ::= { imabLinkIntervalTable 1 }

ImabLinkIntervalEntry ::= SEQUENCE {
           imabLinkIntervalNumber                      INTEGER (1.. 96),
           imabLinkIntervalImaViolations          Gauge32,
           imabLinkIntervalOifAnomalies            Gauge32,
           imabLinkIntervalNeSevErroredSecs    Gauge32,
           imabLinkIntervalFeSevErroredSecs    Gauge32,
           imabLinkIntervalNeUnavailSecs          Gauge32,
           imabLinkIntervalFeUnavailSecs          Gauge32,
           imabLinkIntervalNeTxUnusableSecs    Gauge32,
           imabLinkIntervalNeRxUnusableSecs    Gauge32,
           imabLinkIntervalFeTxUnusableSecs    Gauge32,
           imabLinkIntervalFeRxUnusableSecs    Gauge32,
           imabLinkIntervalNeTxNumFailures      Gauge32,
           imabLinkIntervalNeRxNumFailures      Gauge32,
           imabLinkIntervalFeTxNumFailures      Gauge32,
           imabLinkIntervalFeRxNumFailures      Gauge32,
           imabLinkIntervalTxStuffs                   Gauge32,
           imabLinkIntervalRxStuffs                   Gauge32 }

imabLinkIntervalNumber OBJECT-TYPE
           SYNTAX            INTEGER (1.. 96)
           MAX-ACCESS    not-accessible
           STATUS           current
           DESCRIPTION
              "A number between 1 and 96, where 1 is the most
                recently completed 15 minute interval and 96 is the least
                recently completed 15 minutes interval (assuming that all
                96 intervals are valid)."
           ::= { imabLinkIntervalEntry 1 }

imabLinkIntervalImaViolations OBJECT-TYPE
           SYNTAX           Gauge32
           MAX-ACCESS    read-only
           STATUS           current
           DESCRIPTION
              "ICP violations: count of errored, invalid or missing ICP cells,
              except during SES-IMA or UAS-IMA conditions, in one of the
              previous 96, individual 15 minute, intervals."
           REFERENCE
              "ATM Forum IMA v1.1, (R-125) and (O-26) in Section 12.2.2.2
              on page 77"
           ::= { imabLinkIntervalEntry 2 }

imabLinkIntervalOifAnomalies OBJECT-TYPE
           SYNTAX           Gauge32
           MAX-ACCESS    read-only
           STATUS           current
           DESCRIPTION
              "The number of OIF anomalies, except during SES-IMA or UAS-IMA
              conditions, at the near-end in one of the previous 96, individual
              15 minute, intervals.    This is an optional attribute."
           REFERENCE
              "ATM Forum IMA v1.1, (O-20) and (O-26) in Section 12.2.2.2
              on page 77"
           ::= { imabLinkIntervalEntry 3 }

imabLinkIntervalNeSevErroredSecs OBJECT-TYPE
           SYNTAX           Gauge32
           MAX-ACCESS    read-only
           STATUS           current
           DESCRIPTION
              "Count of one second intervals containing >= 30% of the ICP cells
              counted as IV-IMAs, or one or more link defects (e. g., LOS, OOF/ LOF,
              AIS, or LCD), LIF defects, or LODS defects, except during UAS-IMA
              condition, in one of the previous 96, individual 15 minute,
              intervals."
           REFERENCE
              "ATM Forum IMA v1.1, (R-126) and (O-26) in Section 12.2.2.2
              on page 77"
           ::= { imabLinkIntervalEntry 4 }

imabLinkIntervalFeSevErroredSecs OBJECT-TYPE
           SYNTAX           Gauge32
           MAX-ACCESS    read-only
           STATUS           current
           DESCRIPTION
              "Count of one second intervals containing one or more RDI-IMA
              defects, except during UAS-IMA-FE condition, in one of the previous
              96, individual 15 minute, intervals."
           REFERENCE
              "ATM Forum IMA v1.1, (R-127) and (O-26) in Section 12.2.2.2
              on page 77"
           ::= { imabLinkIntervalEntry 5 }

imabLinkIntervalNeUnavailSecs OBJECT-TYPE
           SYNTAX           Gauge32
           MAX-ACCESS    read-only
           STATUS           current
           DESCRIPTION
              "Count of unavailable seconds at near-end in one of the previous
              96, individual 15 minute, intervals: unavailability begins at the
              onset of 10 contiguous SES-IMA and ends at the onset of 10
              contiguous seconds with no SES-IMA."
           REFERENCE
              "ATM Forum IMA v1.1, (R-128) and (O-26) in Section 12.2.2.2
              on page 77"
           ::= { imabLinkIntervalEntry 6 }

imabLinkIntervalFeUnavailSecs OBJECT-TYPE
           SYNTAX           Gauge32
           MAX-ACCESS    read-only
           STATUS           current
           DESCRIPTION
              "Count of unavailable seconds at far-end in one of the previous
              96, individual 15 minute, intervals: unavailability begins at the
              onset of 10 contiguous SES-IMA-FE and ends at the onset of 10
              contiguous seconds with no SES-IMA-FE."
           REFERENCE
              "ATM Forum IMA v1.1, (R-129) and (O-26) in Section 12.2.2.2
              on page 77"
           ::= { imabLinkIntervalEntry 7 }

imabLinkIntervalNeTxUnusableSecs OBJECT-TYPE
           SYNTAX           Gauge32
           MAX-ACCESS    read-only
           STATUS           current
           DESCRIPTION
              "Tx Unusable seconds: count of Unusable seconds at the near-end
              Tx LSM in one of the previous 96, individual 15 minute, intervals."
           REFERENCE
              "ATM Forum IMA v1.1, (R-130) and (O-26) in Section 12.2.2.2
              on page 77"
           ::= { imabLinkIntervalEntry 8 }

imabLinkIntervalNeRxUnusableSecs OBJECT-TYPE
           SYNTAX           Gauge32
           MAX-ACCESS    read-only
           STATUS           current
           DESCRIPTION
              "Rx Unusable seconds: count of Unusable seconds at the near-end
              Rx LSM in one of the previous 96, individual 15 minute, intervals."
           REFERENCE
              "ATM Forum IMA v1.1, (R-131) and (O-26) in Section 12.2.2.2
              on page 77"
           ::= { imabLinkIntervalEntry 9 }

imabLinkIntervalFeTxUnusableSecs OBJECT-TYPE
           SYNTAX           Gauge32
           MAX-ACCESS    read-only
           STATUS           current
           DESCRIPTION
              "Tx Unusable seconds at far-end: count of seconds with Tx Unusable
              indications from the far-end Tx LSM in one of the previous 96,
              individual 15 minute, intervals."
           REFERENCE
              "ATM Forum IMA v1.1, (R-132) and (O-26) in Section 12.2.2.2
              on page 77"
           ::= { imabLinkIntervalEntry 10 }

imabLinkIntervalFeRxUnusableSecs OBJECT-TYPE
           SYNTAX           Gauge32
           MAX-ACCESS    read-only
           STATUS           current
           DESCRIPTION
              "Rx Unusable seconds at far-end: count of seconds with Rx Unusable
              indications from the far-end Rx LSM in one of the previous 96,
              individual 15 minute, intervals."
           REFERENCE
              "ATM Forum IMA v1.1, (R-133) and (O-26) in Section 12.2.2.2
              on page 77"
           ::= { imabLinkIntervalEntry 11 }

imabLinkIntervalNeTxNumFailures OBJECT-TYPE
           SYNTAX           Gauge32
           MAX-ACCESS    read-only
           STATUS           current
           DESCRIPTION
              "The number of times a near-end transmit failure alarm condition
              has been entered on this link (i. e., some form of implementation
              specific transmit fault) in one of the previous 96, individual
              15 minute, intervals."
           REFERENCE
              "ATM Forum IMA v1.1, (R-134) and (O-26) in Section 12.2.2.2
              on page 77"
           ::= { imabLinkIntervalEntry 12 }

imabLinkIntervalNeRxNumFailures OBJECT-TYPE
           SYNTAX           Gauge32
           MAX-ACCESS    read-only
           STATUS           current
           DESCRIPTION
              "The number of times a near-end receive failure alarm condition
              has been entered on this link (i. e., LIF, LODS, RFI-IMA,
              Mis-Connected, or some form of implementation specific
              receive fault) in one of the previous 96, individual 15 minute,
              intervals."
           REFERENCE
              "ATM Forum IMA v1.1, (R-135) and (O-26) in Section 12.2.2.2
              on page 77"
           ::= { imabLinkIntervalEntry 13 }

imabLinkIntervalFeTxNumFailures OBJECT-TYPE
           SYNTAX           Gauge32
           MAX-ACCESS    read-only
           STATUS           current
           DESCRIPTION
              "The number of times a far-end transmit failure alarm condition
              has been entered on this link (i. e., Tx-Unusable-FE) in one of the
              previous 96, individual 15 minute, intervals.    This is an optional
              attribute."
           REFERENCE
              "ATM Forum IMA v1.1, (O-21) and (O-26) in Section 12.2.2.2
              on page 77"
           ::= { imabLinkIntervalEntry 14 }

imabLinkIntervalFeRxNumFailures OBJECT-TYPE
           SYNTAX           Gauge32
           MAX-ACCESS    read-only
           STATUS           current
           DESCRIPTION
              "The number of times a far-end receive failure alarm condition
              has been entered on this link (i. e., Rx-Unusable-FE) in one of
              the previous 96, individual 15 minute, intervals.    This is an
              optional attribute."
           REFERENCE
              "ATM Forum IMA v1.1, (O-22) and (O-26) in Section 12.2.2.2
              on page 77"
           ::= { imabLinkIntervalEntry 15 }

imabLinkIntervalTxStuffs OBJECT-TYPE
           SYNTAX           Gauge32
           MAX-ACCESS    read-only
           STATUS           current
           DESCRIPTION
              "Count of stuff events inserted in the transmit direction in
              one of the previous 96, individual 15 minute, intervals.    This
              is an optional attribute."
           REFERENCE
              "ATM Forum IMA v1.1, (O-23) and (O-26) in Section 12.2.2.2
              on page 77"
           ::= { imabLinkIntervalEntry 16 }

imabLinkIntervalRxStuffs OBJECT-TYPE
           SYNTAX           Gauge32
           MAX-ACCESS    read-only
           STATUS           current
           DESCRIPTION
              "Count of stuff events detected in the receive direction in
              one of the previous 96, individual 15 minute, intervals.    This
              is an optional attribute."
           REFERENCE
              "ATM Forum IMA v1.1, (O-24) and (O-26) in Section 12.2.2.2
              on page 77"
           ::= { imabLinkIntervalEntry 17 }

--
--The IMA Link Total Statistics subtree
--
--The IMA Link Total Statistics subtree consists of a single table:
--the IMA Link Total Table.    This table contains the cumulative sum
--of the various statistics collected by each IMA link for the 24 hour
--period preceding the current interval.
--
--Implementation of IMA Link Total Table is optional.
--

imabLinkTotalTable OBJECT-TYPE
           SYNTAX           SEQUENCE OF ImabLinkTotalEntry
           MAX-ACCESS    not-accessible
           STATUS           current
           DESCRIPTION
              "The IMA Link Total table."
           ::= { zxImabLinkMibObjects 4 }

imabLinkTotalEntry OBJECT-TYPE
           SYNTAX           ImabLinkTotalEntry
           MAX-ACCESS    not-accessible
           STATUS           current
           DESCRIPTION
              "An entry in the IMA Link Total table."
           INDEX             { ifIndex }
           ::= { imabLinkTotalTable 1 }

ImabLinkTotalEntry ::= SEQUENCE {
           imabLinkTotalImaViolations          Gauge32,
           imabLinkTotalOifAnomalies            Gauge32,
           imabLinkTotalNeSevErroredSecs    Gauge32,
           imabLinkTotalFeSevErroredSecs    Gauge32,
           imabLinkTotalNeUnavailSecs          Gauge32,
           imabLinkTotalFeUnavailSecs          Gauge32,
           imabLinkTotalNeTxUnusableSecs    Gauge32,
           imabLinkTotalNeRxUnusableSecs    Gauge32,
           imabLinkTotalFeTxUnusableSecs    Gauge32,
           imabLinkTotalFeRxUnusableSecs    Gauge32,
           imabLinkTotalNeTxNumFailures      Gauge32,
           imabLinkTotalNeRxNumFailures      Gauge32,
           imabLinkTotalFeTxNumFailures      Gauge32,
           imabLinkTotalFeRxNumFailures      Gauge32,
           imabLinkTotalTxStuffs                   Gauge32,
           imabLinkTotalRxStuffs                   Gauge32 }

imabLinkTotalImaViolations OBJECT-TYPE
           SYNTAX           Gauge32
           MAX-ACCESS    read-only
           STATUS           current
           DESCRIPTION
              "ICP violations: count of errored, invalid or missing ICP cells,
              except during SES-IMA or UAS-IMA conditions, in the previous 24
              hour interval.    Invalid 15 minute intervals count as 0."
           REFERENCE
              "ATM Forum IMA v1.1, (R-125) and (O-27) in Section 12.2.2.2
              on page 77"
           ::= { imabLinkTotalEntry 1 }

imabLinkTotalOifAnomalies OBJECT-TYPE
           SYNTAX           Gauge32
           MAX-ACCESS    read-only
           STATUS           current
           DESCRIPTION
              "The number of OIF anomalies, except during SES-IMA or UAS-IMA
              conditions, at the near-end in the previous 24 hour interval.
              Invalid 15 minute intervals count as 0.    This is an optional
              attribute."
           REFERENCE
              "ATM Forum IMA v1.1, (O-20) and (O-27) in Section 12.2.2.2
              on page 77"
           ::= { imabLinkTotalEntry 2 }

imabLinkTotalNeSevErroredSecs OBJECT-TYPE
           SYNTAX           Gauge32
           MAX-ACCESS    read-only
           STATUS           current
           DESCRIPTION
              "Count of one second intervals containing >= 30% of the ICP cells
              counted as IV-IMAs, or one or more link defects (e. g., LOS, OOF/ LOF,
              AIS, or LCD), LIF defects, or LODS defects, except during UAS-IMA
              condition, in the previous 24 hour interval.    Invalid 15 minute
              intervals count as 0."
           REFERENCE
              "ATM Forum IMA v1.1, (R-126) and (O-27) in Section 12.2.2.2
              on page 77"
           ::= { imabLinkTotalEntry 3 }

imabLinkTotalFeSevErroredSecs OBJECT-TYPE
           SYNTAX           Gauge32
           MAX-ACCESS    read-only
           STATUS           current
           DESCRIPTION
              "Count of one second intervals containing one or more RDI-IMA
              defects, except during UAS-IMA-FE condition, in the previous 24
              hour interval.    Invalid 15 minute intervals count as 0."
           REFERENCE
              "ATM Forum IMA v1.1, (R-127) and (O-27) in Section 12.2.2.2
              on page 77"
           ::= { imabLinkTotalEntry 4 }

imabLinkTotalNeUnavailSecs OBJECT-TYPE
           SYNTAX           Gauge32
           MAX-ACCESS    read-only
           STATUS           current
           DESCRIPTION
              "Count of unavailable seconds at near-end in the previous 24 hour
              interval: unavailability begins at the onset of 10 contiguous
              SES-IMA and ends at the onset of 10 contiguous seconds with no
              SES-IMA.    Invalid 15 minute intervals count as 0."
           REFERENCE
              "ATM Forum IMA v1.1, (R-128) and (O-27) in Section 12.2.2.2
              on page 77"
           ::= { imabLinkTotalEntry 5 }

imabLinkTotalFeUnavailSecs OBJECT-TYPE
           SYNTAX           Gauge32
           MAX-ACCESS    read-only
           STATUS           current
           DESCRIPTION
              "Count of unavailable seconds at far-end in the previous 24 hour
              interval: unavailability begins at the onset of 10 contiguous
              SES-IMA-FE and ends at the onset of 10 contiguous seconds with no
              SES-IMA-FE.    Invalid 15 minute intervals count as 0."
           REFERENCE
              "ATM Forum IMA v1.1, (R-129) and (O-27) in Section 12.2.2.2
              on page 77"
           ::= { imabLinkTotalEntry 6 }

imabLinkTotalNeTxUnusableSecs OBJECT-TYPE
           SYNTAX           Gauge32
           MAX-ACCESS    read-only
           STATUS           current
           DESCRIPTION
              "Tx Unusable seconds: count of Unusable seconds at the near-end
              Tx LSM in the previous 24 hour interval.    Invalid 15 minute
              intervals count as 0."
           REFERENCE
              "ATM Forum IMA v1.1, (R-130) and (O-27) in Section 12.2.2.2
              on page 77"
           ::= { imabLinkTotalEntry 7 }

imabLinkTotalNeRxUnusableSecs OBJECT-TYPE
           SYNTAX           Gauge32
           MAX-ACCESS    read-only
           STATUS           current
           DESCRIPTION
              "Rx Unusable seconds: count of Unusable seconds at the near-end
              Rx LSM in the previous 24 hour interval.    Invalid 15 minute
              intervals count as 0."
           REFERENCE
              "ATM Forum IMA v1.1, (R-131) and (O-27) in Section 12.2.2.2
              on page 77"
           ::= { imabLinkTotalEntry 8 }

imabLinkTotalFeTxUnusableSecs OBJECT-TYPE
           SYNTAX           Gauge32
           MAX-ACCESS    read-only
           STATUS           current
           DESCRIPTION
              "Tx Unusable seconds at far-end: count of seconds with Tx Unusable
              indications from the far-end Tx LSM in the previous 24 hour
              interval.    Invalid 15 minute intervals count as 0."
           REFERENCE
              "ATM Forum IMA v1.1, (R-132) and (O-27) in Section 12.2.2.2
              on page 77"
           ::= { imabLinkTotalEntry 9 }

imabLinkTotalFeRxUnusableSecs OBJECT-TYPE
           SYNTAX           Gauge32
           MAX-ACCESS    read-only
           STATUS           current
           DESCRIPTION
              "Rx Unusable seconds at far-end: count of seconds with Rx Unusable
              indications from the far-end Rx LSM in the previous 24 hour
              interval.    Invalid 15 minute intervals count as 0."
           REFERENCE
              "ATM Forum IMA v1.1, (R-133) and (O-27) in Section 12.2.2.2
              on page 77"
           ::= { imabLinkTotalEntry 10 }

imabLinkTotalNeTxNumFailures OBJECT-TYPE
           SYNTAX           Gauge32
           MAX-ACCESS    read-only
           STATUS           current
           DESCRIPTION
              "The number of times a near-end transmit failure alarm condition
              has been entered on this link (i. e., some form of implementation
              specific transmit fault) in the previous 24 hour interval.
              Invalid 15 minute intervals count as 0."
           REFERENCE
              "ATM Forum IMA v1.1, (R-134) and (O-27) in Section 12.2.2.2
              on page 77"
           ::= { imabLinkTotalEntry 11 }

imabLinkTotalNeRxNumFailures OBJECT-TYPE
           SYNTAX           Gauge32
           MAX-ACCESS    read-only
           STATUS           current
           DESCRIPTION
              "The number of times a near-end receive failure alarm condition
              has been entered on this link (i. e., LIF, LODS, RFI-IMA,
              Mis-Connected, or some form of implementation specific receive fault)
              in the previous 24 hour interval. Invalid 15 minute intervals
              count as 0."
           REFERENCE
              "ATM Forum IMA v1.1, (R-135) and (O-27) in Section 12.2.2.2
              on page 77"
           ::= { imabLinkTotalEntry 12 }

imabLinkTotalFeTxNumFailures OBJECT-TYPE
           SYNTAX           Gauge32
           MAX-ACCESS    read-only
           STATUS           current
           DESCRIPTION
              "The number of times a far-end transmit failure alarm condition
              has been entered on this link (i. e., Tx-Unusable-FE) in the
              previous 24 hour interval.    Invalid 15 minute intervals count
              as 0.    This is an optional attribute."
           REFERENCE
              "ATM Forum IMA v1.1, (O-21) and (O-27) in Section 12.2.2.2
              on page 77"
           ::= { imabLinkTotalEntry 13 }

imabLinkTotalFeRxNumFailures OBJECT-TYPE
           SYNTAX           Gauge32
           MAX-ACCESS    read-only
           STATUS           current
           DESCRIPTION
              "The number of times a far-end receive failure alarm condition
              has been entered on this link (i. e., Rx-Unusable-FE) in the
              previous 24 hour interval.    Invalid 15 minute intervals count
              as 0.    This is an optional attribute."
           REFERENCE
              "ATM Forum IMA v1.1, (O-22) and (O-27) in Section 12.2.2.2
              on page 77"
           ::= { imabLinkTotalEntry 14 }

imabLinkTotalTxStuffs OBJECT-TYPE
           SYNTAX           Gauge32
           MAX-ACCESS    read-only
           STATUS           current
           DESCRIPTION
              "Count of stuff events inserted in the transmit direction in
              the previous 24 hour interval.    Invalid 15 minute intervals
              count as 0.    This is an optional attribute."
           REFERENCE
              "ATM Forum IMA v1.1, (O-23) and (O-27) in Section 12.2.2.2
              on page 77"
           ::= { imabLinkTotalEntry 15 }

imabLinkTotalRxStuffs OBJECT-TYPE
           SYNTAX           Gauge32
           MAX-ACCESS    read-only
           STATUS           current
           DESCRIPTION
              "Count of stuff events detected in the receive direction in
              the previous 24 hour interval.    Invalid 15 minute intervals
              count as 0.    This is an optional attribute."
           REFERENCE
              "ATM Forum IMA v1.1, (O-24) and (O-27) in Section 12.2.2.2
              on page 77"
           ::= { imabLinkTotalEntry 16 }

--Conformance Information
--Compliance Statements

imabLinkGroup OBJECT-GROUP
           OBJECTS {
              imabLinkRowStatus,
              imabLinkGroupIndex,
              imabLinkNeTxState,
              imabLinkNeRxState,
              imabLinkFeTxState,
              imabLinkFeRxState,
              imabLinkNeRxFailureStatus,
              imabLinkFeRxFailureStatus,
              imabLinkTxLid,
              imabLinkRxLid,
              imabLinkRelDelay,
              imabLinkImaViolations,
              imabLinkOifAnomalies,
              imabLinkNeSevErroredSecs,
              imabLinkFeSevErroredSecs,
              imabLinkNeUnavailSecs,
              imabLinkFeUnavailSecs,
              imabLinkNeTxUnusableSecs,
              imabLinkNeRxUnusableSecs,
              imabLinkFeTxUnusableSecs,
              imabLinkFeRxUnusableSecs,
              imabLinkNeTxNumFailures,
              imabLinkNeRxNumFailures,
              imabLinkFeTxNumFailures,
              imabLinkFeRxNumFailures,
              imabLinkTxStuffs,
              imabLinkRxStuffs,
	      imabLinkScramble }
           STATUS          current
           DESCRIPTION
              "A set of objects providing status information for an IMA link."
           ::= { zxImabLinkMibGroups 1 }

 imabLinkTestPatternGroup OBJECT-GROUP
           OBJECTS {
              imabLinkRxTestPattern,
              imabLinkTestProcStatus }
           STATUS          current
           DESCRIPTION
              "Objects in the imaGroupTable and imaLinkTable which control and
              report on the Test Pattern Procedure.    These objects must be
              implemented if the IMA Test Pattern Procedure is supported."
           ::= { zxImabLinkMibGroups 2 }

imabLinkIntervalGroup OBJECT-GROUP
           OBJECTS {
              imabLinkValidIntervals,
              imabLinkInvalidIntervals,
              imabLinkTimeElapsed,
              imabLinkCurrentImaViolations,
              imabLinkCurrentOifAnomalies,
              imabLinkCurrentNeSevErroredSecs,
              imabLinkCurrentFeSevErroredSecs,
              imabLinkCurrentNeUnavailSecs,
              imabLinkCurrentFeUnavailSecs,
              imabLinkCurrentNeTxUnusableSecs,
              imabLinkCurrentNeRxUnusableSecs,
              imabLinkCurrentFeTxUnusableSecs,
              imabLinkCurrentFeRxUnusableSecs,
              imabLinkCurrentNeTxNumFailures,
              imabLinkCurrentNeRxNumFailures,
              imabLinkCurrentFeTxNumFailures,
              imabLinkCurrentFeRxNumFailures,
              imabLinkCurrentTxStuffs,
              imabLinkCurrentRxStuffs,
              imabLinkIntervalImaViolations,
              imabLinkIntervalOifAnomalies,
              imabLinkIntervalNeSevErroredSecs,
              imabLinkIntervalFeSevErroredSecs,
              imabLinkIntervalNeUnavailSecs,
              imabLinkIntervalFeUnavailSecs,
              imabLinkIntervalNeTxUnusableSecs,
              imabLinkIntervalNeRxUnusableSecs,
              imabLinkIntervalFeTxUnusableSecs,
              imabLinkIntervalFeRxUnusableSecs,
              imabLinkIntervalNeTxNumFailures,
              imabLinkIntervalNeRxNumFailures,
              imabLinkIntervalFeTxNumFailures,
              imabLinkIntervalFeRxNumFailures,
              imabLinkIntervalTxStuffs,
              imabLinkIntervalRxStuffs,
              imabLinkTotalimaViolations,
              imabLinkTotalOifAnomalies,
              imabLinkTotalNeSevErroredSecs,
              imabLinkTotalFeSevErroredSecs,
              imabLinkTotalNeUnavailSecs,
              imabLinkTotalFeUnavailSecs,
              imabLinkTotalNeTxUnusableSecs,
              imabLinkTotalNeRxUnusableSecs,
              imabLinkTotalFeTxUnusableSecs,
              imabLinkTotalFeRxUnusableSecs,
              imabLinkTotalNeTxNumFailures,
              imabLinkTotalNeRxNumFailures,
              imabLinkTotalFeTxNumFailures,
              imabLinkTotalFeRxNumFailures,
              imabLinkTotalTxStuffs,
              imabLinkTotalRxStuffs }
           STATUS          current
           DESCRIPTION
              "Objects containing interval statistics for an IMA link."
           ::= { zxImabLinkMibGroups 3 }

zxImabLinkMibCompliance MODULE-COMPLIANCE
    STATUS  current
    DESCRIPTION
           "The compliance statement."
    MODULE  -- this module
    MANDATORY-GROUPS{
            imabLinkGroup,
            imabLinkTestPatternGroup,
            imabLinkIntervalGroup
            }
        ::= { zxImabLinkMibCompliances 1 }

END
IMAB-SYS-MIB DEFINITIONS ::= BEGIN

IMPORTS
           MODULE-IDENTITY, OBJECT-TYPE, Integer32, Counter32, Gauge32,
           NOTIFICATION-TYPE, enterprises
              FROM SNMPv2-SMI
           MODULE-COMPLIANCE, OBJECT-GROUP, NOTIFICATION-GROUP
              FROM SNMPv2-CONF
           TEXTUAL-CONVENTION, DateAndTime, RowStatus
              FROM SNMPv2-TC
           InterfaceIndex, InterfaceIndexOrZero, ifIndex
              FROM IF-MIB;
              
zxImabSysMib MODULE-IDENTITY
           LAST-UPDATED "9902111830Z"
           ORGANIZATION "The ATM Forum"
           CONTACT-INFO
              "ATM Forum
              World Headquarters
              2570 West El Camino Real
              Suite 304
              Mountain View, CA 94040-1313
              USA
              Phone: +1 415 949 6700
              Fax: +1 415 949 6705
              email: info@ atmforum. com"
           DESCRIPTION
              "The MIB module for managing ATM Forum Inverse Multiplexing
              for ATM (IMA) interfaces."
           REVISION          "9902111830Z"
           DESCRIPTION
              "Updated and repaired version of the IMA-MIB released with the
              IMA v1.1 specification (af-phy-0086.001)."
           REVISION          "9701092245Z"
           DESCRIPTION
              "Initial incomplete version of the IMA-MIB as published in the
              IMA v1.0 specification (af-phy-0086.000)."
           ::= { zxIma 4 }

zte OBJECT IDENTIFIER ::= { enterprises 3902 }
zxDsl OBJECT IDENTIFIER ::= { zte 1004 }
zxDslam OBJECT IDENTIFIER ::= { zxDsl 1 }
zxIma	OBJECT IDENTIFIER ::= { zxDslam 11 }

zxImabSysMibObjects OBJECT IDENTIFIER ::= { zxImabSysMib 1 }
zxImabTrap          OBJECT IDENTIFIER ::= { zxImabSysMib 2 }
zxImabSysMibConformance OBJECT IDENTIFIER ::= { zxImabSysMib 3 }
zxImabSysMibTrapPrefix OBJECT IDENTIFIER ::= { zxImabTrap 0 }

zxImabSysMibGroups OBJECT IDENTIFIER ::= { zxImabSysMibConformance 1 }
zxImabSysMibCompliances OBJECT IDENTIFIER ::= { zxImabSysMibConformance 2 }

---IMA common definition.

imabVersionNumber OBJECT-TYPE
	SYNTAX INTEGER
	MAX-ACCESS read-only
	STATUS current
	DESCRIPTION
		"the ima version ,which is from version head structure of 'ver.bin' "
::= { zxImabSysMibObjects 1 }

imabMaxSupportedGroupNumber OBJECT-TYPE
	SYNTAX Integer32
	MAX-ACCESS read-only
	STATUS current
	DESCRIPTION
		"The max number of IMA groups supported in this system
	the default value:16 "
::= { zxImabSysMibObjects 2 }

imabMaxSupportedLinkNumber OBJECT-TYPE
	SYNTAX Integer32
	MAX-ACCESS read-only
	STATUS current
	DESCRIPTION
		"The max number of IMA Links supported in this system
	the default value:16 "
::= { zxImabSysMibObjects 3 }

imabDataManagementCmd OBJECT-TYPE
        SYNTAX INTEGER {
               noop(1),           -- no operation
               save(2),           -- save all configuration parameters to NVM
               saveInProgress(3),  -- read-only: NVM save in progress
               clear(4),		 --  clear all configuration parameters in NVM
               clearInProgress(5),   -- read-only: clear NVM is in progressing
               reset(6)
        }
        MAX-ACCESS read-write
        STATUS current
        DESCRIPTION
            "When set to 'save(2)', all nonvolatile configuration
             parameters are saved to NVM (Nonvolatile Memory).  NVM save
             operations may be slow (e.g., erasing/writing Flash device).
             Consequently, all or many updates should be made before
             saving to NVM.  Note that the SNMP set to 'save(2)' returns
             immediately to the caller.  Gets on this object then return
             'saveInProgress(3)' until the save operation completes, at
             which time 'noop(1)' is returned.  Consequently, a get
             operation always returns 'noop(1)' or 'saveInProgress(3)'
             depending on the current state.

             When set to 'clear(4)', all configuration parameters in NVM will cleared,
             system data return back to 'no config' state. when clear NVM data, this scalar 
             is set to 'clearInProgress(5)' to forbid 'save' or 'clear' command by others.
             
             The agent returns 'badValue' for SNMPv1 or 'inconsistentValue'
             for SNMPv2c/v3 for a set to 'Save(2)' while the current get
             state is 'saveInProgress(3)'.
             
             Attempts to set this object to 'saveInProgress(3)' returns
             'badValue' for SNMPv1 or 'wrongValue' for SNMPv2c/v3. "
             
        ::= { zxImabSysMibObjects 4 }
        
imabSlotID OBJECT-TYPE
	SYNTAX Integer32
	MAX-ACCESS read-only
	STATUS current
	DESCRIPTION
		"the slot id of ima in the dislam  "
::= { zxImabSysMibObjects 5 }

imabAlarmStatus OBJECT-TYPE
	SYNTAX  INTEGER {
		cleared(1),
		declared(2) }
	MAX-ACCESS accessible-for-notify
	STATUS current
	DESCRIPTION
		"Status of the IMA alarm."
::= { zxImabSysMibObjects 6 }

imabAlarmType OBJECT-TYPE
           SYNTAX        INTEGER {
                   ima_EVT_LNK_LIF(1),
  								 ima_EVT_LNK_LODS(2),
  								 ima_EVT_LNK_RFI(3),
  								 ima_EVT_LNK_TX_MISC(4),
  								 ima_EVT_LNK_FAULT(7),
  								 ima_EVT_LNK_TX_UUS_FE(8),
  								 ima_EVT_LNK_RX_UUS_FE(9)  
           }
           MAX-ACCESS    accessible-for-notify
           STATUS        current
           DESCRIPTION
              "The Type of IMA alarm declared or cleared.    The value of
              ImaAlarmType identifies the type of alarm according to the
              definitions in the IMA specification."
           REFERENCE
              "ATM Forum IMA v1.1, Section 12.2.3 on page 79"
            ::= { zxImabSysMibObjects 7 }

imabFailureAlarm NOTIFICATION-TYPE
           OBJECTS {
              ifIndex,
              imaAlarmStatus,
              imaAlarmType }
           STATUS           current
           DESCRIPTION
              "The imaFailureAlarm provides a method for an agent implementing IMA
              to notify an NMS of an alarm condition."
           REFERENCE
              "ATM Forum IMA v1.1, Section 12.2.3 on page 79"
           ::= { zxImabSysMibTrapPrefix 1 }

--Conformance Information
imabCommonGroup OBJECT-GROUP
           OBJECTS {
	      imabVersionNumber,
              imabMaxSupportedGroupNumber,
              imabMaxSupportedLinkNumber,
              imabDataManagementCmd,
              imabSlotID,
              imabAlarmStatus,
              imabAlarmType,
              imabFailureAlarm
              }
           STATUS          current
           DESCRIPTION
              "Objects used in System Cotrol and common information group."
           ::= { zxImabSysMibGroups 1 }

 zxImabSysMibCompliance MODULE-COMPLIANCE
    STATUS  current
    DESCRIPTION
           "The compliance statement."
    MODULE  -- this module
    MANDATORY-GROUPS{
            imabCommonGroup
            }
        ::= { zxImabSysMibCompliances 1 }

END

------------------------------------------------------------------------------

--  IMAB END
------------------------------------------------------------------------------

------------------------------------------------------------------------------
------------------------------------------------------------------------------
--
--  File         : galnet-oem.mib
--  Description  : Sample TMS OEM Product Enterprise MIB for 
--                 Galileo Galbridge 8 Reference Platform
--  Version      : 0.02   
--  Date         : July 12, 2000     
--
--  Copyright (c) 1999-2000 Wind River Systems, Inc.  All Rights Reserved.
--
--  This MIB is an OEM-product enterprise MIB that is SSP (Switch Support
--  Package) specific.  It is specific to the Galileo Galbridge 8
--  Reference Platform.
--
--  Reproduction of this document is authorized on condition that this
--  copyright notice is included.  This Sample TMS OEM Product Enterprise 
--  MIB embodies proprietary intellectual property of Wind River Systems
--  (WRS).  WRS retains all title and ownership in the specification,
--  including any revisions.
--
--  It is the intent of WRS to encourage the widespread use of this
--  specification in connection with the management of TMS-based products.  
--  WRS grants vendor, end-users, and other interested parties a
--  non-exclusive license to use this specification in connection with the
--  management of TMS products.
--
--  This specification is supplied "AS IS", and WRS makes no warranty,
--  either express or implied, as to the use, operations, condition,
--  or performance of this specification.
--
------------------------------------------------------------------------------
------------------------------------------------------------------------------
--  Sample TMS Galileo Galbridge 8 OEM Product Enterprise MIB
--
--  NOTES:
--   1. This is a SMIv2 MIB.
--
--   2. The following groups are supported in this MIB:
--      - oemArchIface  Configure/retrieve architecture interface specific info
--      - oemChipIface  Configure/retrieve chipset interface specific info
--
------------------------------------------------------------------------------
------------------------------------------------------------------------------

    OEM-GALNET-MIB DEFINITIONS ::= BEGIN

    IMPORTS
        MODULE-IDENTITY, OBJECT-TYPE,
        Integer32, Counter64                    FROM SNMPv2-SMI
        
        DisplayString, TruthValue               FROM SNMPv2-TC
        
        MODULE-COMPLIANCE, OBJECT-GROUP         FROM SNMPv2-CONF
        
        oemProd                                 FROM WRS-MASTER-MIB;       

    galnet MODULE-IDENTITY
        LAST-UPDATED    "0007120000Z"  -- July 12, 2000
        ORGANIZATION    "Wind River Systems, Inc."
        CONTACT-INFO    "Wind River Systems, Inc.
                         E-mail: support@windriver.com"

        DESCRIPTION     "TMS Broadcom BCM5600 StrataSwitch OEM-Product
                         Enterprise MIB definition."

        REVISION        "0007120000Z"  -- July 12, 2000
        DESCRIPTION     "Initial MIB creation."

        ::= { oemProd 2 }

------------------------------------------------------------------------------
-- Textual Conventions (i.e., these do not affect object encoding):
------------------------------------------------------------------------------
--
-- "DURABLE":
--    Objects that are saved across a system reset and/or power cycle
--    are noted as "DURABLE" for convenience in the DESCRIPTION
--    section of the object definition.  Code must be explicitly
--    written to implement these DURABLE objects.
--


------------------------------------------------------------------------------
--  define groups in OEM-GALNET-MIB
------------------------------------------------------------------------------
    oemArchIface            OBJECT IDENTIFIER ::= { galnet 1 }
    oemChip                 OBJECT IDENTIFIER ::= { galnet 2 }
    oemProdConformance      OBJECT IDENTIFIER ::= { galnet 3 }
    oemProdGroups           OBJECT IDENTIFIER ::= { oemProdConformance 1 }
    oemProdCompliances      OBJECT IDENTIFIER ::= { oemProdConformance 2 }


------------------------------------------------------------------------------
--  Architecture Interface Specific Section  
--
--  This group provides interface control and status information not easily
--  available from other MIBs.
--
--  Generic switches have a "<unit>.<slot>.<port>" port topology and any port
--  designator may be described in this manner.
--
--  Since the Galileo Galbridge 8 reference platform has no slots and only one unit,
--  the port topology uses the form "<unit>.<port>".  The unit has 8 10/100Mbps ports.
--  Consequently, port designators use the form "<unit>.<port>" where unit egual 1
--  and the port may range from 1 to 8.
--
--  The user interface "<unit>.<port>" numbering scheme is translated into a
--  "Layered Linear With Holes" (LLWH) port numbering scheme for input to the
--  hardware switch API.  These "holes" accommodate missing ports or units.
--  
--  There are 3 layers supported by the "LLWH" concept as is illustrated in
--  the following diagram.
--  
--     +-----+   +-----+    +-----+            +-----+
--     | sw1 |   | sw2 |    | sw3 |            | swN |
--     +-----+   +-----+    +-----+    . . .   +-----+
--        |  \      |          |                  |
--        |   \     NC         |                  |
--        |    \               |                  |
--        |     \              |                  |
--        |      \             |                  |
--     +-----+   +-----+    +-----+            +-----+
--     | ag1 |   | ag2 |    | ag3 |            | agM |
--     +-----+   +-----+    +-----+    . . .   +-----+
--        |         |          |                  |
--        |         |          |                  |
--     +-----+   +-----+    +-----+            +-----+
--     | ap1 |   | ap2 |    | ap3 |            | agM |
--     +-----+   +-----+    +-----+    . . .   +-----+
--  
--  where:
--    swX: VLAN for L2/L3 switches or interface for L3 only devices; there
--         is one 'sw' for each of the maximum number of L2/L3 VLANs or
--         L3 only interfaces.
--         
--    agY: IEEE 802.3ad Aggregator (application's "logical port"); there
--         is one 'ag' for each of the maximum number of physical ports
--         in the unit.
--       
--    apY: IEEE 802.3ad Aggregation Port (physical port); there is
--         one 'ap' for each of the maximum number of physical ports in
--         the unit.
--  
--  Although IEEE 802.3ad Link Aggregation is not implemented in TMS 2.0,
--  the layering concept has been added to provide for a smooth transition
--  to Link Aggregation in a future release.  The 'agY' Aggregators are the
--  "logical ports" for TMS applications such as Spanning Tree and 802.1Q
--  VLANs.  This logical port (or Aggregator) is the "port" referenced above
--  in the "<unit>.<port>" discussions.
--
--  In the above diagram, logical ports ag1 and ag2 are both attached to the
--  sw1 VLAN.  The sw2 VLAN has no attached logical ports.  For TMS 2.0,
--  the Aggregation Ports are mapped 1-to-1 to the Aggregators.  When Link
--  Aggregation is implemented, multiple Aggregation Ports can be attached
--  to a single Aggregator (please reference the IEEE 802.3ad spec).
--  
--  LLWH FORMAT:
--  The LLWH value is a 16-bit entity that uses the following nibble-based
--  format:
--    "LPPP"
--      where:
--        'L':    indicates the "layer"
--                  1 - swX (L2/L3 VLAN or L3 Only interface)
--                  2 - agY (Aggregator)
--                  3 - apY (Aggregatiton Port)
--        'PPP':  indicates the "port" from 1 to 4095
--  
--  The ifIndex to support RFCs 1213, 2233 and 2665 also supports the
--  IEEE 802.3ad layering concept.
--
--  ifIndex FORMAT:
--  The ifIndex is a 32-bit signed integer that has the following nibble-based
--  format:
--    "0LUSPPPP"
--      where:
--        '0':   always zero
--        'L':   indicates the "layer"
--                  1 - swX (L2/L3 VLAN or L3 Only interface)
--                  2 - agY (Aggregator)
--                  3 - apY (Aggregatiton Port)
--        'U':    indicates the "unit" from 1 to 15
--        'S':    indicates the "slot" from 0 to 15 (0=base unit ports;
--                                                   1 to 15 for actual slots)
--        'PPPP': indicates the "port" from 1 to 65,535
--
--  Note that a unit without any slots, uses "slot 0"
--  for the ports in the base unit.  An ifIndex value of 34603009 (0x02100001)
--  represents the Aggregator layer, unit 1, slot 0 (base unit ports), port 1.
--
------------------------------------------------------------------------------
--
    oemArchIfaceTable OBJECT-TYPE
        SYNTAX SEQUENCE OF OemArchIfaceEntry
        MAX-ACCESS not-accessible
        STATUS current
        DESCRIPTION
            "A table of switch interfaces and associated properties."
        ::= { oemArchIface 1 }

    oemArchIfaceEntry OBJECT-TYPE
        SYNTAX OemArchIfaceEntry
        MAX-ACCESS not-accessible
        STATUS current
        DESCRIPTION
            "Table entry for switch interface control and status information."
        INDEX { oemArchIfaceUnit, oemArchIfacePort }
        ::= { oemArchIfaceTable 1 }

    OemArchIfaceEntry ::= SEQUENCE {
        oemArchIfaceUnit                Integer32,
        oemArchIfacePort                Integer32,
        oemArchIfaceLLWHPort            Integer32,
        oemArchIfaceIfIndex             Integer32,
        oemArchIfaceName                DisplayString,
        oemArchIfaceEnable              TruthValue,
        oemArchIfaceSTPEnable           TruthValue,
        oemArchIfaceLink                INTEGER,
        oemArchIfaceDuplexSpeedSet      INTEGER,
        oemArchIfaceDuplexSpeedGet      INTEGER,
        oemArchIfaceTxVlanTagPkts       Counter64,
        oemArchIfaceTxL3Pkts            Counter64,
        oemArchIfaceTxL3AbortedPkts     Counter64,
        oemArchIfaceRxIpInHdrErrors     Counter64
    }

    oemArchIfaceUnit OBJECT-TYPE
        SYNTAX Integer32 (1..4)
        MAX-ACCESS not-accessible
        STATUS current
        DESCRIPTION
            "An index that uniquely identifies a unit in the TMS galnet
             stack.  If an invalid value is used for the index, a SNMP
             'noSuchName' error (SNMPv1) or 'noSuchInstance' exception
             (SNMPv2/v3) is returned.  For implementations that do not support
             stacking, the same response is returned for any unit index other
             than 1."
        ::= { oemArchIfaceEntry 1 }

    oemArchIfacePort OBJECT-TYPE
        SYNTAX Integer32 (1..8)
        MAX-ACCESS not-accessible
        STATUS current
        DESCRIPTION
            "An index that uniquely identifies a TMS Application 'logical port'
             (i.e., IEEE 802.3ad Aggregator) within the oemArchIfaceUnit."
        ::= { oemArchIfaceEntry 2 }

    oemArchIfaceLLWHPort OBJECT-TYPE
        SYNTAX Integer32 (8193..8296)
        MAX-ACCESS read-only
        STATUS current
        DESCRIPTION
            "A value that uniquely identifies a TMS Application 'logical port'
             (i.e., IEEE 802.3ad Aggregator) in the TMS galnet stack.  This is
             a 'Layered Linear With Holes' (LLWH) port number that may may have
             holes for missing ports or units.  For this MIB, 26 port numbers
             are reserved for each unit in the stack.  For example, LLHW port
             8193 is unit 1, port 1 and LLHW 8228 is unit 2, port 10."
        ::= { oemArchIfaceEntry 3 }

    oemArchIfaceIfIndex OBJECT-TYPE
        SYNTAX Integer32
        MAX-ACCESS read-only
        STATUS current
        DESCRIPTION
            "The ifIndex of this TMS Application 'logical port' (i.e., IEEE
             802.3ad Aggregator).  Note that an ifIndex value of 34603009 
             (0x02100001) represents the Aggregator layer, unit 1, slot 0
             (base unit ports), port 1."
        ::= { oemArchIfaceEntry 4 }

    oemArchIfaceName OBJECT-TYPE
        SYNTAX DisplayString (SIZE (0..16))
        MAX-ACCESS read-write
        STATUS current
        DESCRIPTION
            "DURABLE:
             The textual name of this interface, e.g., 'John'."
        ::= { oemArchIfaceEntry 5 }

    oemArchIfaceEnable OBJECT-TYPE
        SYNTAX TruthValue
        MAX-ACCESS read-write
        STATUS current
        DESCRIPTION
            "DURABLE: { true:all }
             This object is true(1) when this interface is enabled and
             false(1) when it is disabled.  For this product, this is the
             ONLY way to enable or disable this interface.  Note that
             'ifAdminStatus' in RFC1213 and RFC2233 and 'dot1dStpPortEnable'
             in RFC1493 are each implemented as 'read-only'."
        ::= { oemArchIfaceEntry 6 }

    oemArchIfaceSTPEnable OBJECT-TYPE
        SYNTAX TruthValue
        MAX-ACCESS read-write
        STATUS current
        DESCRIPTION
            "DURABLE: { true:all }
             This object is true(1) when Spanning Tree operation is enabled
             for this interface and false(2) when it is disabled."
        ::= { oemArchIfaceEntry 7 }

    oemArchIfaceLink OBJECT-TYPE
        SYNTAX INTEGER {
             up(1), 
             down(2)
        }
        MAX-ACCESS read-only
        STATUS current
        DESCRIPTION
            "The state of Link Detect on this interface."
        ::= { oemArchIfaceEntry 8 }

    oemArchIfaceDuplexSpeedSet OBJECT-TYPE
        SYNTAX INTEGER {
             autonegotiate(1),
             half-10(2),
             full-10(3),
             half-100(4),
             full-100(5),
             full-1000(6),
             illegal(99)
        }
        MAX-ACCESS read-write
        STATUS current
        DESCRIPTION
            "DURABLE: { autonegotiate:all }
            The desired speed and duplex for this interface. If the selected
            control is not possible on the interface, a value of illegal(99)
            is returned.  If the port type does NOT support the default
            of autonegotiate(1), then the application initializes the
            port to a valid value (e.g., 1000full(6)).  Note that not all
            controls are possible for all interfaces.  For example, only
            full-1000(6) is available for Gigabit Ethernet interfaces."
        ::= { oemArchIfaceEntry 9 }

    oemArchIfaceDuplexSpeedGet OBJECT-TYPE
        SYNTAX INTEGER {
             unknown(1),
             half-10(2),
             full-10(3),
             half-100(4),
             full-100(5),
             full-1000(6),
             illegal(99)
        }
        MAX-ACCESS read-only
        STATUS current
        DESCRIPTION
            "The actual speed and duplex for this interface.  If the
            interface is not configured for an acceptable value, a value of
            illegal(99) is returned.  A value of unknown(1) is returned when
            the 'oemArchIfaceLink' indicates down(2) for this interface." 
        ::= { oemArchIfaceEntry 10 }

    oemArchIfaceTxVlanTagPkts OBJECT-TYPE
        SYNTAX Counter64 
        MAX-ACCESS read-only
        STATUS current
        DESCRIPTION
            "The number of VLAN tagged packets transmitted on this interface."
        ::= { oemArchIfaceEntry 11 }

    oemArchIfaceTxL3Pkts OBJECT-TYPE
        SYNTAX Counter64 
        MAX-ACCESS read-only
        STATUS current
        DESCRIPTION
            "The number of Layer 3 packets transmitted on this interface."
        ::= { oemArchIfaceEntry 12 }

    oemArchIfaceTxL3AbortedPkts OBJECT-TYPE
        SYNTAX Counter64 
        MAX-ACCESS read-only
        STATUS current
        DESCRIPTION
            "The number of Layer 3 transmit packets aborted on this interface."
        ::= { oemArchIfaceEntry 13 }

    oemArchIfaceRxIpInHdrErrors OBJECT-TYPE
        SYNTAX Counter64 
        MAX-ACCESS read-only
        STATUS current
        DESCRIPTION
            "The number of Layer 3 packets received on this interface that
             were discarded due to IP header errors (e.g., bad checksum,
             invalid versions, format errors)."
        ::= { oemArchIfaceEntry 14 }


------------------------------------------------------------------------------
--  Chip Interface Section  
------------------------------------------------------------------------------
--
    oemChipStub OBJECT-TYPE
        SYNTAX INTEGER {  
            noop(1),
            chip-value2(2),
            chip-value3(3)
        }
        MAX-ACCESS read-write
        STATUS current
        DESCRIPTION
            "This object is a place holder for the OEM Chip interface." 
        ::= { oemChip 1 }


------------------------------------------------------------------------------
--  conformance information
------------------------------------------------------------------------------

--  --------------------------------------------------------------------------
--  units of conformance
--  --------------------------------------------------------------------------

    oemArchIfaceGroup   OBJECT-GROUP
        OBJECTS {
            oemArchIfaceLLWHPort,
            oemArchIfaceIfIndex,
            oemArchIfaceName,
            oemArchIfaceEnable,
            oemArchIfaceSTPEnable,
            oemArchIfaceLink,
            oemArchIfaceDuplexSpeedSet,
            oemArchIfaceDuplexSpeedGet,
            oemArchIfaceTxVlanTagPkts,
            oemArchIfaceTxL3Pkts,
            oemArchIfaceTxL3AbortedPkts,
            oemArchIfaceRxIpInHdrErrors
        }
        STATUS  current
        DESCRIPTION
           "This group configures and retrieves Architecture interface
            specific objects."
        ::= { oemProdGroups 1 }
    
    oemChipGroup    OBJECT-GROUP
        OBJECTS {
            oemChipStub
        }
        STATUS  current
        DESCRIPTION
           "This group configures OEM Chip specific objects."
        ::= { oemProdGroups 2 }
    

--  --------------------------------------------------------------------------
--  compliance statements
--  --------------------------------------------------------------------------

    oemProdCompliance MODULE-COMPLIANCE
        STATUS  current
        DESCRIPTION
           "The compliance statement."
        MODULE  -- this module
        MANDATORY-GROUPS {
             oemArchIfaceGroup
        }
        
    GROUP   oemChipGroup
    DESCRIPTION
        "This group is optional."
        
        ::= { oemProdCompliances 1 }

--
-- END of OEM-galnet-MIB                
--

END

----------------------------------------------------------------------
--
-- RFC2665
--
----------------------------------------------------------------------

   EtherLike-MIB DEFINITIONS ::= BEGIN

       IMPORTS
           MODULE-IDENTITY, OBJECT-TYPE, OBJECT-IDENTITY,
           Counter32, mib-2, transmission
               FROM SNMPv2-SMI
           MODULE-COMPLIANCE, OBJECT-GROUP
               FROM SNMPv2-CONF
           ifIndex, InterfaceIndex
               FROM IF-MIB;

       etherMIB MODULE-IDENTITY
           LAST-UPDATED "9908240400Z"  -- August 24, 1999
           ORGANIZATION "IETF Ethernet Interfaces and Hub MIB
                        Working Group"
           CONTACT-INFO
               "WG E-mail: hubmib@hprnd.rose.hp.com
             To subscribe: hubmib-request@hprnd.rose.hp.com

                    Chair: Dan Romascanu
                   Postal: Lucent Technologies
                           Atidum Technology Park, Bldg. 3
                           Tel Aviv 61131
                           Israel
                      Tel: +972 3 645 8414
                   E-mail: dromasca@lucent.com

                  Editor: John Flick
                  Postal: Hewlett-Packard Company
                          8000 Foothills Blvd. M/S 5557
                          Roseville, CA 95747-5557
                          USA
                     Tel: +1 916 785 4018
                     Fax: +1 916 785 1199
                  E-mail: johnf@rose.hp.com

                  Editor: Jeffrey Johnson
                  Postal: RedBack Networks
                          2570 North First Street, Suite 410
                          San Jose, CA, 95131
                          USA
                     Tel: +1 408 571 2699
                     Fax: +1 408 571 2698
                  E-Mail: jeff@redbacknetworks.com"

           DESCRIPTION "The MIB module to describe generic objects for

                       Ethernet-like network interfaces.

                       The following reference is used throughout this
                       MIB module:

                       [IEEE 802.3 Std] refers to:
                          IEEE Std 802.3, 1998 Edition: 'Information
                          technology - Telecommunications and
                          information exchange between systems -
                          Local and metropolitan area networks -
                          Specific requirements - Part 3: Carrier
                          sense multiple access with collision
                          detection (CSMA/CD) access method and
                          physical layer specifications',
                          September 1998.

                       Of particular interest is Clause 30, '10Mb/s,
                       100Mb/s and 1000Mb/s Management'."

           REVISION    "9908240400Z"  -- August 24, 1999
           DESCRIPTION "Updated to include support for 1000 Mb/sec
                        interfaces and full-duplex interfaces.
                        This version published as RFC 2665."

           REVISION    "9806032150Z"
           DESCRIPTION "Updated to include support for 100 Mb/sec
                        interfaces.
                        This version published as RFC 2358."

           REVISION    "9402030400Z"
           DESCRIPTION "Initial version, published as RFC 1650."

           ::= { mib-2 35 }


       etherMIBObjects OBJECT IDENTIFIER ::= { etherMIB 1 }

       dot3    OBJECT IDENTIFIER ::= { transmission 7 }

       -- the Ethernet-like Statistics group

       dot3StatsTable OBJECT-TYPE
           SYNTAX     SEQUENCE OF Dot3StatsEntry
           MAX-ACCESS not-accessible
           STATUS     current
           DESCRIPTION "Statistics for a collection of ethernet-like
                       interfaces attached to a particular system.
                       There will be one row in this table for each
                       ethernet-like interface in the system."
           ::= { dot3 2 }

       dot3StatsEntry OBJECT-TYPE
           SYNTAX     Dot3StatsEntry
           MAX-ACCESS not-accessible
           STATUS     current
           DESCRIPTION "Statistics for a particular interface to an
                       ethernet-like medium."
           INDEX       { dot3StatsIndex }
           ::= { dot3StatsTable 1 }

       Dot3StatsEntry ::=
           SEQUENCE {
               dot3StatsIndex                      InterfaceIndex,
               dot3StatsAlignmentErrors            Counter32,
               dot3StatsFCSErrors                  Counter32,
               dot3StatsSingleCollisionFrames      Counter32,
               dot3StatsMultipleCollisionFrames    Counter32,
               dot3StatsSQETestErrors              Counter32,
               dot3StatsDeferredTransmissions      Counter32,
               dot3StatsLateCollisions             Counter32,
               dot3StatsExcessiveCollisions        Counter32,
               dot3StatsInternalMacTransmitErrors  Counter32,
               dot3StatsCarrierSenseErrors         Counter32,
               dot3StatsFrameTooLongs              Counter32,
               dot3StatsInternalMacReceiveErrors   Counter32,
               dot3StatsEtherChipSet               OBJECT IDENTIFIER,
               dot3StatsSymbolErrors               Counter32,
               dot3StatsDuplexStatus               INTEGER
           }

       dot3StatsIndex OBJECT-TYPE
           SYNTAX      InterfaceIndex
           MAX-ACCESS  read-only
           STATUS      current
           DESCRIPTION "An index value that uniquely identifies an
                       interface to an ethernet-like medium.  The
                       interface identified by a particular value of
                       this index is the same interface as identified
                       by the same value of ifIndex."
           REFERENCE   "RFC 2233, ifIndex"
           ::= { dot3StatsEntry 1 }

       dot3StatsAlignmentErrors OBJECT-TYPE
           SYNTAX      Counter32
           MAX-ACCESS  read-only
           STATUS      current

           DESCRIPTION "A count of frames received on a particular
                       interface that are not an integral number of
                       octets in length and do not pass the FCS check.

                       The count represented by an instance of this
                       object is incremented when the alignmentError
                       status is returned by the MAC service to the
                       LLC (or other MAC user). Received frames for
                       which multiple error conditions obtain are,
                       according to the conventions of IEEE 802.3
                       Layer Management, counted exclusively according
                       to the error status presented to the LLC.

                       This counter does not increment for 8-bit wide
                       group encoding schemes.

                       Discontinuities in the value of this counter can
                       occur at re-initialization of the management
                       system, and at other times as indicated by the
                       value of ifCounterDiscontinuityTime."
           REFERENCE   "[IEEE 802.3 Std.], 30.3.1.1.7,
                       aAlignmentErrors"
           ::= { dot3StatsEntry 2 }

       dot3StatsFCSErrors OBJECT-TYPE
           SYNTAX      Counter32
           MAX-ACCESS  read-only
           STATUS      current
           DESCRIPTION "A count of frames received on a particular
                       interface that are an integral number of octets
                       in length but do not pass the FCS check.  This
                       count does not include frames received with
                       frame-too-long or frame-too-short error.

                       The count represented by an instance of this
                       object is incremented when the frameCheckError
                       status is returned by the MAC service to the
                       LLC (or other MAC user). Received frames for
                       which multiple error conditions obtain are,
                       according to the conventions of IEEE 802.3
                       Layer Management, counted exclusively according
                       to the error status presented to the LLC.

                       Note:  Coding errors detected by the physical
                       layer for speeds above 10 Mb/s will cause the
                       frame to fail the FCS check.
                       Discontinuities in the value of this counter can
                       occur at re-initialization of the management
                       system, and at other times as indicated by the
                       value of ifCounterDiscontinuityTime."
           REFERENCE   "[IEEE 802.3 Std.], 30.3.1.1.6,
                       aFrameCheckSequenceErrors."
           ::= { dot3StatsEntry 3 }

       dot3StatsSingleCollisionFrames OBJECT-TYPE
           SYNTAX      Counter32
           MAX-ACCESS  read-only
           STATUS      current
           DESCRIPTION "A count of successfully transmitted frames on
                       a particular interface for which transmission
                       is inhibited by exactly one collision.

                       A frame that is counted by an instance of this
                       object is also counted by the corresponding
                       instance of either the ifOutUcastPkts,
                       ifOutMulticastPkts, or ifOutBroadcastPkts,
                       and is not counted by the corresponding
                       instance of the dot3StatsMultipleCollisionFrames
                       object.

                       This counter does not increment when the
                       interface is operating in full-duplex mode.

                       Discontinuities in the value of this counter can
                       occur at re-initialization of the management
                       system, and at other times as indicated by the
                       value of ifCounterDiscontinuityTime."
           REFERENCE   "[IEEE 802.3 Std.], 30.3.1.1.3,
                       aSingleCollisionFrames."
           ::= { dot3StatsEntry 4 }

       dot3StatsMultipleCollisionFrames OBJECT-TYPE
           SYNTAX      Counter32
           MAX-ACCESS  read-only
           STATUS      current
           DESCRIPTION "A count of successfully transmitted frames on
                       a particular interface for which transmission
                       is inhibited by more than one collision.

                       A frame that is counted by an instance of this
                       object is also counted by the corresponding
                       instance of either the ifOutUcastPkts,
                       ifOutMulticastPkts, or ifOutBroadcastPkts,
                       and is not counted by the corresponding
                       instance of the dot3StatsSingleCollisionFrames
                       object.

                       This counter does not increment when the
                       interface is operating in full-duplex mode.

                       Discontinuities in the value of this counter can
                       occur at re-initialization of the management
                       system, and at other times as indicated by the
                       value of ifCounterDiscontinuityTime."
           REFERENCE   "[IEEE 802.3 Std.], 30.3.1.1.4,
                       aMultipleCollisionFrames."
           ::= { dot3StatsEntry 5 }

       dot3StatsSQETestErrors OBJECT-TYPE
           SYNTAX      Counter32
           MAX-ACCESS  read-only
           STATUS      current
           DESCRIPTION "A count of times that the SQE TEST ERROR
                       message is generated by the PLS sublayer for a
                       particular interface. The SQE TEST ERROR
                       is set in accordance with the rules for
                       verification of the SQE detection mechanism in
                       the PLS Carrier Sense Function as described in
                       IEEE Std. 802.3, 1998 Edition, section 7.2.4.6.

                       This counter does not increment on interfaces
                       operating at speeds greater than 10 Mb/s, or on
                       interfaces operating in full-duplex mode.

                       Discontinuities in the value of this counter can
                       occur at re-initialization of the management
                       system, and at other times as indicated by the
                       value of ifCounterDiscontinuityTime."
           REFERENCE   "[IEEE 802.3 Std.], 7.2.4.6, also 30.3.2.1.4,
                       aSQETestErrors."
           ::= { dot3StatsEntry 6 }

       dot3StatsDeferredTransmissions OBJECT-TYPE
           SYNTAX      Counter32
           MAX-ACCESS  read-only
           STATUS      current
           DESCRIPTION "A count of frames for which the first
                       transmission attempt on a particular interface
                       is delayed because the medium is busy.
                       The count represented by an instance of this
                       object does not include frames involved in
                       collisions.

                       This counter does not increment when the
                       interface is operating in full-duplex mode.

                       Discontinuities in the value of this counter can
                       occur at re-initialization of the management
                       system, and at other times as indicated by the
                       value of ifCounterDiscontinuityTime."
           REFERENCE   "[IEEE 802.3 Std.], 30.3.1.1.9,
                       aFramesWithDeferredXmissions."
           ::= { dot3StatsEntry 7 }

       dot3StatsLateCollisions OBJECT-TYPE
           SYNTAX      Counter32
           MAX-ACCESS  read-only
           STATUS      current
           DESCRIPTION "The number of times that a collision is
                       detected on a particular interface later than
                       one slotTime into the transmission of a packet.

                       A (late) collision included in a count
                       represented by an instance of this object is
                       also considered as a (generic) collision for
                       purposes of other collision-related
                       statistics.

                       This counter does not increment when the
                       interface is operating in full-duplex mode.

                       Discontinuities in the value of this counter can
                       occur at re-initialization of the management
                       system, and at other times as indicated by the
                       value of ifCounterDiscontinuityTime."
           REFERENCE   "[IEEE 802.3 Std.], 30.3.1.1.10,
                       aLateCollisions."
           ::= { dot3StatsEntry 8 }

       dot3StatsExcessiveCollisions OBJECT-TYPE
           SYNTAX      Counter32
           MAX-ACCESS  read-only
           STATUS      current
           DESCRIPTION "A count of frames for which transmission on a
                       particular interface fails due to excessive
                       collisions.
                       This counter does not increment when the
                       interface is operating in full-duplex mode.

                       Discontinuities in the value of this counter can
                       occur at re-initialization of the management
                       system, and at other times as indicated by the
                       value of ifCounterDiscontinuityTime."
           REFERENCE   "[IEEE 802.3 Std.], 30.3.1.1.11,

                       aFramesAbortedDueToXSColls."
           ::= { dot3StatsEntry 9 }

       dot3StatsInternalMacTransmitErrors OBJECT-TYPE
           SYNTAX      Counter32
           MAX-ACCESS  read-only
           STATUS      current
           DESCRIPTION "A count of frames for which transmission on a
                       particular interface fails due to an internal
                       MAC sublayer transmit error. A frame is only
                       counted by an instance of this object if it is
                       not counted by the corresponding instance of
                       either the dot3StatsLateCollisions object, the
                       dot3StatsExcessiveCollisions object, or the
                       dot3StatsCarrierSenseErrors object.

                       The precise meaning of the count represented by
                       an instance of this object is implementation-
                       specific.  In particular, an instance of this
                       object may represent a count of transmission
                       errors on a particular interface that are not
                       otherwise counted.

                       Discontinuities in the value of this counter can
                       occur at re-initialization of the management
                       system, and at other times as indicated by the
                       value of ifCounterDiscontinuityTime."
           REFERENCE   "[IEEE 802.3 Std.], 30.3.1.1.12,
                       aFramesLostDueToIntMACXmitError."
           ::= { dot3StatsEntry 10 }

       dot3StatsCarrierSenseErrors OBJECT-TYPE
           SYNTAX      Counter32
           MAX-ACCESS  read-only
           STATUS      current
           DESCRIPTION "The number of times that the carrier sense
                       condition was lost or never asserted when
                       attempting to transmit a frame on a particular
                       interface.

                       The count represented by an instance of this
                       object is incremented at most once per
                       transmission attempt, even if the carrier sense
                       condition fluctuates during a transmission
                       attempt.

                       This counter does not increment when the
                       interface is operating in full-duplex mode.

                       Discontinuities in the value of this counter can
                       occur at re-initialization of the management
                       system, and at other times as indicated by the
                       value of ifCounterDiscontinuityTime."
           REFERENCE   "[IEEE 802.3 Std.], 30.3.1.1.13,
                       aCarrierSenseErrors."
           ::= { dot3StatsEntry 11 }

       -- { dot3StatsEntry 12 } is not assigned

       dot3StatsFrameTooLongs OBJECT-TYPE
           SYNTAX      Counter32
           MAX-ACCESS  read-only
           STATUS      current
           DESCRIPTION "A count of frames received on a particular
                       interface that exceed the maximum permitted
                       frame size.

                       The count represented by an instance of this
                       object is incremented when the frameTooLong
                       status is returned by the MAC service to the
                       LLC (or other MAC user). Received frames for
                       which multiple error conditions obtain are,
                       according to the conventions of IEEE 802.3
                       Layer Management, counted exclusively according
                       to the error status presented to the LLC.

                       Discontinuities in the value of this counter can
                       occur at re-initialization of the management
                       system, and at other times as indicated by the
                       value of ifCounterDiscontinuityTime."
           REFERENCE   "[IEEE 802.3 Std.], 30.3.1.1.25,
                       aFrameTooLongErrors."
           ::= { dot3StatsEntry 13 }

       -- { dot3StatsEntry 14 } is not assigned

       -- { dot3StatsEntry 15 } is not assigned

       dot3StatsInternalMacReceiveErrors OBJECT-TYPE
           SYNTAX      Counter32
           MAX-ACCESS  read-only
           STATUS      current
           DESCRIPTION "A count of frames for which reception on a
                       particular interface fails due to an internal
                       MAC sublayer receive error. A frame is only
                       counted by an instance of this object if it is
                       not counted by the corresponding instance of
                       either the dot3StatsFrameTooLongs object, the
                       dot3StatsAlignmentErrors object, or the
                       dot3StatsFCSErrors object.

                       The precise meaning of the count represented by
                       an instance of this object is implementation-
                       specific.  In particular, an instance of this
                       object may represent a count of receive errors
                       on a particular interface that are not
                       otherwise counted.

                       Discontinuities in the value of this counter can
                       occur at re-initialization of the management
                       system, and at other times as indicated by the
                       value of ifCounterDiscontinuityTime."
           REFERENCE   "[IEEE 802.3 Std.], 30.3.1.1.15,
                       aFramesLostDueToIntMACRcvError."
           ::= { dot3StatsEntry 16 }

       dot3StatsEtherChipSet OBJECT-TYPE
           SYNTAX      OBJECT IDENTIFIER
           MAX-ACCESS  read-only
           STATUS      deprecated
           DESCRIPTION "******** THIS OBJECT IS DEPRECATED ********

                       This object contains an OBJECT IDENTIFIER
                       which identifies the chipset used to
                       realize the interface. Ethernet-like
                       interfaces are typically built out of
                       several different chips. The MIB implementor
                       is presented with a decision of which chip
                       to identify via this object. The implementor
                       should identify the chip which is usually
                       called the Medium Access Control chip.
                       If no such chip is easily identifiable,
                       the implementor should identify the chip
                       which actually gathers the transmit
                       and receive statistics and error
                       indications. This would allow a
                       manager station to correlate the
                       statistics and the chip generating
                       them, giving it the ability to take
                       into account any known anomalies
                       in the chip."
           ::= { dot3StatsEntry 17 }

       dot3StatsSymbolErrors OBJECT-TYPE
           SYNTAX      Counter32
           MAX-ACCESS  read-only
           STATUS      current
           DESCRIPTION "For an interface operating at 100 Mb/s, the
                       number of times there was an invalid data symbol
                       when a valid carrier was present.

                       For an interface operating in half-duplex mode
                       at 1000 Mb/s, the number of times the receiving
                       media is non-idle (a carrier event) for a period
                       of time equal to or greater than slotTime, and
                       during which there was at least one occurrence
                       of an event that causes the PHY to indicate
                       'Data reception error' or 'carrier extend error'
                       on the GMII.

                       For an interface operating in full-duplex mode
                       at 1000 Mb/s, the number of times the receiving
                       media is non-idle a carrier event) for a period
                       of time equal to or greater than minFrameSize,
                       and during which there was at least one
                       occurrence of an event that causes the PHY to
                       indicate 'Data reception error' on the GMII.

                       The count represented by an instance of this
                       object is incremented at most once per carrier
                       event, even if multiple symbol errors occur
                       during the carrier event.  This count does
                       not increment if a collision is present.

                       Discontinuities in the value of this counter can
                       occur at re-initialization of the management
                       system, and at other times as indicated by the
                       value of ifCounterDiscontinuityTime."
           REFERENCE   "[IEEE 802.3 Std.], 30.3.2.1.5,
                       aSymbolErrorDuringCarrier."
           ::= { dot3StatsEntry 18 }

       dot3StatsDuplexStatus OBJECT-TYPE
           SYNTAX      INTEGER {
                           unknown(1),
                           halfDuplex(2),
                           fullDuplex(3)
                       }
           MAX-ACCESS  read-only
           STATUS      current
           DESCRIPTION "The current mode of operation of the MAC
                       entity.  'unknown' indicates that the current
                       duplex mode could not be determined.

                       Management control of the duplex mode is
                       accomplished through the MAU MIB.  When
                       an interface does not support autonegotiation,
                       or when autonegotiation is not enabled, the
                       duplex mode is controlled using
                       ifMauDefaultType.  When autonegotiation is
                       supported and enabled, duplex mode is controlled
                       using ifMauAutoNegAdvertisedBits.  In either
                       case, the currently operating duplex mode is
                       reflected both in this object and in ifMauType.

                       Note that this object provides redundant
                       information with ifMauType.  Normally, redundant
                       objects are discouraged.  However, in this
                       instance, it allows a management application to
                       determine the duplex status of an interface
                       without having to know every possible value of
                       ifMauType.  This was felt to be sufficiently
                       valuable to justify the redundancy."
           REFERENCE   "[IEEE 802.3 Std.], 30.3.1.1.32,
                       aDuplexStatus."
           ::= { dot3StatsEntry 19 }

       -- the Ethernet-like Collision Statistics group

       -- Implementation of this group is optional; it is appropriate
       -- for all systems which have the necessary metering

       dot3CollTable OBJECT-TYPE
           SYNTAX      SEQUENCE OF Dot3CollEntry
           MAX-ACCESS  not-accessible
           STATUS      current
           DESCRIPTION "A collection of collision histograms for a
                       particular set of interfaces."
           REFERENCE   "[IEEE 802.3 Std.], 30.3.1.1.30,
                       aCollisionFrames."
           ::= { dot3 5 }

       dot3CollEntry OBJECT-TYPE
           SYNTAX      Dot3CollEntry
           MAX-ACCESS  not-accessible
           STATUS      current
           DESCRIPTION "A cell in the histogram of per-frame
                       collisions for a particular interface.  An
                       instance of this object represents the
                       frequency of individual MAC frames for which
                       the transmission (successful or otherwise) on a
                       particular interface is accompanied by a
                       particular number of media collisions."
           INDEX       { ifIndex, dot3CollCount }
           ::= { dot3CollTable 1 }

       Dot3CollEntry ::=
           SEQUENCE {
               dot3CollCount        INTEGER,
               dot3CollFrequencies  Counter32
           }

       -- { dot3CollEntry 1 } is no longer in use

       dot3CollCount OBJECT-TYPE
           SYNTAX      INTEGER (1..16)
           MAX-ACCESS  not-accessible
           STATUS      current
           DESCRIPTION "The number of per-frame media collisions for
                       which a particular collision histogram cell
                       represents the frequency on a particular
                       interface."
           ::= { dot3CollEntry 2 }

       dot3CollFrequencies OBJECT-TYPE
           SYNTAX      Counter32
           MAX-ACCESS  read-only
           STATUS      current
           DESCRIPTION "A count of individual MAC frames for which the
                       transmission (successful or otherwise) on a
                       particular interface occurs after the
                       frame has experienced exactly the number
                       of collisions in the associated
                       dot3CollCount object.

                       For example, a frame which is transmitted
                       on interface 77 after experiencing
                       exactly 4 collisions would be indicated
                       by incrementing only dot3CollFrequencies.77.4.
                       No other instance of dot3CollFrequencies would
                       be incremented in this example.

                       This counter does not increment when the
                       interface is operating in full-duplex mode.

                       Discontinuities in the value of this counter can
                       occur at re-initialization of the management
                       system, and at other times as indicated by the
                       value of ifCounterDiscontinuityTime."
           ::= { dot3CollEntry 3 }

       dot3ControlTable OBJECT-TYPE
           SYNTAX      SEQUENCE OF Dot3ControlEntry
           MAX-ACCESS  not-accessible
           STATUS      current
           DESCRIPTION "A table of descriptive and status information
                       about the MAC Control sublayer on the
                       ethernet-like interfaces attached to a
                       particular system.  There will be one row in
                       this table for each ethernet-like interface in
                       the system which implements the MAC Control
                       sublayer.  If some, but not all, of the
                       ethernet-like interfaces in the system implement
                       the MAC Control sublayer, there will be fewer
                       rows in this table than in the dot3StatsTable."
           ::= { dot3 9 }

       dot3ControlEntry OBJECT-TYPE
           SYNTAX      Dot3ControlEntry
           MAX-ACCESS  not-accessible
           STATUS      current
           DESCRIPTION "An entry in the table, containing information
                       about the MAC Control sublayer on a single
                       ethernet-like interface."
           INDEX       { dot3StatsIndex }
           ::= { dot3ControlTable 1 }

       Dot3ControlEntry ::=
           SEQUENCE {
               dot3ControlFunctionsSupported       BITS,
               dot3ControlInUnknownOpcodes         Counter32
           }

       dot3ControlFunctionsSupported OBJECT-TYPE
           SYNTAX      BITS {
                           pause(0)   -- 802.3x flow control
                       }
           MAX-ACCESS  read-only
           STATUS      current
           DESCRIPTION "A list of the possible MAC Control functions
                       implemented for this interface."
           REFERENCE   "[IEEE 802.3 Std.], 30.3.3.2,
                       aMACControlFunctionsSupported."
           ::= { dot3ControlEntry 1 }

       dot3ControlInUnknownOpcodes OBJECT-TYPE
           SYNTAX      Counter32
           MAX-ACCESS  read-only
           STATUS      current
           DESCRIPTION "A count of MAC Control frames received on this
                       interface that contain an opcode that is not
                       supported by this device.

                       Discontinuities in the value of this counter can
                       occur at re-initialization of the management
                       system, and at other times as indicated by the
                       value of ifCounterDiscontinuityTime."
           REFERENCE   "[IEEE 802.3 Std.], 30.3.3.5,
                       aUnsupportedOpcodesReceived"
           ::= { dot3ControlEntry 2 }

       dot3PauseTable OBJECT-TYPE
           SYNTAX      SEQUENCE OF Dot3PauseEntry
           MAX-ACCESS  not-accessible
           STATUS      current
           DESCRIPTION "A table of descriptive and status information
                       about the MAC Control PAUSE function on the
                       ethernet-like interfaces attached to a
                       particular system. There will be one row in
                       this table for each ethernet-like interface in
                       the system which supports the MAC Control PAUSE
                       function (i.e., the 'pause' bit in the
                       corresponding instance of
                       dot3ControlFunctionsSupported is set).  If some,
                       but not all, of the ethernet-like interfaces in
                       the system implement the MAC Control PAUSE
                       function (for example, if some interfaces only
                       support half-duplex), there will be fewer rows
                       in this table than in the dot3StatsTable."
           ::= { dot3 10 }

       dot3PauseEntry OBJECT-TYPE
           SYNTAX      Dot3PauseEntry
           MAX-ACCESS  not-accessible
           STATUS      current
           DESCRIPTION "An entry in the table, containing information
                       about the MAC Control PAUSE function on a single
                       ethernet-like interface."
           INDEX       { dot3StatsIndex }
           ::= { dot3PauseTable 1 }

       Dot3PauseEntry ::=
           SEQUENCE {
               dot3PauseAdminMode                  INTEGER,
               dot3PauseOperMode                   INTEGER,
               dot3InPauseFrames                   Counter32,
               dot3OutPauseFrames                  Counter32

           }

       dot3PauseAdminMode OBJECT-TYPE
           SYNTAX      INTEGER {
                           disabled(1),
                           enabledXmit(2),
                           enabledRcv(3),
                           enabledXmitAndRcv(4)
                       }
           MAX-ACCESS  read-write
           STATUS      current
           DESCRIPTION "This object is used to configure the default
                       administrative PAUSE mode for this interface.

                       This object represents the
                       administratively-configured PAUSE mode for this
                       interface.  If auto-negotiation is not enabled
                       or is not implemented for the active MAU
                       attached to this interface, the value of this
                       object determines the operational PAUSE mode
                       of the interface whenever it is operating in
                       full-duplex mode.  In this case, a set to this
                       object will force the interface into the
                       specified mode.

                       If auto-negotiation is implemented and enabled
                       for the MAU attached to this interface, the
                       PAUSE mode for this interface is determined by
                       auto-negotiation, and the value of this object
                       denotes the mode to which the interface will
                       automatically revert if/when auto-negotiation is
                       later disabled.  Note that when auto-negotiation
                       is running, administrative control of the PAUSE
                       mode may be accomplished using the
                       ifMauAutoNegCapAdvertisedBits object in the
                       MAU-MIB.

                       Note that the value of this object is ignored
                       when the interface is not operating in
                       full-duplex mode.

                       An attempt to set this object to
                       'enabledXmit(2)' or 'enabledRcv(3)' will fail
                       on interfaces that do not support operation
                       at greater than 100 Mb/s."
           ::= { dot3PauseEntry 1 }

       dot3PauseOperMode OBJECT-TYPE

           SYNTAX      INTEGER {
                           disabled(1),
                           enabledXmit(2),
                           enabledRcv(3),
                           enabledXmitAndRcv(4)
                       }
           MAX-ACCESS  read-only
           STATUS      current
           DESCRIPTION "This object reflects the PAUSE mode currently
                       in use on this interface, as determined by
                       either (1) the result of the auto-negotiation
                       function or (2) if auto-negotiation is not
                       enabled or is not implemented for the active MAU
                       attached to this interface, by the value of
                       dot3PauseAdminMode.  Interfaces operating at
                       100 Mb/s or less will never return
                       'enabledXmit(2)' or 'enabledRcv(3)'.  Interfaces
                       operating in half-duplex mode will always return
                       'disabled(1)'.  Interfaces on which
                       auto-negotiation is enabled but not yet
                       completed should return the value
                       'disabled(1)'."
           ::= { dot3PauseEntry 2 }

       dot3InPauseFrames OBJECT-TYPE
           SYNTAX      Counter32
           MAX-ACCESS  read-only
           STATUS      current
           DESCRIPTION "A count of MAC Control frames received on this
                       interface with an opcode indicating the PAUSE
                       operation.

                       This counter does not increment when the
                       interface is operating in half-duplex mode.
                       Discontinuities in the value of this counter can
                       occur at re-initialization of the management
                       system, and at other times as indicated by the
                       value of ifCounterDiscontinuityTime."
           REFERENCE   "[IEEE 802.3 Std.], 30.3.4.3,
                       aPAUSEMACCtrlFramesReceived."
           ::= { dot3PauseEntry 3 }

       dot3OutPauseFrames OBJECT-TYPE
           SYNTAX      Counter32
           MAX-ACCESS  read-only
           STATUS      current
           DESCRIPTION "A count of MAC Control frames transmitted on
                       this interface with an opcode indicating the
                       PAUSE operation.

                       This counter does not increment when the
                       interface is operating in half-duplex mode.

                       Discontinuities in the value of this counter can
                       occur at re-initialization of the management
                       system, and at other times as indicated by the
                       value of ifCounterDiscontinuityTime."
           REFERENCE   "[IEEE 802.3 Std.], 30.3.4.2,
                       aPAUSEMACCtrlFramesTransmitted."
           ::= { dot3PauseEntry 4 }

       --  802.3 Tests

       dot3Tests   OBJECT IDENTIFIER ::= { dot3 6 }

       dot3Errors  OBJECT IDENTIFIER ::= { dot3 7 }

       --  TDR Test

       dot3TestTdr OBJECT-IDENTITY
           STATUS      current
           DESCRIPTION "The Time-Domain Reflectometry (TDR) test is
                       specific to ethernet-like interfaces of type
                       10Base5 and 10Base2.  The TDR value may be
                       useful in determining the approximate distance
                       to a cable fault.  It is advisable to repeat
                       this test to check for a consistent resulting
                       TDR value, to verify that there is a fault.

                       A TDR test returns as its result the time
                       interval, measured in 10 MHz ticks or 100 nsec
                       units, between the start of TDR test
                       transmission and the subsequent detection of a
                       collision or deassertion of carrier.  On
                       successful completion of a TDR test, the result
                       is stored as the value of an appropriate
                       instance of an appropriate vendor specific MIB
                       object, and the OBJECT IDENTIFIER of that
                       instance is stored in the appropriate instance
                       of the appropriate test result code object
                       (thereby indicating where the result has been
                       stored)."
           ::= { dot3Tests 1 }

       -- Loopback Test

       dot3TestLoopBack OBJECT-IDENTITY
           STATUS      current
           DESCRIPTION "This test configures the MAC chip and executes
                       an internal loopback test of memory, data paths,
                       and the MAC chip logic.  This loopback test can
                       only be executed if the interface is offline.
                       Once the test has completed, the MAC chip should
                       be reinitialized for network operation, but it
                       should remain offline.

                       If an error occurs during a test, the
                       appropriate test result object will be set
                       to indicate a failure.  The two OBJECT
                       IDENTIFIER values dot3ErrorInitError and
                       dot3ErrorLoopbackError may be used to provided
                       more information as values for an appropriate
                       test result code object."
           ::= { dot3Tests 2 }

       dot3ErrorInitError OBJECT-IDENTITY
           STATUS      current
           DESCRIPTION "Couldn't initialize MAC chip for test."
           ::= { dot3Errors 1 }

       dot3ErrorLoopbackError OBJECT-IDENTITY
           STATUS      current
           DESCRIPTION "Expected data not received (or not received
                       correctly) in loopback test."
           ::= { dot3Errors 2 }

       -- { dot3 8 }, the dot3ChipSets tree, is defined in [28]

       -- conformance information

       etherConformance OBJECT IDENTIFIER ::= { etherMIB 2 }

       etherGroups      OBJECT IDENTIFIER ::= { etherConformance 1 }
       etherCompliances OBJECT IDENTIFIER ::= { etherConformance 2 }

       -- compliance statements

       etherCompliance MODULE-COMPLIANCE
           STATUS      deprecated
           DESCRIPTION "******** THIS COMPLIANCE IS DEPRECATED ********

                       The compliance statement for managed network
                       entities which have ethernet-like network
                       interfaces.

                       This compliance is deprecated and replaced by
                       dot3Compliance."

           MODULE  -- this module
               MANDATORY-GROUPS { etherStatsGroup }

               GROUP       etherCollisionTableGroup
               DESCRIPTION "This group is optional. It is appropriate
                           for all systems which have the necessary
                           metering. Implementation in such systems is
                           highly recommended."
           ::= { etherCompliances 1 }

       ether100MbsCompliance MODULE-COMPLIANCE
           STATUS      deprecated
           DESCRIPTION "******** THIS COMPLIANCE IS DEPRECATED ********

                       The compliance statement for managed network
                       entities which have 100 Mb/sec ethernet-like
                       network interfaces.

                       This compliance is deprecated and replaced by
                       dot3Compliance."

           MODULE  -- this module
               MANDATORY-GROUPS { etherStats100MbsGroup }

               GROUP       etherCollisionTableGroup
               DESCRIPTION "This group is optional. It is appropriate
                           for all systems which have the necessary
                           metering. Implementation in such systems is
                           highly recommended."
           ::= { etherCompliances 2 }

       dot3Compliance MODULE-COMPLIANCE
           STATUS      current
           DESCRIPTION "The compliance statement for managed network
                       entities which have ethernet-like network
                       interfaces."

           MODULE  -- this module
               MANDATORY-GROUPS { etherStatsBaseGroup }

               GROUP       etherDuplexGroup
               DESCRIPTION "This group is mandatory for all
                           ethernet-like network interfaces which are
                           capable of operating in full-duplex mode.
                           It is highly recommended for all
                           ethernet-like network interfaces."

               GROUP       etherStatsLowSpeedGroup
               DESCRIPTION "This group is mandatory for all
                           ethernet-like network interfaces which are
                           capable of operating at 10 Mb/s or slower in
                           half-duplex mode."

               GROUP       etherStatsHighSpeedGroup
               DESCRIPTION "This group is mandatory for all
                           ethernet-like network interfaces which are
                           capable of operating at 100 Mb/s or faster."

               GROUP       etherControlGroup
               DESCRIPTION "This group is mandatory for all
                           ethernet-like network interfaces that
                           support the MAC Control sublayer."

               GROUP       etherControlPauseGroup
               DESCRIPTION "This group is mandatory for all
                           ethernet-like network interfaces that
                           support the MAC Control PAUSE function."

               GROUP       etherCollisionTableGroup
               DESCRIPTION "This group is optional. It is appropriate
                           for all ethernet-like network interfaces
                           which are capable of operating in
                           half-duplex mode and have the necessary
                           metering. Implementation in systems with
                           such interfaces is highly recommended."

           ::= { etherCompliances 3 }

       -- units of conformance

       etherStatsGroup OBJECT-GROUP
           OBJECTS     { dot3StatsIndex,
                         dot3StatsAlignmentErrors,
                         dot3StatsFCSErrors,
                         dot3StatsSingleCollisionFrames,
                         dot3StatsMultipleCollisionFrames,
                         dot3StatsSQETestErrors,
                         dot3StatsDeferredTransmissions,
                         dot3StatsLateCollisions,
                         dot3StatsExcessiveCollisions,
                         dot3StatsInternalMacTransmitErrors,
                         dot3StatsCarrierSenseErrors,
                         dot3StatsFrameTooLongs,
                         dot3StatsInternalMacReceiveErrors,
                         dot3StatsEtherChipSet
                       }
           STATUS      deprecated
           DESCRIPTION "********* THIS GROUP IS DEPRECATED **********

                       A collection of objects providing information
                       applicable to all ethernet-like network
                       interfaces.

                       This object group has been deprecated and
                       replaced by etherStatsBaseGroup and
                       etherStatsLowSpeedGroup."
           ::= { etherGroups 1 }

       etherCollisionTableGroup OBJECT-GROUP
           OBJECTS     { dot3CollFrequencies
                       }
           STATUS      current
           DESCRIPTION "A collection of objects providing a histogram
                       of packets successfully transmitted after
                       experiencing exactly N collisions."
           ::= { etherGroups 2 }

       etherStats100MbsGroup OBJECT-GROUP
           OBJECTS     { dot3StatsIndex,
                         dot3StatsAlignmentErrors,
                         dot3StatsFCSErrors,
                         dot3StatsSingleCollisionFrames,
                         dot3StatsMultipleCollisionFrames,
                         dot3StatsDeferredTransmissions,
                         dot3StatsLateCollisions,
                         dot3StatsExcessiveCollisions,
                         dot3StatsInternalMacTransmitErrors,
                         dot3StatsCarrierSenseErrors,
                         dot3StatsFrameTooLongs,
                         dot3StatsInternalMacReceiveErrors,
                         dot3StatsEtherChipSet,
                         dot3StatsSymbolErrors
                       }
           STATUS      deprecated
           DESCRIPTION "********* THIS GROUP IS DEPRECATED **********

                       A collection of objects providing information
                       applicable to 100 Mb/sec ethernet-like network
                       interfaces.

                       This object group has been deprecated and
                       replaced by etherStatsBaseGroup and
                       etherStatsHighSpeedGroup."
           ::= { etherGroups 3 }

       etherStatsBaseGroup OBJECT-GROUP
           OBJECTS     { dot3StatsIndex,
                         dot3StatsAlignmentErrors,
                         dot3StatsFCSErrors,
                         dot3StatsSingleCollisionFrames,
                         dot3StatsMultipleCollisionFrames,
                         dot3StatsDeferredTransmissions,
                         dot3StatsLateCollisions,
                         dot3StatsExcessiveCollisions,
                         dot3StatsInternalMacTransmitErrors,
                         dot3StatsCarrierSenseErrors,
                         dot3StatsFrameTooLongs,
                         dot3StatsInternalMacReceiveErrors
                       }
           STATUS      current
           DESCRIPTION "A collection of objects providing information
                       applicable to all ethernet-like network
                       interfaces."
           ::= { etherGroups 4 }

       etherStatsLowSpeedGroup OBJECT-GROUP
           OBJECTS     { dot3StatsSQETestErrors }
           STATUS      current
           DESCRIPTION "A collection of objects providing information
                       applicable to ethernet-like network interfaces
                       capable of operating at 10 Mb/s or slower in
                       half-duplex mode."

           ::= { etherGroups 5 }

       etherStatsHighSpeedGroup OBJECT-GROUP
           OBJECTS     { dot3StatsSymbolErrors }
           STATUS      current
           DESCRIPTION "A collection of objects providing information
                       applicable to ethernet-like network interfaces
                       capable of operating at 100 Mb/s or faster."
           ::= { etherGroups 6 }

       etherDuplexGroup OBJECT-GROUP
           OBJECTS     { dot3StatsDuplexStatus }
           STATUS      current
           DESCRIPTION "A collection of objects providing information
                       about the duplex mode of an ethernet-like
                       network interface."

           ::= { etherGroups 7 }

       etherControlGroup OBJECT-GROUP
           OBJECTS     { dot3ControlFunctionsSupported,
                         dot3ControlInUnknownOpcodes
                       }
           STATUS      current
           DESCRIPTION "A collection of objects providing information
                       about the MAC Control sublayer on ethernet-like
                       network interfaces."
           ::= { etherGroups 8 }

       etherControlPauseGroup OBJECT-GROUP
           OBJECTS     { dot3PauseAdminMode,
                         dot3PauseOperMode,
                         dot3InPauseFrames,
                         dot3OutPauseFrames
                       }
           STATUS      current
           DESCRIPTION "A collection of objects providing information
                       about and control of the MAC Control PAUSE
                       function on ethernet-like network interfaces."
           ::= { etherGroups 9 }

   END
   
--------------------------------------------------------------------------
--
-- LAGSTATIC
--
--------------------------------------------------------------------------
    WAND-LAG-MIB DEFINITIONS ::= BEGIN

    IMPORTS
        MODULE-IDENTITY, OBJECT-TYPE,
        Integer32                               FROM SNMPv2-SMI   
        wandGeneric                             FROM WRS-MASTER-MIB ;                
----------------------------------------------------------
    zte MODULE-IDENTITY
        LAST-UPDATED    "2002-05-21-00"  -- August 29, 2000
        ORGANIZATION    "ZTE Corporation."
        CONTACT-INFO    "ZTE Corporation.
                         http://www.zte.com.cn"
        DESCRIPTION     "ZTE ADSL lan Bridge MIB OID defines and documentation."
        REVISION        "0008290000Z"  -- August 29, 2000
        DESCRIPTION     "Initial MIB creation."

        ::= { enterprises 3902 }
 
  wandComLagMib         OBJECT IDENTIFIER  ::= { wandGeneric 1 } 
  wandLagStatic         OBJECT IDENTIFIER  ::= {wandComLagMib 1}  

  wandDot8023adPortTable OBJECT-TYPE
        SYNTAX      SEQUENCE OF WandDot8023adPortEntry
        MAX-ACCESS  not-accessible
        STATUS      current
        DESCRIPTION
          "A table containing per port control and status
           information for port configuration in the device."
        ::= { wandLagStatic 1 }

    wandDot8023adPortEntry OBJECT-TYPE
        SYNTAX      WandDot8023adPortEntry
        MAX-ACCESS  not-accessible
        STATUS      current
        DESCRIPTION
        "Information controlling Aggregator configuration for a port
        on the device.  This is indexed by dot1dBasePort."
 	INDEX   {wandDot8023adPortId}
         ::= { wandDot8023adPortTable 1 }

    WandDot8023adPortEntry ::=
        SEQUENCE {
           wandDot8023adPortId  Integer32 ,
           wandDot8023adAggNo   Integer32
        }


	wandDot8023adPortId OBJECT-TYPE
  	SYNTAX      Integer32
  	MAX-ACCESS  not-accessible
  	STATUS      current
  	DESCRIPTION
      " the lag port id ,the range from 1 to 4"
  	REFERENCE
        ""
    ::= { wandDot8023adPortEntry 1 }
    
    wandDot8023adAggNo OBJECT-TYPE
        SYNTAX      Integer32
        MAX-ACCESS  read-write
        STATUS      current
        DESCRIPTION
          "The aggIndex  assigned to this port."
        REFERENCE
          "IEEE 802.3ad"
        ::= { wandDot8023adPortEntry 2 }
END

------------------------------------------------------------------------------
--
--  File         : wandCommMib.mib
--  Description  : ZTE WAND MIB  
--
------------------------------------------------------------------------------
WAND-COMM-MIB DEFINITIONS ::= BEGIN

	IMPORTS
			MODULE-IDENTITY, OBJECT-TYPE,
			enterprises					FROM SNMPv2-SMI
			MODULE-COMPLIANCE, OBJECT-GROUP			FROM SNMPv2-CONF		
			MacAddress                           FROM SNMPv2-TC
			wandCommMib                          FROM WRS-MASTER-MIB
			PortList, dot1qStaticMulticastEntry		FROM Q-BRIDGE-MIB;       

    wandCleanFlash OBJECT-TYPE
        SYNTAX INTEGER {
               noop(1),            -- no operation
               clean(2),           -- clean the data in flash
               cleanInProgress(3)  -- read-only: flash clean in progress
        }
        MAX-ACCESS read-write
        STATUS current
        DESCRIPTION
            "When set to 'clean(2)', the data in flash are cleaned . This
             operations may be slow . Consequently, all or many updates 
             should be made before cleaning the flash.  Note that the SNMP
             set to 'clean(2)' returns immediately to the caller.  Gets on
             this object then return  'cleanInProgress(3)' until the clean
             operation completes, at which time 'noop(1)' is returned.  
             Consequently, a get operation always returns 'noop(1)' or 
             'cleanInProgress(3)' depending on the current state.
            
             The agent returns 'badValue' for SNMPv1 or 'inconsistentValue'
             for SNMPv2c/v3 for a set to 'clean(2)' while the current get
             state is 'cleanInProgress(3)'.
             
             Attempts to set this object to 'cleanInProgress(3)' returns
             'badValue' for SNMPv1 or 'wrongValue' for SNMPv2c/v3."
        ::= { wandCommMib 1 }

    wandReset OBJECT-TYPE
        SYNTAX INTEGER {
               noop(1),           -- no operation
               reset(2),          -- reset unit
               resetToDefaults(3) -- reset to factory defaults/reset unit
        }
        MAX-ACCESS read-write
        STATUS current
        DESCRIPTION
            "Physically performs a hardware reset of the unit. 
             Use with care.  A 'reset(2)' resets the unit, a
             'resetToDefaults(3)' resets the NVM configuration
             to factory defaults and then resets the unit, and 'noop(1)'
             does nothing.  A value of 'noop(1)' is always returned for a
             GET operation."
        ::= { wandCommMib 2 }

    wandVersionNumber OBJECT-TYPE
        SYNTAX OCTET STRING (SIZE (0..4))
        MAX-ACCESS read-only
        STATUS current
        DESCRIPTION
            "Get this MIB Major version number.  This number should 
             match the Major version given in the documentation header
             at the beginning text of this MIB.  Note that the '.c' file
             corresponding to this MIB has to be manually edited to
             change the version number if this file is modified and
             the version number is therefore changed."
        ::= { wandCommMib 3 }


    wandSaveFlash OBJECT-TYPE
        SYNTAX INTEGER {
               noop(1),           -- no operation
               save(2),           -- save all configuration parameters to NVM
               saveInProgress(3)  -- read-only: NVM save in progress
        }
        MAX-ACCESS read-write
        STATUS current
        DESCRIPTION
            "When set to 'save(2)', all nonvolatile configuration
             parameters are saved to NVM (Nonvolatile Memory).  NVM save
             operations may be slow (e.g., erasing/writing Flash device).
             Consequently, all or many updates should be made before
             saving to NVM.  Note that the SNMP set to 'save(2)' returns
             immediately to the caller.  Gets on this object then return
             'saveInProgress(3)' until the save operation completes, at
             which time 'noop(1)' is returned.  Consequently, a get
             operation always returns 'noop(1)' or 'saveInProgress(3)'
             depending on the current state.
             
             The agent returns 'badValue' for SNMPv1 or 'inconsistentValue'
             for SNMPv2c/v3 for a set to 'Save(2)' while the current get
             state is 'saveInProgress(3)'.
             
             Attempts to set this object to 'saveInProgress(3)' returns
             'badValue' for SNMPv1 or 'wrongValue' for SNMPv2c/v3."
        ::= { wandCommMib 4 }

    wandSpanOnOff OBJECT-TYPE
        SYNTAX INTEGER {
               enable(1),
               disable(2)
        }
        MAX-ACCESS read-write
        STATUS current
        DESCRIPTION
            "DURABLE: { enable }
             Enable/Disable Spanning Tree for the bridge.
             When 'disable(2)', all ports of the device are placed in the
             forwarding mode, regardless of current Spanning Tree state.
             When 'enable(1)', the normal STP state transitions take place."
        ::= { wandCommMib 5 }

    wandLACPOnOff OBJECT-TYPE
        SYNTAX INTEGER {
               enable(1),
               disable(2)
        }
        MAX-ACCESS read-write
        STATUS current
        DESCRIPTION
            "DURABLE: { disable }
             Enable/Disable LACP operation for the TMS agent.
             When 'disable(2)', no LACP's are transmitted by the Application.
             When enabled, the Application sends LACP requests during
             system startup."
        ::= { wandCommMib 6 }

       wandBroadcasdOnOff OBJECT-TYPE
               SYNTAX INTEGER {
               enable(1),
               disable(2)
        }
        MAX-ACCESS read-write
        STATUS current
        DESCRIPTION
            "DURABLE: { disable }
             disable/enable forward broadcast pkt to ARM  "
        ::= { wandCommMib 7 }
      
       wandMulticastOnOff OBJECT-TYPE
               SYNTAX INTEGER {
               enable(1),
               disable(2)
        }
        MAX-ACCESS read-write
        STATUS current
        DESCRIPTION
            "DURABLE: { disable }
             disable/enable forward multicast  pkt to ARM  "
        ::= { wandCommMib 8 }        
        

    wandBoardID  OBJECT-TYPE
        SYNTAX INTEGER 
        MAX-ACCESS read-only
        STATUS current
        DESCRIPTION
            "wand Board standing in the dislam"
        ::= { wandCommMib 9 }
       
   wandCommonIPMACAddr OBJECT-TYPE
        SYNTAX MacAddress
        MAX-ACCESS read-write
        STATUS current
        DESCRIPTION
            "DURABLE: { '000000000000'H }
             The base (i.e., first) MAC address used by the TMS agent for its
             in-band ports."
        ::= { wandCommMib 10 }


    wandIgmpSnoopOnOff  OBJECT-TYPE
        SYNTAX INTEGER {
               enable(1),
               disable(2)
        }
        MAX-ACCESS read-write
        STATUS current
        DESCRIPTION
            "DURABLE: { disable }
             Enable/Disable IGMP Snooping operation for the TMS agent.
             Setting this object to enable(1) enables IGMP Snooping.  Setting
             it to disable(2) disables IGMP Snooping.
             
             Note that IGMP Snooping can function with or without GVRP and
             GMRP enabled."
        ::= { wandCommMib 11}

    wandIgmpSnoopAlertsOnOff  OBJECT-TYPE
        SYNTAX INTEGER {
               enable(1),
               disable(2)
        }
        MAX-ACCESS read-write
        STATUS current
        DESCRIPTION
            "DURABLE: { disable }
             Setting this object to enable(1) enables the IP Router Alert
             Option (as defined in RFC2113) for transmitted IGMP packets.
             Setting it to disable(2) disables this option."
        ::= { wandCommMib 12 }

    wandIgmpSnoopAging  OBJECT-TYPE
        SYNTAX INTEGER (30..3600)
        MAX-ACCESS read-write
        STATUS current
        DESCRIPTION
            "DURABLE: { 300 }
             The timeout period in seconds for aging out Multicast Groups
             dynamically learned with IGMP Snooping.  Note that aging operates
             on a per interface per VLAN per multicast group basis."
        ::= { wandCommMib 13 }

    wandIgmpSnoopTable OBJECT-TYPE
        SYNTAX           SEQUENCE OF WandIgmpSnoopEntry
        MAX-ACCESS not-accessible
        STATUS current
        DESCRIPTION
            "This table, which provides IGMP Snooping information, augments
             the 'dot1qStaticMulticastTable' in the Q-MIB (RFC2674)."
        ::= { wandCommMib 14 }

    wandIgmpSnoopEntry OBJECT-TYPE
        SYNTAX 	WandIgmpSnoopEntry
        MAX-ACCESS not-accessible
        STATUS current
        DESCRIPTION
            "Displays by VLAN, Multicast Group, and Multicast receive port
             the set of ports enabled to forward Multicast Group traffic as
             determined by the IGMP Snooping task."
        AUGMENTS { dot1qStaticMulticastEntry }
        ::= { wandIgmpSnoopTable 1 }

    WandIgmpSnoopEntry ::= SEQUENCE {
        wandIgmpSnoopEgressPorts   PortList
    }

    wandIgmpSnoopEgressPorts  OBJECT-TYPE
        SYNTAX PortList
        MAX-ACCESS read-only
        STATUS current
        DESCRIPTION
            "This read-only object displays the set of ports enabled to
             forward specific Multicast Group traffic as determined by the
             IGMP Snooping task.
            
             It should be noted that the IGMP Snooping task generates a pseudo-
             static (i.e., not saved in NVM) port list similar to the RFC2674
             Q-MIB 'dot1qStaticMulticastStaticEgressPorts' object. Consequently,
             a port will not be a member of 'tmsCommonIgmpSnoopEgressPorts' if
             it is a member of 'dot1qStaticMulticastForbiddenEgressPorts'."
        ::= { wandIgmpSnoopEntry 1 }

     wandBoradcastToAtmPortStatus  OBJECT-TYPE
        SYNTAX INTEGER {
               enable(1),
               disable(2)
        }
        MAX-ACCESS read-write
        STATUS current
        DESCRIPTION
            " "
           ::= { wandCommMib 15 }

     wandStatisticStatus  OBJECT-TYPE
        SYNTAX INTEGER {
               enable(1),
               disable(2)
        }
        MAX-ACCESS read-write
        STATUS current
        DESCRIPTION
            "enable or disable the port statistics information  "
           ::= { wandCommMib 16 }
           
      
      wandFloodToAtmPortStatus OBJECT-TYPE
               SYNTAX INTEGER {
               enable(1),
               disable(2)
        }
        MAX-ACCESS read-write
        STATUS current
        DESCRIPTION
            "DURABLE: { disable }
             disable/enable forward flood unicast pkt to ARM  "
        ::= { wandCommMib 17 }
        
       
       wandMuliticastToAtmPortStatus OBJECT-TYPE
               SYNTAX INTEGER {
               enable(1),
               disable(2)
        }
        MAX-ACCESS read-write
        STATUS current
        DESCRIPTION
            "DURABLE: { disable }
             disable/enable forward multciast pkt to ARM  "
        ::= { wandCommMib 18 }

-- END of LAN-MIB                
END


-------------------------------------------------------------------------
--
--  WANDPVCMIB
--
-------------------------------------------------------------------------
------------------------------------------------------------------------------
--
--  File         : wandPvcMIB.mib
--  Description  : ZTE ADSL WAND PVC MANAGER MIB  
--
------------------------------------------------------------------------------
WAND-PVC-MIB DEFINITIONS ::= BEGIN

	IMPORTS
    		MODULE-IDENTITY, OBJECT-TYPE,
    		Counter32, Counter64, Unsigned32, TimeTicks,
			  Integer32, enterprises					FROM SNMPv2-SMI
    
    		RowStatus, TruthValue, TEXTUAL-CONVENTION, MacAddress
        											FROM SNMPv2-TC
        											
			  MODULE-COMPLIANCE, OBJECT-GROUP			FROM SNMPv2-CONF
		    wandPvcMib									        FROM WRS-MASTER-MIB
			  dot1dBridge, dot1dBasePortEntry, dot1dBasePort
													FROM BRIDGE-MIB;


wandCurrManagePortNum  OBJECT-TYPE
    SYNTAX      INTEGER
    MAX-ACCESS  read-only
    STATUS      current
    DESCRIPTION
        "all ports in the system at present"
    REFERENCE
        ""
    ::= { wandPvcMib 1 }


wandPvcManagerTable   OBJECT-TYPE
		SYNTAX      SEQUENCE OF WandPvcManagerEntry
    MAX-ACCESS  not-accessible
    STATUS      current
    DESCRIPTION
        " "
    ::= { wandPvcMib 2 }

wandPvcManagerEntry OBJECT-TYPE
    SYNTAX      WandPvcManagerEntry
    MAX-ACCESS  not-accessible
    STATUS      current
    DESCRIPTION
        ""
    INDEX   {VPI ,VCI}
    ::= { wandPvcManagerTable 1 }

WandPvcManagerEntry ::=
    SEQUENCE {
        VPI
             INTEGER,
        VCI
             INTEGER,
        port
             INTEGER,      
              
        pvcMacNumSupport
             INTEGER,
             
        pvcPortForwBroad
             INTEGER,
             
        pvcPortPriority
             INTEGER ,  
              
        pvcRowStatus 
             RowStatus
        
    }

VPI OBJECT-TYPE
  SYNTAX      INTEGER
  MAX-ACCESS  not-accessible
  STATUS      current
  DESCRIPTION
      " the vpi index of wand pvc port "
  REFERENCE
        ""
    ::= { wandPvcManagerEntry 1 }

VCI OBJECT-TYPE
    SYNTAX      INTEGER 
    MAX-ACCESS  not-accessible
    STATUS      current
    DESCRIPTION
 				 " the vci index of wand pvc port "
    REFERENCE
        ""
    ::= { wandPvcManagerEntry 2 }
    
port OBJECT-TYPE
  SYNTAX      INTEGER
  MAX-ACCESS  read-only
  STATUS      current
  DESCRIPTION
      " according vpi and vpi ,to get the port id "
  REFERENCE
        ""
    ::= { wandPvcManagerEntry 3 }

pvcMacNumSupport OBJECT-TYPE
  SYNTAX      INTEGER
  MAX-ACCESS  read-write
  STATUS      current
  DESCRIPTION
      "the learning macaddresses of every pvc port"
  REFERENCE
        ""
    ::= { wandPvcManagerEntry 4}

pvcPortForwBroad OBJECT-TYPE
 SYNTAX INTEGER {
               enable(1),           
               disable(2)
             }
            
  MAX-ACCESS  read-write
  STATUS      current
  DESCRIPTION
      " disable/enable the port receive broad packet"
  REFERENCE
        ""
    ::= { wandPvcManagerEntry 5}

pvcPortPriority OBJECT-TYPE
  SYNTAX      INTEGER(0..7)
  MAX-ACCESS  read-write
  STATUS      current
  DESCRIPTION
      "the prority of every pvc port"
  REFERENCE
        ""
    ::= { wandPvcManagerEntry 6}

pvcRowStatus OBJECT-TYPE
    SYNTAX      RowStatus
    MAX-ACCESS  read-create
    STATUS      current
    DESCRIPTION
        "the create port command object"
    ::= { wandPvcManagerEntry 7 }

-- END of WAND-BRIDGE-MIB                
END

----
--- IXPOEM.MIB
---
    WAND-OEM-BCM5600-MIB DEFINITIONS ::= BEGIN

    IMPORTS
        MODULE-IDENTITY, OBJECT-TYPE,
        Integer32, Counter64                    FROM SNMPv2-SMI
        
        DisplayString, TruthValue               FROM SNMPv2-TC
        
        MODULE-COMPLIANCE, OBJECT-GROUP         FROM SNMPv2-CONF
        
        wandOemProd                             FROM WRS-MASTER-MIB;       

    wandBcm5600 MODULE-IDENTITY
        LAST-UPDATED    "0105030000Z"  -- May 03,2001  
        ORGANIZATION    "Wind River Systems, Inc."
        CONTACT-INFO    "Wind River Systems, Inc.
                         E-mail: support@windriver.com"

        DESCRIPTION     "TMS Broadcom BCM5600 StrataSwitch OEM-Product
                         Enterprise MIB definition."

        REVISION        "0105030000Z"  -- May 03,2001
        DESCRIPTION     "Initial MIB creation."

        ::= { wandOemProd 2 }

------------------------------------------------------------------------------
-- Textual Conventions (i.e., these do not affect object encoding):
------------------------------------------------------------------------------
--
-- "DURABLE":
--    Objects that are saved across a system reset and/or power cycle
--    are noted as "DURABLE" for convenience in the DESCRIPTION
--    section of the object definition.  Code must be explicitly
--    written to implement these DURABLE objects.
--

------------------------------------------------------------------------------
--  define groups in OEM-BCM5600-MIB
------------------------------------------------------------------------------
    wandOemArchIface            OBJECT IDENTIFIER ::= { wandBcm5600 1 }
    wandOemChip                 OBJECT IDENTIFIER ::= { wandBcm5600 2 }
    wandOemProdConformance      OBJECT IDENTIFIER ::= { wandBcm5600 3 }
    wandOemProdGroups           OBJECT IDENTIFIER ::= { wandOemProdConformance 1 }
    wandOemProdCompliances      OBJECT IDENTIFIER ::= { wandOemProdConformance 2 }


    wandOemArchIfaceTable OBJECT-TYPE
        SYNTAX SEQUENCE OF WandOemArchIfaceEntry
        MAX-ACCESS not-accessible
        STATUS current
        DESCRIPTION
            "A table of switch interfaces and associated properties."
        ::= { wandOemArchIface 1 }

    wandOemArchIfaceEntry OBJECT-TYPE
        SYNTAX WandOemArchIfaceEntry
        MAX-ACCESS not-accessible
        STATUS current
        DESCRIPTION
            "Table entry for switch interface control and status information."
        INDEX { wandOemArchIfaceUnit, wandOemArchIfacePort }
        ::= { wandOemArchIfaceTable 1 }

    WandOemArchIfaceEntry ::= SEQUENCE {
        wandOemArchIfaceUnit                Integer32,
        wandOemArchIfacePort                Integer32,
        wandOemArchIfaceLLWHPort            Integer32,
        wandOemArchIfaceIfIndex             Integer32,
        wandOemArchIfaceName                DisplayString,
        wandOemArchIfaceEnable              TruthValue,
        wandOemArchIfaceLink                INTEGER,
        wandOemArchIfaceDuplexSpeed         INTEGER
    }

    wandOemArchIfaceUnit OBJECT-TYPE
        SYNTAX Integer32 (1..4)
        MAX-ACCESS not-accessible
        STATUS current
        DESCRIPTION
            "An index that uniquely identifies a unit in the TMS BCM5600
             stack.  If an invalid value is used for the index, a SNMP
             'noSuchName' error (SNMPv1) or 'noSuchInstance' exception
             (SNMPv2/v3) is returned.  For implementations that do not support
             stacking, the same response is returned for any unit index other
             than 1."
        ::= { wandOemArchIfaceEntry 1 }

    wandOemArchIfacePort OBJECT-TYPE
        SYNTAX Integer32 (1..26)
        MAX-ACCESS not-accessible
        STATUS current
        DESCRIPTION
            "An index that uniquely identifies a TMS Application 'logical port'
             (i.e., IEEE 802.3ad Aggregator) within the oemArchIfaceUnit."
        ::= { wandOemArchIfaceEntry 2 }

    wandOemArchIfaceLLWHPort OBJECT-TYPE
        SYNTAX Integer32 (8193..8296)
        MAX-ACCESS read-only
        STATUS current
        DESCRIPTION
            "A value that uniquely identifies a TMS Application 'logical port'
             (i.e., IEEE 802.3ad Aggregator) in the TMS BCM5600 stack.  This is
             a 'Layered Linear With Holes' (LLWH) port number that may may have
             holes for missing ports or units.  For this MIB, 26 port numbers
             are reserved for each unit in the stack.  For example, LLHW port
             8193 is unit 1, port 1 and LLHW 8228 is unit 2, port 10."
        ::= { wandOemArchIfaceEntry 3 }

    wandOemArchIfaceIfIndex OBJECT-TYPE
        SYNTAX Integer32
        MAX-ACCESS read-only
        STATUS current
        DESCRIPTION
            "The ifIndex of this TMS Application 'logical port' (i.e., IEEE
             802.3ad Aggregator).  Note that an ifIndex value of 34603009 
             (0x02100001) represents the Aggregator layer, unit 1, slot 0
             (base unit ports), port 1."
        ::= { wandOemArchIfaceEntry 4 }

    wandOemArchIfaceName OBJECT-TYPE
        SYNTAX DisplayString (SIZE (0..16))
        MAX-ACCESS read-write
        STATUS current
        DESCRIPTION
            "DURABLE:
             The textual name of this interface, e.g., 'John'."
        ::= { wandOemArchIfaceEntry 5 }

    wandOemArchIfaceEnable OBJECT-TYPE
        SYNTAX TruthValue
        MAX-ACCESS read-write
        STATUS current
        DESCRIPTION
            "DURABLE: { true:all }
             This object is true(1) when this interface is enabled and
             false(1) when it is disabled.  For this product, this is the
             ONLY way to enable or disable this interface.  Note that
             'ifAdminStatus' in RFC1213 and RFC2233 and 'dot1dStpPortEnable'
             in RFC1493 are each implemented as 'read-only'."
        ::= { wandOemArchIfaceEntry 6 }

    wandOemArchIfaceLink OBJECT-TYPE
        SYNTAX INTEGER {
             up(1), 
             down(2)
        }
        MAX-ACCESS read-only
        STATUS current
        DESCRIPTION
            "The state of Link Detect on this interface."
        ::= { wandOemArchIfaceEntry 7 }

   wandOemArchIfaceDuplexSpeed OBJECT-TYPE
        SYNTAX INTEGER {
             autonegotiate(1),
             half-10(2),
             full-10(3),
             half-100(4),
             full-100(5),
             illegal(99)
        }
        MAX-ACCESS read-write
        STATUS current
        DESCRIPTION
            "DURABLE: { autonegotiate:all }
            The desired speed and duplex for this interface. If the selected
            control is not possible on the interface, a value of illegal(99)
            is returned.  If the port type does NOT support the default
            of autonegotiate(1), then the application initializes the
            port to a valid value (e.g., 1000full(6)).  Note that not all
            controls are possible for all interfaces.  For example, only
            full-1000(6) is available for Gigabit Ethernet interfaces."
        ::= { wandOemArchIfaceEntry 8 }

------------------------------------------------------------------------------
--  Chip Interface Section  
------------------------------------------------------------------------------
--
    wandOemChipStub OBJECT-TYPE
        SYNTAX INTEGER {  
            noop(1),
            chip-value2(2),
            chip-value3(3)
        }
        MAX-ACCESS read-write
        STATUS current
        DESCRIPTION
            "This object is a place holder for the OEM Chip interface." 
        ::= { wandOemChip 1 }


------------------------------------------------------------------------------
--  conformance information
------------------------------------------------------------------------------

--  --------------------------------------------------------------------------
--  units of conformance
--  --------------------------------------------------------------------------

    wandOemArchIfaceGroup   OBJECT-GROUP
        OBJECTS {
            wandOemArchIfaceLLWHPort,
            wandOemArchIfaceIfIndex,
            wandOemArchIfaceName,
            wandOemArchIfaceEnable,
            wandOemArchIfaceLink,
            wandOemArchIfaceDuplexSpeed
           }
        STATUS  current
        DESCRIPTION
           "This group configures and retrieves Architecture interface
            specific objects."
        ::= { wandOemProdGroups 1 }
    
    wandOemChipGroup    OBJECT-GROUP
        OBJECTS {
            wandOemChipStub
        }
        STATUS  current
        DESCRIPTION
           "This group configures OEM Chip specific objects."
        ::= { wandOemProdGroups 2 }
    

--  --------------------------------------------------------------------------
--  compliance statements
--  --------------------------------------------------------------------------

    wandOemProdCompliance MODULE-COMPLIANCE
        STATUS  current
        DESCRIPTION
           "The compliance statement."
        MODULE  -- this module
        MANDATORY-GROUPS {
             wandOemArchIfaceGroup
        }
        
    GROUP   wandOemChipGroup
    DESCRIPTION
        "This group is optional."
        
        ::= { wandOemProdCompliances 1 }

--
-- END of OEM-BCM5600-MIB                
--

END
