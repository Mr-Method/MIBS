----------------------------------------------------------------------------
-- WRS-MASTER-MIB,TMS-L3-MIB,OEMMIB,OEMZXEDSL,OEMRADIUSMIB
-- 
-- reference mib file of edsl (9210,9426):
--     IEEE8021-PAE-MIB,ADSL-LINE-MIB.mib
--
----------------------------------------------------------------------------


WRS-MASTER-MIB DEFINITIONS ::= BEGIN

IMPORTS
    MODULE-IDENTITY, enterprises              FROM SNMPv2-SMI;

    zte MODULE-IDENTITY
        LAST-UPDATED    "0110290000Z"  -- Octember 29, 2001
        ORGANIZATION    "Zhongxing Telcom Co. Ltd."
        CONTACT-INFO    "Zhongxing Telcom Co. Ltd.
                         E-mail: info@mail.zte.com.cn
                         http   : www.zte.com.cn or www.zhongxing.com"

        DESCRIPTION     "zte MIB OID defines and documentation."

        REVISION        "0110290000Z"  -- Octember 29, 2001
        DESCRIPTION     "Initial MIB creation."

        ::= { enterprises 3902 }
    
-- zte Products
   zxEdsl               OBJECT IDENTIFIER ::= { zte 1008 }
   zxEdslOwn            OBJECT IDENTIFIER ::= { zxEdsl  1 }
   zxEdslLR1            OBJECT IDENTIFIER ::= { zxEdslOwn 1 }

    tms             OBJECT IDENTIFIER ::= { zxEdslLR1 1 }
--  tms1_0          OBJECT IDENTIFIER ::= { wrs 1 } Obsolete

-- TMS Major MIB Categories
    idb             OBJECT IDENTIFIER ::= { tms 1 }     -- IDB MIBs
    tmsGeneric      OBJECT IDENTIFIER ::= { tms 2 }     -- TMS Generic MIBs
    oemSwapi        OBJECT IDENTIFIER ::= { tms 3 }     -- OEM swAPI MIBs
    oemProd         OBJECT IDENTIFIER ::= { tms 4 }     -- OEM Product MIBs

-- TMS IDB Internal Module MIBs
    rmonMib         OBJECT IDENTIFIER ::= { idb 1 }
    
--
-- END of WRS-MASTER-MIB
--

END


TMS-COMMON-MIB DEFINITIONS ::= BEGIN

    IMPORTS
        MODULE-IDENTITY, OBJECT-TYPE,
        Integer32, IpAddress, 
        NOTIFICATION-TYPE                       FROM SNMPv2-SMI
        
        DisplayString, MacAddress,
        RowStatus, TruthValue                   FROM SNMPv2-TC
        
        MODULE-COMPLIANCE, OBJECT-GROUP         FROM SNMPv2-CONF
        
        tmsGeneric                              FROM WRS-MASTER-MIB
        
        SnmpAdminString                         FROM SNMP-FRAMEWORK-MIB

        PortList, dot1qStaticMulticastEntry     FROM Q-BRIDGE-MIB;       

    tmsCommonMib MODULE-IDENTITY
        LAST-UPDATED    "0011020000Z"  -- November 2, 2000
        ORGANIZATION    "Wind River Systems, Inc."
        CONTACT-INFO    "Wind River Systems, Inc.
                         E-mail: support@windriver.com"

        DESCRIPTION     "TMS Common Enterprise MIB definition."

        REVISION        "0011020000Z"  -- November 2, 2000
        DESCRIPTION     "Initial MIB creation."

        ::= { tmsGeneric 1 }


------------------------------------------------------------------------------
--  Textual Conventions (i.e., these do not affect object encoding):
------------------------------------------------------------------------------
    --
    --  "DURABLE":
    --    Objects that are saved across a system reset and/or power cycle
    --    are noted as "DURABLE" for convenience in the DESCRIPTION
    --    section of the object definition.  Code must be explicitly
    --    written to implement these DURABLE objects.
    --

------------------------------------------------------------------------------
--  define groups in TMS-COMMON-MIB
------------------------------------------------------------------------------
    tmsCommonNotify         OBJECT IDENTIFIER ::= { tmsCommonMib 0 }
    tmsCommonVer            OBJECT IDENTIFIER ::= { tmsCommonMib 1 }
    tmsCommonIP             OBJECT IDENTIFIER ::= { tmsCommonMib 2 }
--  tmsCommonAuth           OBJECT IDENTIFIER ::= { tmsCommonMib 3 } obsolete
--  tmsCommonTrap           OBJECT IDENTIFIER ::= { tmsCommonMib 4 } obsolete
    tmsCommonLoad           OBJECT IDENTIFIER ::= { tmsCommonMib 5 }
    tmsCommonMisc           OBJECT IDENTIFIER ::= { tmsCommonMib 6 }
    tmsCommonCommToView     OBJECT IDENTIFIER ::= { tmsCommonMib 7 }
    tmsCommonIgmpSnoop      OBJECT IDENTIFIER ::= { tmsCommonMib 8 }
    tmsCommonConformance    OBJECT IDENTIFIER ::= { tmsCommonMib 9 }
    tmsCommonTrapTarget     OBJECT IDENTIFIER ::= { tmsCommonMib 10 }    
    
    tmsCommonMiscZteTest     OBJECT IDENTIFIER ::= { tmsCommonMib 19 }
    tmsCommonMiscTrap       OBJECT IDENTIFIER ::= { tmsCommonMib 20 }
    tmsCommonSysLog         OBJECT IDENTIFIER ::= { tmsCommonMib 21 } 
    tmsCommonGroups         OBJECT IDENTIFIER ::= { tmsCommonConformance 1 }
    tmsCommonCompliances    OBJECT IDENTIFIER ::= { tmsCommonConformance 2 }
    --

------------------------------------------------------------------------------
--
--  tmsCommonVer - Version Group                    
--
--  This group enables the retrieval of version information for 
--  various components in the system.
--
--  Some version numbers have the concept of "Major.Minor" designators.
--  In these version numbers, the Major designator represents the
--  primary release version, while the Minor designator represents
--  the secondary version, incremented for bug-fixes or non-critical
--  modifications.  For example, the version number 1.2 has "1" as
--  the Major version number and "2" as the minor version number.
--
------------------------------------------------------------------------------
--
    tmsCommonVerMIBMajor OBJECT-TYPE
        SYNTAX Integer32
        MAX-ACCESS read-only
        STATUS current
        DESCRIPTION
            "Get this MIB Major version number.  This number should 
             match the Major version given in the documentation header
             at the beginning text of this MIB.  Note that the '.c' file
             corresponding to this MIB has to be manually edited to
             change the version number if this file is modified and
             the version number is therefore changed."
        ::= { tmsCommonVer 1 }

    tmsCommonVerMIBMinor OBJECT-TYPE
        SYNTAX Integer32
        MAX-ACCESS read-only
        STATUS current
        DESCRIPTION
            "Get this MIB Minor version number.  This number should 
             match the Minor version given in the documentation header
             at the beginning text of this MIB. Note that the '.c' file
             corresponding to this MIB has to be manually edited to
             change the version number if this file is modified and
             the version number is therefore changed."
        ::= { tmsCommonVer 2 }

    tmsCommonVerBootSWMajor OBJECT-TYPE
        SYNTAX Integer32
        MAX-ACCESS read-only
        STATUS current
        DESCRIPTION
            "Get the Boot Software Major version number.
             This number references the VxWorks TMS Boot ROM module."
        ::= { tmsCommonVer 3 }

    tmsCommonVerBootSWMinor OBJECT-TYPE
        SYNTAX Integer32
        MAX-ACCESS read-only
        STATUS current
        DESCRIPTION
            "Get the Boot Software Minor version number.
             This number references the VxWorks TMS Boot ROM module."
        ::= { tmsCommonVer 4 }

    tmsCommonVerAppSWMajor OBJECT-TYPE
        SYNTAX Integer32
        MAX-ACCESS read-only
        STATUS current
        DESCRIPTION
            "Get the Application Software Major version number.  
             This number references the core TMS modules as a whole."
        ::= { tmsCommonVer 5 }

    tmsCommonVerAppSWMinor OBJECT-TYPE
        SYNTAX Integer32
        MAX-ACCESS read-only
        STATUS current
        DESCRIPTION
            "Get the Application Software Minor version number.  
             This number references the core TMS modules as a whole."
        ::= { tmsCommonVer 6 }

    tmsCommonZteMasterSCBVerName OBJECT-TYPE
        SYNTAX         DisplayString (SIZE (1..50))
        MAX-ACCESS     read-write
        STATUS         current
        DESCRIPTION
            "Version name or number in master System Control Borad."
        ::= { tmsCommonVer 7 }

    tmsCommonZteSlaveSCBVerName OBJECT-TYPE
        SYNTAX         DisplayString (SIZE (1..50))
        MAX-ACCESS     read-write
        STATUS         current
        DESCRIPTION
            "Version name or number in slave System Control Borad."
        ::= { tmsCommonVer 8 }

    tmsCommonZteMasterSCBVerState OBJECT-TYPE
        SYNTAX         INTEGER{
                        new(1),
                 test(2),
                 valid(3),
                 invalid(4)
                        }
        MAX-ACCESS     read-only
        STATUS         current
        DESCRIPTION
            "Version state in master System Control Borad."
        ::= { tmsCommonVer 9 }

    tmsCommonZteSlaveSCBVerState OBJECT-TYPE
        SYNTAX         INTEGER{
                        new(1),
                 test(2),
                 valid(3),
                 invalid(4)
                        }
        MAX-ACCESS     read-only
        STATUS         current
        DESCRIPTION
            "Version state in slave System Control Borad."
        ::= { tmsCommonVer 10 }

    tmsCommonZteMasterSCBVerSize OBJECT-TYPE
        SYNTAX Integer32
        MAX-ACCESS read-only
        STATUS current
        DESCRIPTION
            "Version size in master System Control Borad."
        ::= { tmsCommonVer 11 }

    tmsCommonZteSlaveSCBVerSize OBJECT-TYPE
        SYNTAX Integer32
        MAX-ACCESS read-only
        STATUS current
        DESCRIPTION
            "Version size in slave System Control Borad."
        ::= { tmsCommonVer 12 }

    tmsCommonBootVer OBJECT-TYPE
        SYNTAX OCTET STRING(0..32)
        MAX-ACCESS read-only
        STATUS current
        DESCRIPTION
            ""
        ::= { tmsCommonVer 13 }
   
    tmsCommonAppVer OBJECT-TYPE
        SYNTAX OCTET STRING(0..32)
        MAX-ACCESS read-only
        STATUS current
        DESCRIPTION
            ""
        ::= { tmsCommonVer 14 }

------------------------------------------------------------------------------
--
--  tmsCommonIP - IP Connectivity Information         
--
--  This group is meant to be a collection of controls and data 
--  that configure the device for IP connectivity.
--
------------------------------------------------------------------------------
--
    tmsCommonIPMACAddr OBJECT-TYPE
        SYNTAX MacAddress
        MAX-ACCESS read-only
        STATUS current
        DESCRIPTION
            "DURABLE: { '000000000000'H }
             The base (i.e., first) MAC address used by the TMS agent for its
             in-band ports."
        ::= { tmsCommonIP 1 }

    tmsCommonIPIpAddress OBJECT-TYPE
        SYNTAX IpAddress
        MAX-ACCESS read-write
        STATUS current
        DESCRIPTION
            "DURABLE: { '00000000'H }
             The IP Address for sw0 (swEND 0); only applies after reset - 
             see 'tmsCommonMiscReset'."
        ::= { tmsCommonIP 2 }

    tmsCommonIPGateAddress OBJECT-TYPE
        SYNTAX IpAddress
        MAX-ACCESS read-write
        STATUS current
        DESCRIPTION
            "DURABLE: { '00000000'H }
             The default Gateway Address (i.e., next hop router) for sw0
             (swEND 0); only applies after reset - see 'tmsCommonMiscReset'."
        ::= { tmsCommonIP 3 }

    tmsCommonIPNetMask OBJECT-TYPE
        SYNTAX IpAddress
        MAX-ACCESS read-write
        STATUS current
        DESCRIPTION
            "DURABLE: { 'ffffff00'H }
             The IP NetMask for sw0 (swEND 0); only applies after reset - 
             see 'tmsCommonMiscReset'."
        ::= { tmsCommonIP 4 }

    tmsCommonIPStatus OBJECT-TYPE
        SYNTAX INTEGER {
               notModified(1),
               modified(2),
               restore(3),
               apply(4)
        }
        MAX-ACCESS read-write
        STATUS current
        DESCRIPTION
            "This object is used to synchronize the modification of the IP
            parameters used by the protocol stack based on the tmsCommonIP
            MIB objects.  This allows the user to change tmsCommonIPMACAddr, 
            tmsCommonIPIpAddress, tmsCommonIPGateAddress, and
            tmsCommonIPNetMask, and then apply the changes to the unit
            using apply(4).  If tmsCommonIPStatus returns notModified(1),
            no modifications were made to any tmsCommonIP MIB objects.
            If tmsCommonIPStatus returns modified(2), one or more objects
            were changed, but have not been applied.  Both notModified(1)
            and modified(2) are read-only values; the agent returns a
            SNMP_BADVALUE for sets using these values.  Both restore(3) and
            apply(4) are valid SET values.  If one or more of the tmsCommonIP
            objects were modified, the user can restore the parameters to a
            mirror of the NVM values using restore(3)."
        ::= { tmsCommonIP 5 }


------------------------------------------------------------------------------
--
--  tmsCommonLoad - Load TFTP Group                    
--
--  This group is a collection of objects used to configure the TFTP file
--  download and upload facilities.  This group may be used to upload and
--  download the NVM configuration file or to download either the TMS
--  Application or Boot image.
--
------------------------------------------------------------------------------
--
    tmsCommonLoadTftpAddress OBJECT-TYPE
        SYNTAX IpAddress
        MAX-ACCESS read-write
        STATUS current
        DESCRIPTION
            "DURABLE:
             The IP Address for the TFTP server used for downloading
             and/or uploading files." 
        ::= { tmsCommonLoad 1 }

    tmsCommonLoadTftpFileName OBJECT-TYPE
        SYNTAX DisplayString (SIZE (1..64))
        MAX-ACCESS read-write
        STATUS current
        DESCRIPTION
            "DURABLE:
             The TFTP file path and name."
        ::= { tmsCommonLoad 2 }

    tmsCommonLoadType OBJECT-TYPE
        SYNTAX INTEGER {
               application(1),
               boot(2),
               configuration(3)
        }
        MAX-ACCESS read-write
        STATUS current
        DESCRIPTION
            "DURABLE: { application }
             The type of file to download or upload upon an 
             'tmsCommonLoadExecute'.  WARNING: The boot should only be 
             downloaded when absolutely required (e.g., if power is
             removed during the boot Flash write operation, the agent
             cannot be recovered)."
        ::= { tmsCommonLoad 3 }

    tmsCommonLoadExecute OBJECT-TYPE
        SYNTAX INTEGER {
               noop(1),         -- no operation
               download(2),     -- Application, Boot, or Configuration
               upload(3)        -- Configuration only
        }
        MAX-ACCESS read-write
        STATUS current
        DESCRIPTION
            "Execute file download or upload procedure.  A SET of this
             object starts the load procedure.  Note that the Application
             and Boot images can only be downloaded.  The NVM Configuration
             file can be uploaded and downloaded.  A GET of this object
             will return the status of the executed operation. 
             Use 'tmsCommonLoadExecuteStatus' to determine the status of
             the executed load." 
        ::= { tmsCommonLoad 4 }

    tmsCommonLoadExecuteStatus OBJECT-TYPE
        SYNTAX INTEGER {
               notStarted(1),       -- download has not yet started
               inProgress(2),       -- download has not yet finished
               success(3),          -- download has finished successfully
               errorConnection(4),  -- download cannot connect
               errorFilename(5),    -- download has bad image path/filename
               errorFault(6)        -- download has fault condition on device
        }
        MAX-ACCESS read-only 
        STATUS current
        DESCRIPTION
            "Provides status on the execute file load progress."
        ::= { tmsCommonLoad 5 }

    tmsCommonZteLoadExecute OBJECT-TYPE
        SYNTAX INTEGER {
               noop(1),            -- no operation
               backload(2),     -- load back application to slave SCB. 
               back2main(3)   -- use back application.
        }
        MAX-ACCESS read-write
        STATUS current
        DESCRIPTION
            "Execute file download  procedure.  A SET of this
             object starts the load procedure. " 
        ::= { tmsCommonLoad 6 }

    tmsCommonZteLoadCardVer OBJECT-TYPE
        SYNTAX     INTEGER(1..10)
        MAX-ACCESS read-write
        STATUS current
        DESCRIPTION
            "Execute the No. card application file download  procedure.
            the value is slot number." 
        ::= { tmsCommonLoad 7 }

------------------------------------------------------------------------------
--
--  tmsCommonMisc - Miscellaneous Information         
--
--  This group is meant to be a collection of controls and data 
--  that do not require a group of their own, or fall into the 
--  category of "miscellaneous".  The user may easily add simple 
--  objects in this group without destroying the integrity or definition
--  of the group.
--
------------------------------------------------------------------------------
--
    tmsCommonMiscSaveToNvm OBJECT-TYPE
        SYNTAX INTEGER {
               noop(1),           -- no operation
               save(2),           -- save all configuration parameters to NVM
               saveInProgress(3),  -- read-only: NVM save in progress
               saveSCB(4)          -- save NVM to slave SCB.
        }
        MAX-ACCESS read-write
        STATUS current
        DESCRIPTION
            "When set to 'save(2)', all nonvolatile configuration
             parameters are saved to NVM (Nonvolatile Memory).  NVM save
             operations may be slow (e.g., erasing/writing Flash device).
             Consequently, all or many updates should be made before
             saving to NVM.  Note that the SNMP set to 'save(2)' returns
             immediately to the caller.  Gets on this object then return
             'saveInProgress(3)' until the save operation completes, at
             which time 'noop(1)' is returned.  Consequently, a get
             operation always returns 'noop(1)' or 'saveInProgress(3)'
             depending on the current state.
             
             The agent returns 'badValue' for SNMPv1 or 'inconsistentValue'
             for SNMPv2c/v3 for a set to 'Save(2)' while the current get
             state is 'saveInProgress(3)'.
             
             Attempts to set this object to 'saveInProgress(3)' returns
             'badValue' for SNMPv1 or 'wrongValue' for SNMPv2c/v3."
        ::= { tmsCommonMisc 1 }

--    tmsCommonMiscSnmpSecurityOnOff OBJECT-TYPE
--        SYNTAX INTEGER {
--               enable(1),
--               disable(2)
--        }
--        MAX-ACCESS read-write
--        STATUS obsolete
--        DESCRIPTION
--            "Enable/Disable SNMPv1 Security.  This object is now obsolete
--             and is not implemented."
--        ::= { tmsCommonMisc 2 }

    tmsCommonMiscSpanOnOff OBJECT-TYPE
        SYNTAX INTEGER {
               enable(1),
               disable(2)
        }
        MAX-ACCESS read-write
        STATUS current
        DESCRIPTION
            "DURABLE: { enable }
             Enable/Disable Spanning Tree for the bridge.
             When 'disable(2)', all ports of the device are placed in the
             forwarding mode, regardless of current Spanning Tree state.
             When 'enable(1)', the normal STP state transitions take place."
        ::= { tmsCommonMisc 3 }

    tmsCommonMiscFTPUserName OBJECT-TYPE
        SYNTAX DisplayString (SIZE (1..32))
        MAX-ACCESS read-write
        STATUS current
        DESCRIPTION
            "."
        ::= { tmsCommonMisc 4 }

    tmsCommonMiscFTPUserPwd OBJECT-TYPE
        SYNTAX DisplayString (SIZE (1..32))
        MAX-ACCESS read-write
        STATUS current
        DESCRIPTION
            "."
        ::= { tmsCommonMisc 5 }

    tmsCommonMiscBaud OBJECT-TYPE
        SYNTAX INTEGER {
               baud2400(1),
               baud9600(2),
               baud19200(3),
               baud38400(4)
        } 
        MAX-ACCESS read-write 
        STATUS current
        DESCRIPTION
            "DURABLE: { baud38400 }
             The serial port baud rate.  Attributes include 8 data bits,
             no parity and 1 stop bit (8N1) with hardware flow control.
             Valid values are 2400, 9600, 19200, and 38400 baud."
        ::= { tmsCommonMisc 6 }

    tmsCommonMiscPassword OBJECT-TYPE
        SYNTAX DisplayString (SIZE (1..16))
        MAX-ACCESS read-write
        STATUS current
        DESCRIPTION
            "DURABLE: { 'password' }
             The system password used for serial console, Telnet console
             and Web page login."
        ::= { tmsCommonMisc 7 }

    tmsCommonMiscProductName OBJECT-TYPE
        SYNTAX DisplayString (SIZE (0..32))
        MAX-ACCESS read-write
        STATUS current
        DESCRIPTION
            "DURABLE: { 'WindRiver TMS Agent' }
             The product name associated with this agent.  This name is
             displayed on the console screens and Web pages." 
        ::= { tmsCommonMisc 8 }

    tmsCommonMiscReset OBJECT-TYPE
        SYNTAX INTEGER {
               noop(1),           -- no operation
               reset(2),          -- reset unit
               resetToDefaults(3), -- reset to factory defaults/reset unit
               resetToNoData(4), -- reset to no data unit
               resetSlaveSCB(5) -- reset to factory defaults/reset unit
        }
        MAX-ACCESS read-write
        STATUS current
        DESCRIPTION
            "Physically performs a hardware reset of the unit. 
             Use with care.  A 'reset(2)' resets the unit, a
             'resetToDefaults(3)' resets the NVM configuration
             to factory defaults and then resets the unit, and 'noop(1)'
             does nothing.  A value of 'noop(1)' is always returned for a
             GET operation."
        ::= { tmsCommonMisc 9 }

        tmsCommonMiscTrapTest OBJECT-TYPE
        SYNTAX INTEGER {
            noop(1),
            coldstart(2),
            linkdown(3),
            linkup(4),
            authentication(5),
            tmsTestTrap(6)
        }
        MAX-ACCESS read-write
        STATUS current
        DESCRIPTION
            "This object sends a specific SNMP Trap, as selected by the type,
             to the SNMP manager(s) to verify proper operation of the Notify
             Subsystem.  Note that the specific SNMP Message Processing Model
             (SNMP v1, v2c or v3) is specified using 'snmpTargetParamsMPModel'
             in the 'snmpTargetParamsTable' in RFC2573 (Target MIB).
             
             To distinguish the linkdown(3) and linkup(4) test traps from the
             actual link down and up traps, both trap types use '0' for the
             ifIndex value.
             
             Note that tmsTestTrap(6) generates a 'tmsCommonSnmpV2TestTrap'. 
             
             A GET always returns the 'noop(1)' value."  
        ::= { tmsCommonMisc 10 }

    tmsEnableRmonRunning  OBJECT-TYPE
            SYNTAX INTEGER {
            enable(1),
            disable(2)
            }
        MAX-ACCESS read-write
        STATUS current
        DESCRIPTION
            "Enable/disable RMON"
        ::= { tmsCommonMisc 11 }
          
          tmsCommonMiscSwap   OBJECT-TYPE
            SYNTAX INTEGER {
            none(1),        -- none(in set); main to slave(in get)
            swap(2),        -- swap(in set); slave to main(in get)
            swaperror(3)    -- swap error(in get)
            }
        MAX-ACCESS read-write
        STATUS current
        DESCRIPTION
            "Swap between master and slave SCB."
        ::= { tmsCommonMisc 12}
        
       tmsCommonMiscUserTable OBJECT-TYPE
        SYNTAX SEQUENCE OF TmsCommonMiscUserEntry
        MAX-ACCESS not-accessible
        STATUS current
        DESCRIPTION
            "A table contain user information for web and console and telnet.."
        ::= { tmsCommonMisc 13 }

    tmsCommonMiscUserEntry OBJECT-TYPE
        SYNTAX TmsCommonMiscUserEntry
        MAX-ACCESS not-accessible
        STATUS current
        DESCRIPTION
            "A list of user information."
        INDEX { tmsCommonMiscUserIndex }
        ::= { tmsCommonMiscUserTable 1 }

    TmsCommonMiscUserEntry ::= SEQUENCE {
        tmsCommonMiscUserIndex         Integer32,
        tmsCommonMiscUserName          DisplayString,
        tmsCommonMiscUserPwd          DisplayString,
        tmsCommonMiscUserAccess      INTEGER,
        tmsCommonMiscUserState     INTEGER
    }

    tmsCommonMiscUserIndex  OBJECT-TYPE
        SYNTAX Integer32 (1..8)
        MAX-ACCESS not-accessible
        STATUS current
        DESCRIPTION
            "A simple index into 'TmsCommonMiscUserTable'."
        ::= { tmsCommonMiscUserEntry 1 }

    tmsCommonMiscUserName  OBJECT-TYPE
        SYNTAX DisplayString (SIZE(0..20))
        MAX-ACCESS read-write
        STATUS current
        DESCRIPTION
            "A simple index into 'TmsCommonMiscUserTable'."
        ::= { tmsCommonMiscUserEntry 2 }

    tmsCommonMiscUserPwd  OBJECT-TYPE
        SYNTAX DisplayString (SIZE(0..20))
        MAX-ACCESS read-write
        STATUS current
        DESCRIPTION
            "A simple index into 'TmsCommonMiscUserTable'."
        ::= { tmsCommonMiscUserEntry 3 }

    tmsCommonMiscUserAccess  OBJECT-TYPE
        SYNTAX     INTEGER(1..10)
        MAX-ACCESS read-write
        STATUS current
        DESCRIPTION
            "the user access in this row."
        ::= { tmsCommonMiscUserEntry 4 }

    tmsCommonMiscUserState  OBJECT-TYPE
        SYNTAX     INTEGER{
                    valid(1),
                    invalid(2)
                    }
        MAX-ACCESS read-write
        STATUS current
        DESCRIPTION
            "the user state in this row."
        ::= { tmsCommonMiscUserEntry 5 }

          tmsCommonMiscAgingTime   OBJECT-TYPE
            SYNTAX INTEGER 
        MAX-ACCESS read-write
        STATUS current
        DESCRIPTION
            "AgingTime of all the device."
        ::= { tmsCommonMisc 14}
          tmsCommonMiscMaxTimerNum   OBJECT-TYPE
            SYNTAX INTEGER 
        MAX-ACCESS read-only
        STATUS current
        DESCRIPTION
            "Maximun timer number in garp protocol."
        ::= { tmsCommonMisc 15}

          tmsCommonMiscCurTimerNum  OBJECT-TYPE
            SYNTAX INTEGER 
        MAX-ACCESS read-only
        STATUS current
        DESCRIPTION
            "Current timer num in grap protocol."
        ::= { tmsCommonMisc 16}

          tmsCommonMiscMaxMulticastNum   OBJECT-TYPE
            SYNTAX INTEGER 
        MAX-ACCESS read-only
        STATUS current
        DESCRIPTION
            "Maximum multicast number.."
        ::= { tmsCommonMisc 17}

          tmsCommonMiscCardReset   OBJECT-TYPE
            SYNTAX Integer32(1..10) 
        MAX-ACCESS read-write
        STATUS current
        DESCRIPTION
            "Reset card."
        ::= { tmsCommonMisc 18}

        tmsCommonMiscCSV   OBJECT-TYPE
        SYNTAX OCTET STRING (SIZE (0..255)) 
        MAX-ACCESS read-write
        STATUS current
        DESCRIPTION
        "Item for CSV .
          Array of ulong_t, first ulong_t is item type,
         second ulong_t is folllowing data number, other ulong_t is item
         data. all data is 100 times of factual data. temperature is added 100
         on factual temperature.
           in GET operation, command only have item type.bellow is GET result:
           itemType                           DataLength        Data
            
            "
        ::= { tmsCommonMisc 19}

        tmsCommonMiscSwapError   OBJECT-TYPE
        SYNTAX INTEGER 
        MAX-ACCESS read-only
        STATUS current
        DESCRIPTION
         "idedicate Swap Trap failure cause for Trap."
        ::= { tmsCommonMisc 20}

        tmsCommonMiscRouteEnable   OBJECT-TYPE
           SYNTAX INTEGER 
        MAX-ACCESS read-only
        STATUS current
        DESCRIPTION
            "."
        ::= { tmsCommonMisc 21}

          tmsCommonLacpEnable   OBJECT-TYPE
            SYNTAX INTEGER 
        MAX-ACCESS read-write
        STATUS current
        DESCRIPTION
            "Maximum multicast number.."
        ::= { tmsCommonMisc 22}
        
        tmsCommonVbaseEnable   OBJECT-TYPE
           SYNTAX INTEGER 
        MAX-ACCESS read-write
        STATUS current
        DESCRIPTION
            "."
        ::= { tmsCommonMisc 23}

        tmsCommonMiscVbasPortlistEnable   OBJECT-TYPE
           SYNTAX PortList 
        MAX-ACCESS read-write
        STATUS current
        DESCRIPTION
            "the vbas status of portlist."
        ::= { tmsCommonMisc 24}

    tmsCommonMiscVbasTable OBJECT-TYPE
        SYNTAX SEQUENCE OF TmsCommonMiscVbasEntry
        MAX-ACCESS not-accessible
        STATUS current
        DESCRIPTION
            "A table contain user information for web and console and telnet.."
        ::= { tmsCommonMisc 25 }

        tmsCommonMiscVbasEntry OBJECT-TYPE
        SYNTAX TmsCommonMiscVbasEntry
        MAX-ACCESS not-accessible
        STATUS current
        DESCRIPTION
            "A list of user information."
        INDEX { tmsCommonMiscVlanIndex }
        ::= { tmsCommonMiscVbasTable 1 }

        TmsCommonMiscVbasEntry ::= SEQUENCE {
        tmsCommonMiscVlanIndex         Integer32,
        tmsCommonMiscVbasVlanEnable    Integer32
        }

        tmsCommonMiscVlanIndex  OBJECT-TYPE
        SYNTAX Integer32 (1..8)
        MAX-ACCESS not-accessible
        STATUS current
        DESCRIPTION
            "A vlan index."
        ::= { tmsCommonMiscVbasEntry 1 }

        tmsCommonMiscVbasVlanEnable  OBJECT-TYPE
        SYNTAX Integer32 (1..8)
        MAX-ACCESS read-write
        STATUS current
        DESCRIPTION
            "A simple index into 'TmsCommonMiscUserTable'."
        ::= { tmsCommonMiscVbasEntry 2 }

        tmsCommonMiscVbasIsMaxVlanNum   OBJECT-TYPE
           SYNTAX INTEGER 
        MAX-ACCESS read-only
        STATUS current
        DESCRIPTION
            "whether reach the maximum allowed vlannum."
        ::= { tmsCommonMisc 26}

        tmsCommonMiscVbasCurrentVlanNum   OBJECT-TYPE
           SYNTAX INTEGER 
        MAX-ACCESS read-only
        STATUS current
        DESCRIPTION
            "current vlannum which enable vabs"
        ::= { tmsCommonMisc 27}

        tmsCommonMiscVbasIsMaxPortNum   OBJECT-TYPE
           SYNTAX INTEGER 
        MAX-ACCESS read-only
        STATUS current
        DESCRIPTION
            "whether reach the maximum allowed Portnum."
        ::= { tmsCommonMisc 28}

        tmsCommonMiscVbasCurrentPortNum   OBJECT-TYPE
           SYNTAX INTEGER 
        MAX-ACCESS read-only
        STATUS current
        DESCRIPTION
            "current Portnum which enable vabs"
        ::= { tmsCommonMisc 29}

          tmsCommonMiscVlanMode   OBJECT-TYPE
            SYNTAX INTEGER 
        MAX-ACCESS read-write
        STATUS current
        DESCRIPTION
            ""
        ::= { tmsCommonMisc 30}
        
          tmsCommonMiscRootMode   OBJECT-TYPE
            SYNTAX INTEGER 
        MAX-ACCESS read-write
        STATUS current
        DESCRIPTION
            ""
        ::= { tmsCommonMisc 31}
        
------------------------------------------------------------------------------
--
--  tmsCommonCommToView - SNMP 'Community-to-View' Mapping
--
--  Starting with TMS 1.1, SNMP access uses the SNMP-VIEW-BASED-ACM-MIB
--  (RFC2575) for all SNMP versions (i.e., v1, v2c and v3).  Note that SNMP
--  v1 and v2c both use the SNMP 'community string' to implement limited
--  security and administrative control.  Consequently, to support the
--  'View-based Access Control Model' for SNMPv1/v2c requires a mechanism to
--  map the 'community string' to a 'view'.  This is implemented using the
--  'tmsCommonCommunityToViewTable'.  This table allows up to 8 unique
--  community strings to be mapped to the same or different views as defined
--  in the SNMP-VIEW-BASED-ACM-MIB.  Each community can have read-only or 
--  read-write access permission.
--
--  For test and development purposes, the factory default setting includes
--  a single 'active(1)' entry for index '1' that contains:
--      tmsCommonComm2ViewCommName   = "public"
--      tmsCommonComm2ViewViewName   = "internet"       ==>1.3.6.1
--      tmsCommonComm2ViewPermission = "readWrite(2)"
--
--  These default settings, in conjunction with a corresponding factory 
--  default entry in the RFC2575 'vacmViewTreeFamilyTable', allow full GET
--  and SET access for the entire 'internet' MIB subtree.  Although useful
--  for test and development, this is not a desirable default for a
--  production switch.
--
------------------------------------------------------------------------------
--
    tmsCommonCommunityToViewTable OBJECT-TYPE
        SYNTAX SEQUENCE OF TmsCommonCommunityToViewEntry
        MAX-ACCESS not-accessible
        STATUS current
        DESCRIPTION
            "A table of SNMPv1/v2c community string to view name mappings."
        ::= { tmsCommonCommToView 1 }

    tmsCommonCommunityToViewEntry OBJECT-TYPE
        SYNTAX TmsCommonCommunityToViewEntry
        MAX-ACCESS not-accessible
        STATUS current
        DESCRIPTION
            "A list of community-to-view parameters."
        INDEX { tmsCommonComm2ViewIndex }
        ::= { tmsCommonCommunityToViewTable 1 }

    TmsCommonCommunityToViewEntry ::= SEQUENCE {
        tmsCommonComm2ViewIndex         Integer32,
        tmsCommonComm2ViewCommName      DisplayString,
        tmsCommonComm2ViewViewName      SnmpAdminString,
        tmsCommonComm2ViewPermission    INTEGER,
        tmsCommonComm2ViewRowStatus     RowStatus
    }

    tmsCommonComm2ViewIndex  OBJECT-TYPE
        SYNTAX Integer32 (1..8)
        MAX-ACCESS not-accessible
        STATUS current
        DESCRIPTION
            "A simple index into 'tmsCommonCommunityToViewTable'."
        ::= { tmsCommonCommunityToViewEntry 1 }

    tmsCommonComm2ViewCommName  OBJECT-TYPE
        SYNTAX DisplayString (SIZE(1..20))
        MAX-ACCESS read-create
        STATUS current
        DESCRIPTION
            "DURABLE: { 'public','':all }
             The SNMPv1/v2c community name string.  Duplicate community
             names are not allowed in this table.  Note that a null string
             is not a valid community name (i.e., a null string forces
             'tmsCommonComm2ViewRowStatus' to 'notReady(3)')."
        ::= { tmsCommonCommunityToViewEntry 2 }

    tmsCommonComm2ViewViewName  OBJECT-TYPE
        SYNTAX SnmpAdminString (SIZE(1..32))
        MAX-ACCESS read-create
        STATUS current
        DESCRIPTION
            "DURABLE: { 'internet':all }
             At runtime (i.e., not when this object is SET), this view name
             is compared to the 'vacmViewTreeFamilyViewName' in the
             'vacmViewTreeFamilyTable' (see RFC2575).  If a match is
             found and the varbind(s) specify valid object type and instance,
             the 'tmsCommonComm2ViewPermission' privilege is permitted.
             
             Note that a null string is not a valid view name value.
             Also note that the value of this object does not have to match
             an existing entry in the 'vacmViewTreeFamilyTable' (if no match,
             no access is allowed).
             
             Note that the factory default value for this object is 'internet',
             which allows access to the subtree under '1.3.6.1'."
        ::= { tmsCommonCommunityToViewEntry 3 }

    tmsCommonComm2ViewPermission OBJECT-TYPE
        SYNTAX INTEGER {
               readOnly(1),
               readWrite(2)
        }
        MAX-ACCESS read-create
        STATUS current
        DESCRIPTION
            "DURABLE: { readWrite:all }
             This object specifies the type of access allowed. 'readOnly(1)'
             allows GET operations (i.e., GET, GET-NEXT, GET-BULK) and
             'readWrite(2)' allows both GET and SET operations."
        ::= { tmsCommonCommunityToViewEntry 4 }

    tmsCommonComm2ViewRowStatus OBJECT-TYPE
        SYNTAX  RowStatus
        MAX-ACCESS  read-create
        STATUS  current
        DESCRIPTION
            "DURABLE:
             This object indicates the status of this entry.  A row in this
             table can be created using the 'createAndGo(4)' (i.e., all
             parameters must be valid - supplied in a single SNMP PDU or have
             default values) or the 'createAndWait(5)' action states.  Until
             all parameters are valid for a conceptual row, this object is
             'notReady(3)'.  All parameters must be valid before this object
             can be set to 'active(1)'.
             
             Any object in a conceptual row can be modified independent of the
             value of this object (e.g., can be changed while 'active(1)')."
        ::= { tmsCommonCommunityToViewEntry 5 }


------------------------------------------------------------------------------
--
--  tmsCommonIgmpSnoop - IGMP Snooping Parameters
--
--  This group is used to instrument the Layer 2 IGMP Snooping support.
--
------------------------------------------------------------------------------
--
    tmsCommonIgmpSnoopEnabled  OBJECT-TYPE
        SYNTAX TruthValue
        MAX-ACCESS read-write
        STATUS current
        DESCRIPTION
            "DURABLE: { false )
             Setting this object to true(1) enables IGMP Snooping.  Setting
             it to false(2) disables IGMP Snooping.
             
             Note that IGMP Snooping can function with or without GVRP and
             GMRP enabled."
        ::= { tmsCommonIgmpSnoop 1 }


    tmsCommonIgmpSnoopAlerts  OBJECT-TYPE
        SYNTAX TruthValue
        MAX-ACCESS read-write
        STATUS current
        DESCRIPTION
            "DURABLE: { false )
             Setting this object to true(1) enables the IP Router Alert
             Option (as defined in RFC2113) for transmitted IGMP packets.
             Setting it to false(2) disables this option."
        ::= { tmsCommonIgmpSnoop 2 }

    tmsCommonIgmpSnoopAging  OBJECT-TYPE
        SYNTAX Integer32 (30..3600)
        MAX-ACCESS read-write
        STATUS current
        DESCRIPTION
            "DURABLE: { 300 )
             The timeout period in seconds for aging out Multicast Groups
             dynamically learned with IGMP Snooping.  Note that aging operates
             on a per interface per VLAN per multicast group basis."
        ::= { tmsCommonIgmpSnoop 3 }

    tmsCommonIgmpSnoopTable OBJECT-TYPE
        SYNTAX SEQUENCE OF TmsCommonIgmpSnoopEntry
        MAX-ACCESS not-accessible
        STATUS current
        DESCRIPTION
            "This table, which provides IGMP Snooping information, augments
             the 'dot1qStaticMulticastTable' in the Q-MIB (RFC2674)."
        ::= { tmsCommonIgmpSnoop 4 }

    tmsCommonIgmpSnoopEntry OBJECT-TYPE
        SYNTAX TmsCommonIgmpSnoopEntry
        MAX-ACCESS not-accessible
        STATUS current
        DESCRIPTION
            "Displays by VLAN, Multicast Group, and Multicast receive port
             the set of ports enabled to forward Multicast Group traffic as
             determined by the IGMP Snooping task."
        AUGMENTS { dot1qStaticMulticastEntry }
        ::= { tmsCommonIgmpSnoopTable 1 }

    TmsCommonIgmpSnoopEntry ::= SEQUENCE {
        tmsCommonIgmpSnoopEgressPorts   PortList
    }

    tmsCommonIgmpSnoopEgressPorts  OBJECT-TYPE
        SYNTAX PortList
        MAX-ACCESS read-only
        STATUS current
        DESCRIPTION
            "This read-only object displays the set of ports enabled to
             forward specific Multicast Group traffic as determined by the
             IGMP Snooping task.
            
             It should be noted that the IGMP Snooping task generates a pseudo-
             static (i.e., not saved in NVM) port list similar to the RFC2674
             Q-MIB 'dot1qStaticMulticastStaticEgressPorts' object. Consequently,
             a port will not be a member of 'tmsCommonIgmpSnoopEgressPorts' if
             it is a member of 'dot1qStaticMulticastForbiddenEgressPorts'."
        ::= { tmsCommonIgmpSnoopEntry 1 }


------------------------------------------------------------------------------
--
--  tmsCommonTrapTarget - I
--
--  
--
------------------------------------------------------------------------------
--
    tmsTrapTargetTable OBJECT-TYPE
        SYNTAX SEQUENCE OF TmsTrapTargetEntry
        MAX-ACCESS not-accessible
        STATUS current
        DESCRIPTION
            "This table, which provides Trap target."
        ::= { tmsCommonTrapTarget 1 }

    tmsTrapTargetEntry OBJECT-TYPE
        SYNTAX TmsTrapTargetEntry
        MAX-ACCESS not-accessible
        STATUS current
        DESCRIPTION
            ""
        INDEX { tmsTrapTargetIndex }
        ::= { tmsTrapTargetTable 1 }

    TmsTrapTargetEntry ::= SEQUENCE {
        tmsTrapTargetIndex                INTEGER,
        tmsTrapTargetIpAddr            IpAddress,
        tmsTrapTargetSnmpVer            INTEGER,
        tmsTrapTargetBaseType            INTEGER,
        tmsTrapTargetCommunity            DisplayString,
        tmsTrapTargetRowStatus            RowStatus,
    tmsTrapHostIsZteNmsSever                TruthValue 
    }

    tmsTrapTargetIndex  OBJECT-TYPE
        SYNTAX INTEGER(1..8)
        MAX-ACCESS read-only
        STATUS current
        DESCRIPTION
            ""
        ::= { tmsTrapTargetEntry 1 }

    tmsTrapTargetIpAddr  OBJECT-TYPE
        SYNTAX IpAddress
        MAX-ACCESS read-write
        STATUS current
        DESCRIPTION
            ""
        ::= { tmsTrapTargetEntry 2 }

    tmsTrapTargetSnmpVer  OBJECT-TYPE
        SYNTAX INTEGER(0..1)
        MAX-ACCESS read-write
        STATUS current
        DESCRIPTION
            ""
        ::= { tmsTrapTargetEntry 3 }

    tmsTrapTargetBaseType  OBJECT-TYPE
        SYNTAX INTEGER(1..2)
        MAX-ACCESS read-write
        STATUS current
        DESCRIPTION
            ""
        ::= { tmsTrapTargetEntry 4 }

    tmsTrapTargetCommunity  OBJECT-TYPE
        SYNTAX DisplayString(SIZE(0..30))
        MAX-ACCESS read-write
        STATUS current
        DESCRIPTION
            ""
        ::= { tmsTrapTargetEntry 5 }

    tmsTrapTargetRowStatus  OBJECT-TYPE
        SYNTAX RowStatus
        MAX-ACCESS read-write
        STATUS current
        DESCRIPTION
            ""
        ::= { tmsTrapTargetEntry 6 }

    tmsTrapHostIsZteNmsSever  OBJECT-TYPE
        SYNTAX TruthValue 
        MAX-ACCESS read-write
        STATUS current
        DESCRIPTION
            "If or not it is a zte's nms.
            true(1): it is a zte's nms;
            false(2): it is not a zte's nms.
            "
        ::= { tmsTrapTargetEntry 7 }


------------------------------------------------------------------------------
--
--  tmsCommonMiscZteTest
--
------------------------------------------------------------------------------

    tmsCommonMiscZteTestPing  OBJECT-TYPE
        SYNTAX IpAddress
        MAX-ACCESS read-write
        STATUS current
        DESCRIPTION
            "in SET operation, ping IPADDRESS from CPU, if operation is successful,
            ping is OK, otherwise ERROR.
            "
        ::= { tmsCommonMiscZteTest 1 }

    tmsCommonMiscZteTestLoopTable OBJECT-TYPE
        SYNTAX SEQUENCE OF TmsCommonMiscZteTestLoopEntry
        MAX-ACCESS not-accessible
        STATUS current
        DESCRIPTION
            "This table,testing port loop and send packets on the port."
        ::= { tmsCommonMiscZteTest 2 }

    tmsCommonMiscZteTestLoopEntry OBJECT-TYPE
        SYNTAX TmsCommonMiscZteTestLoopEntry
        MAX-ACCESS not-accessible
        STATUS current
        DESCRIPTION
            ""
        INDEX { tmsCommonMiscZteTestLoopIndex }
        ::= { tmsCommonMiscZteTestLoopTable 1 }

    TmsCommonMiscZteTestLoopEntry ::= SEQUENCE {
        tmsCommonMiscZteTestLoopIndex    INTEGER,
        tmsCommonMiscZteTestLoopMode    INTEGER,
        tmsCommonMiscZteTestLoopEnable    INTEGER,
        tmsCommonMiscZteTestSendNum        INTEGER,
        tmsCommonMiscZteTestSendLength    INTEGER,
        tmsCommonMiscZteTestSendEnable    INTEGER
    }

    tmsCommonMiscZteTestLoopIndex  OBJECT-TYPE
        SYNTAX INTEGER(1..248)
        MAX-ACCESS not-accessible
        STATUS current
        DESCRIPTION
            "Index of port. assign a port to test."
        ::= { tmsCommonMiscZteTestLoopEntry 1 }

    tmsCommonMiscZteTestLoopMode  OBJECT-TYPE
        SYNTAX INTEGER{
                lt(1),
                nt(2),
                noloop(3)
                }
        MAX-ACCESS read-write
        STATUS current
        DESCRIPTION
            "loop mode.
            in new version ,this item can finish loop and send in one time. "
        ::= { tmsCommonMiscZteTestLoopEntry 2 }

    tmsCommonMiscZteTestLoopEnable  OBJECT-TYPE
        SYNTAX INTEGER{
                enable(1),
                disable(2)
                }
        MAX-ACCESS read-write
        STATUS current
        DESCRIPTION
            " Enable or disable loop test."
        ::= { tmsCommonMiscZteTestLoopEntry 3 }

    tmsCommonMiscZteTestSendNum  OBJECT-TYPE
        SYNTAX INTEGER(1..10000)
        MAX-ACCESS read-write
        STATUS current
        DESCRIPTION
            " packet number. "
        ::= { tmsCommonMiscZteTestLoopEntry 4 }

    tmsCommonMiscZteTestSendLength  OBJECT-TYPE
        SYNTAX INTEGER(1..2000)
        MAX-ACCESS read-write
        STATUS current
        DESCRIPTION
            "packet length ."
        ::= { tmsCommonMiscZteTestLoopEntry 5 }
        
    tmsCommonMiscZteTestSendEnable  OBJECT-TYPE
        SYNTAX INTEGER{
                enable(1),
                disable(2)
                }
        MAX-ACCESS read-write
        STATUS current
        DESCRIPTION
            "Enable or disable sending packet."
        ::= { tmsCommonMiscZteTestLoopEntry 6 }

    tmsCommonMiscZteTestLoopPort  OBJECT-TYPE
        SYNTAX INTEGER
        MAX-ACCESS read-only
        STATUS current
        DESCRIPTION
            "which port in loop mode. if 0 no port is in loop mode.
            "
        ::= { tmsCommonMiscZteTest 3 }

------------------------------------------------------------------------------
--
--  tmsCommonSysLog
--
--  
--
------------------------------------------------------------------------------
--
    tmsCommonSysLogEnabled  OBJECT-TYPE
        SYNTAX TruthValue
        MAX-ACCESS read-write
        STATUS current
        DESCRIPTION
            "Setting this object to true(1) enables SysLog.  Setting
             it to false(2) disables SysLog."
        DEFVAL { false }               
        ::= { tmsCommonSysLog 1 }
        
    tmsCommonSysLogFaciclity OBJECT-TYPE
        SYNTAX INTEGER(0..23)
        MAX-ACCESS read-write
        STATUS current
        DESCRIPTION
            "Faciclity of SysLog."
        DEFVAL { 0 }              
        ::= { tmsCommonSysLog 2 }        
        
    tmsCommonSysLogSeverity  OBJECT-TYPE
        SYNTAX INTEGER(0..7)
        MAX-ACCESS read-write
        STATUS current
        DESCRIPTION
            "Severity of SysLog."
        DEFVAL { 0 }              
        ::= { tmsCommonSysLog 3 }                      
        
    tmsCommonSysLogHostname OBJECT-TYPE
        SYNTAX DisplayString(SIZE(1..64))
        MAX-ACCESS read-write
        STATUS current
        DESCRIPTION
            "Hostname of SysLog."
        ::= { tmsCommonSysLog 4 }        
        
    tmsCommonSysLogServerTable OBJECT-TYPE
        SYNTAX SEQUENCE OF TmsCommonSysLogServerEntry
        MAX-ACCESS not-accessible
        STATUS current
        DESCRIPTION
            "This table, which provides Syslog Server."
        ::= { tmsCommonSysLog 5 }

    tmsCommonSysLogServerEntry OBJECT-TYPE
        SYNTAX TmsCommonSysLogServerEntry
        MAX-ACCESS not-accessible
        STATUS current
        DESCRIPTION
            ""
        INDEX { tmsCommonSysLogServerIndex }
        ::= { tmsCommonSysLogServerTable 1 }

    TmsCommonSysLogServerEntry ::= SEQUENCE {
        tmsCommonSysLogServerIndex       INTEGER,
        tmsCommonSysLogServerIpAddr      IpAddress,
        tmsCommonSysLogServerFPort       Integer32,
        tmsCommonSysLogServerLPort       Integer32,
        tmsCommonSysLogServerSendMsgType BITS,               
        tmsCommonSysLogServerRowStatus   RowStatus
    }

    tmsCommonSysLogServerIndex  OBJECT-TYPE
        SYNTAX INTEGER(1..5)
        MAX-ACCESS read-only
        STATUS current
        DESCRIPTION
            ""
        ::= { tmsCommonSysLogServerEntry 1 }

    tmsCommonSysLogServerIpAddr  OBJECT-TYPE
        SYNTAX IpAddress
        MAX-ACCESS read-write
        STATUS current
        DESCRIPTION
            "Ip address of this SysLog Server."        
        ::= { tmsCommonSysLogServerEntry 2 }

    tmsCommonSysLogServerFPort  OBJECT-TYPE
        SYNTAX Integer32(0..65535)
        MAX-ACCESS read-write
        STATUS current
        DESCRIPTION
            "remote portNo of this SysLog Server."
        DEFVAL { 514 }             
        ::= { tmsCommonSysLogServerEntry 3 }

    tmsCommonSysLogServerLPort  OBJECT-TYPE
        SYNTAX Integer32(0..65535)
        MAX-ACCESS read-write
        STATUS current
        DESCRIPTION
            "local portNo of this SysLog Server."
        DEFVAL { 514 }    
        ::= { tmsCommonSysLogServerEntry 4 }

    tmsCommonSysLogServerLogType  OBJECT-TYPE
        SYNTAX     BITS
        {
            alarm(0),
            cmd(1),            
            snmp(2)
        }        
        MAX-ACCESS read-write
        STATUS current
        DESCRIPTION
            "send log type of this SysLog Server."
        ::= { tmsCommonSysLogServerEntry 5 }
            
    tmsCommonSysLogServerRowStatus  OBJECT-TYPE
        SYNTAX RowStatus
        MAX-ACCESS read-write
        STATUS current
        DESCRIPTION
            "RowStatus of this table."
        ::= { tmsCommonSysLogServerEntry 6 }

------------------------------------------------------------------------------
--  Trap  information
------------------------------------------------------------------------------

tmsCommonMiscCSVTrap    NOTIFICATION-TYPE
    OBJECTS   { tmsCommonMiscCSV }
    STATUS    current
    DESCRIPTION 
    "  Trap for CSV. array of ulong_t, first ulong_t is alarm type,
     second ulong_t is folllowing data number, other ulong_t is alarm
     data. all data is 100 times of factual data. temperature is added 100
     on factual temperature.
     
                 almType                    almDataLen   almStatus                    almData            
    "
        
             ::= { tmsCommonMiscTrap 0 1 }
             
tmsCommonMiscSwapTrap     NOTIFICATION-TYPE
    OBJECTS   { tmsCommonMiscSwap, tmsCommonMiscSwapError }
    STATUS    current
    DESCRIPTION
    "Trap for Swap."
       ::= { tmsCommonMiscTrap 0 2 }
       

------------------------------------------------------------------------------
--  conformance information
------------------------------------------------------------------------------

--  --------------------------------------------------------------------------
--  units of conformance
--  --------------------------------------------------------------------------
    tmsCommonVerGroup   OBJECT-GROUP
        OBJECTS {
            tmsCommonVerMIBMajor,
            tmsCommonVerMIBMinor,
            tmsCommonVerBootSWMajor,
            tmsCommonVerBootSWMinor,
            tmsCommonVerAppSWMajor,
            tmsCommonVerAppSWMinor            
        }
        STATUS  current
        DESCRIPTION
           "This group retrieves system component versions."
        ::= { tmsCommonGroups 1 }
    
    tmsCommonIPGroup    OBJECT-GROUP
        OBJECTS {
            tmsCommonIPMACAddr,
            tmsCommonIPIpAddress,
            tmsCommonIPGateAddress,
            tmsCommonIPNetMask,
            tmsCommonIPStatus
        }
        STATUS  current
        DESCRIPTION
           "This group configures and retrieves IP related objects."
        ::= { tmsCommonGroups 2 }
    
    tmsCommonLoadGroup  OBJECT-GROUP
        OBJECTS {
            tmsCommonLoadTftpAddress,
            tmsCommonLoadTftpFileName,
            tmsCommonLoadType,
            tmsCommonLoadExecute,
            tmsCommonLoadExecuteStatus
        }
        STATUS  current
        DESCRIPTION
           "This group configures and retrieves TFTP download and upload
            objects."
        ::= { tmsCommonGroups 3 }

    tmsCommonMiscGroup  OBJECT-GROUP
        OBJECTS {
            tmsCommonMiscSaveToNvm,
            tmsCommonMiscSpanOnOff,
            tmsCommonMiscFTPUserName,
            tmsCommonMiscFTPUserPwd,
            tmsCommonMiscBaud,
            tmsCommonMiscPassword,
            tmsCommonMiscProductName,
            tmsCommonMiscReset,
            tmsCommonMiscTrapTest
       }
        STATUS  current
        DESCRIPTION
           "This group configures and retrieves misc. switch objects."
        ::= { tmsCommonGroups 4 }

    tmsCommonCommToViewGroup    OBJECT-GROUP
        OBJECTS {
        tmsCommonComm2ViewCommName,
        tmsCommonComm2ViewViewName,
        tmsCommonComm2ViewPermission,
        tmsCommonComm2ViewRowStatus
        }
        STATUS  current
        DESCRIPTION
           "This group configures and retrieves community-to-view SNMP
            information."
        ::= { tmsCommonGroups 5 }

    tmsCommonIgmpSnoopGroup     OBJECT-GROUP
        OBJECTS {
        tmsCommonIgmpSnoopEnabled,
        tmsCommonIgmpSnoopAlerts,
        tmsCommonIgmpSnoopAging,
        tmsCommonIgmpSnoopEgressPorts
        }
        STATUS  current
        DESCRIPTION
           "This group configures and retrieves IGMP Snooping information."
        ::= { tmsCommonGroups 6 }


--  --------------------------------------------------------------------------
--  compliance statements
--  --------------------------------------------------------------------------

    tmsCommonCompliance MODULE-COMPLIANCE
        STATUS  current
        DESCRIPTION
           "The compliance statement."
        MODULE  -- this module
        MANDATORY-GROUPS {
            tmsCommonVerGroup,
            tmsCommonIPGroup,
            tmsCommonLoadGroup,     
            tmsCommonMiscGroup,
            tmsCommonCommToViewGroup,
            tmsCommonIgmpSnoopGroup
        }
        ::= { tmsCommonCompliances 1 }

------------------------------------------------------------------------------
--
--  Sample TMS Common MIB Enterprise Trap
--
--  This trap facilitates testing of SNMP traps.  It can also be used as
--  an example for developers of custom enterprise MIBs.
--
------------------------------------------------------------------------------
--

    tmsCommonSnmpV2TestTrap NOTIFICATION-TYPE
        OBJECTS { tmsCommonMiscProductName }
        STATUS  current
        DESCRIPTION
             "This trap is used for the sample SNMP enterprise trap in the
              'tmsCommonMiscTrapTest' object.  Note that it includes the 
              'tmsCommonMiscProductName' object as a varbind."
        ::= { tmsCommonNotify 1 }


--
-- END of TMS-COMMON-MIB                
--

END


------------------------------------------------------------------------------
------------------------------------------------------------------------------

TMS-L3-MIB DEFINITIONS ::= BEGIN

    IMPORTS
        MODULE-IDENTITY, OBJECT-TYPE,
        Counter32, Gauge32,
        Unsigned32, Integer32,
        IpAddress                               FROM SNMPv2-SMI
        
        RowStatus, TruthValue, 
        DisplayString, MacAddress               FROM SNMPv2-TC
        
        MODULE-COMPLIANCE, OBJECT-GROUP         FROM SNMPv2-CONF
        
        tmsGeneric                              FROM WRS-MASTER-MIB;       

    tmsL3Mib MODULE-IDENTITY
        LAST-UPDATED    "0011040000Z"  -- November 4, 2000
        ORGANIZATION    "Wind River Systems, Inc."
        CONTACT-INFO    "Wind River Systems, Inc.
                         E-mail: support@windriver.com"

        DESCRIPTION     "TMS Generic Layer 3 MIB definition."

        REVISION        "0011040000Z"  -- November 4, 2000
        DESCRIPTION     "Initial MIB creation."

        ::= { tmsGeneric 2 }

------------------------------------------------------------------------------
-- Textual Conventions (i.e., these do not affect object encoding):
------------------------------------------------------------------------------
--
-- "DURABLE":
--    Objects that are saved across a system reset and/or power cycle
--    are noted as "DURABLE" for convenience in the DESCRIPTION
--    section of the object definition.  Code must be explicitly
--    written to implement these DURABLE objects.
--

------------------------------------------------------------------------------
--  groups in the TMS Layer 3 MIB
------------------------------------------------------------------------------
    tmsL3IpMisc             OBJECT IDENTIFIER ::= { tmsL3Mib 1 }
    tmsL3IpSubnet           OBJECT IDENTIFIER ::= { tmsL3Mib 2 }
    tmsL3IpStatic           OBJECT IDENTIFIER ::= { tmsL3Mib 3 }
    tmsL3IpRoute            OBJECT IDENTIFIER ::= { tmsL3Mib 4 }
    tmsL3MibConformance     OBJECT IDENTIFIER ::= { tmsL3Mib 5 }
    tmsL3MibGroups          OBJECT IDENTIFIER ::= { tmsL3MibConformance 1 }
    tmsL3MibCompliances     OBJECT IDENTIFIER ::= { tmsL3MibConformance 2 }


------------------------------------------------------------------------------
--
--  tmsL3IpMisc:
--      This group is used to configure and retrieve miscellaneous global
--      Layer 3 parameters.
--
------------------------------------------------------------------------------
--
    tmsL3IpMiscNumLogicalPorts OBJECT-TYPE
        SYNTAX Integer32
        MAX-ACCESS  read-only
        STATUS  current
        DESCRIPTION
            "The number of logical ports (i.e., L2/3 Aggregators or L3 only
             interfaces).  For TMS, this is normally equal to the number
             of physical ports."
        ::= { tmsL3IpMisc 1 }

    tmsL3IpMiscRoutingProtocol OBJECT-TYPE
        SYNTAX  INTEGER {
            none(1),        -- no dynamic routing protocols
            rip(2),         -- RIPv1/v2
            ospf(3)         -- OSPFv2
                }
        MAX-ACCESS  read-write
        STATUS  current
        DESCRIPTION
            "DURABLE: { none }
             The selected dynamic routing protocol.

             Note that static routing is still functional even when this
             object is set to none(1)."
        ::= { tmsL3IpMisc 2 }
        
        
    tmsL3IpMiscOspfv2Config OBJECT-TYPE
        SYNTAX OCTET STRING (SIZE (0..4096))
        MAX-ACCESS read-only
        STATUS current
        DESCRIPTION
             "This object is used for retrieving the RFC1850
              Open Shortest Path First version 2 (OSPFv2) nonvolatile
              (NVM) configuration data in an ASCII character string format.
              
              The format for this object is defined in the TMS 2.0 User Guide."
             
        REFERENCE
              "RFC1583 OSPFv2,
               RFC1850 OSPFv2 MIB, 
               WindNet OSPFv2 1.1 Release Notes,
               WindNet OSPFv2 1.1 User's Guide, Section 6 Configuration" 
        ::= { tmsL3IpMisc 3 }        


------------------------------------------------------------------------------
--
--  tmsL3IpSubnet:
--      This group is used to configure and retrieve subnet parameters
--      required for the basic routing functionality.  Before a "L2/3" VLAN or
--      a "L3 only" interface is used for routing, it must be assigned to at
--      least one subnet.  Although TMS supports multiple subnets per VLAN or
--      L3 interface, TMS recommends using one subnet per interface.
--
--      Note that the subnet IP address is added indirectly.  It is calculated
--      by logically AND'ing the Agent's IP address (tmsL3IpSubnetAgentIpAddr)
--      for this subnet with its subnet mask (tmsL3IpSubnetMask).  These
--      subnets are automatically added to the software Routing Table by IP.
--
--      The hardware routing table is often constrained to a very limited size.
--      Consequently, if it is desirable to have these subnets in the hardware
--      routing table, they must be manually entered as static routes (see
--      tmsL3IpStaticRouteTable).
--  
--      For a L2/3 switch, a static VLAN must be created for the specified
--      tmsL3IpSubnetVidIface VLAN ID value before this entry can be used.
--
--      Note that one of the entries for the first interface in this table
--      (i.e., tmsL3IpSubnetIfIndex for the 'sw0' swEnd driver) is directly
--      mapped to the IP address parameters in the TMS Common MIB
--      (TMS-COMMON-MIB; i.e., tmsCommonIPIpAddress, tmsCommonIPNetMask).
--      This allows the initial agent IP address to be set using the serial
--      console, BOOTP, or DHCP.  The remaining subnet entries can be entered
--      using SNMP or the Web management interfaces.
--
------------------------------------------------------------------------------
--
    tmsL3IpSubnetMaxRows  OBJECT-TYPE
        SYNTAX Unsigned32
        MAX-ACCESS read-only
        STATUS current
        DESCRIPTION
            "The maximum possible number of rows in the 'tmsL3IpSubnetTable'."
        ::= { tmsL3IpSubnet 1 }

    tmsL3IpSubnetCurrentRows  OBJECT-TYPE
        SYNTAX Unsigned32
        MAX-ACCESS read-only
        STATUS current
        DESCRIPTION
            "The current number of rows in the 'tmsL3IpSubnetTable'."
        ::= { tmsL3IpSubnet 2 }

    tmsL3IpSubnetTable OBJECT-TYPE
        SYNTAX SEQUENCE OF TmsL3IpSubnetEntry
        MAX-ACCESS not-accessible
        STATUS current
        DESCRIPTION
            "A table of subnet parameters.  There is one entry
             available for each of the 'tmsL3IpSubnetMaxRows'
             supported IP subnets."
        ::= { tmsL3IpSubnet 3 }

    tmsL3IpSubnetEntry OBJECT-TYPE
        SYNTAX TmsL3IpSubnetEntry
        MAX-ACCESS not-accessible
        STATUS current
        DESCRIPTION
            "A list of subnet parameters."
        INDEX { tmsL3IpSubnetIfIndex, tmsL3IpSubnetAgentIpAddr }
        ::= { tmsL3IpSubnetTable 1 }

    TmsL3IpSubnetEntry ::= SEQUENCE {
        tmsL3IpSubnetIfIndex        Integer32,
        tmsL3IpSubnetAgentIpAddr    IpAddress,
        tmsL3IpSubnetMask           IpAddress,
        tmsL3IpSubnetVidIface       Integer32,
        tmsL3IpSubnetName           DisplayString,
        tmsL3IpSubnetRowStatus      RowStatus
    }

    tmsL3IpSubnetIfIndex  OBJECT-TYPE
        SYNTAX Integer32
        MAX-ACCESS not-accessible
        STATUS current
        DESCRIPTION
            "DURABLE:
             The ifIndex of the swEnd driver associated with this subnet."
        ::= { tmsL3IpSubnetEntry 1 }

    tmsL3IpSubnetAgentIpAddr  OBJECT-TYPE
        SYNTAX IpAddress
        MAX-ACCESS not-accessible
        STATUS current
        DESCRIPTION
            "DURABLE:
             The network management station uses this IP Address to talk
             with the Agent on this subnet.  This IP address logically
             AND'ed with 'tmsL3IpSubnetMask' yields the actual subnet
             value for this subnet."
        ::= { tmsL3IpSubnetEntry 2 }

    tmsL3IpSubnetMask  OBJECT-TYPE
        SYNTAX IpAddress
        MAX-ACCESS read-create
        STATUS current
        DESCRIPTION
            "DURABLE:
             The subnet mask for this subnet.  It contains 1's in the
             bit positions for the net and subnet IDs and 0's in the
             bit positions for host ID.  The 1's must be contiguous,
             starting with the left most bit."
        ::= { tmsL3IpSubnetEntry 3 }

    tmsL3IpSubnetVidIface  OBJECT-TYPE
        SYNTAX Integer32 (0..4094)
        MAX-ACCESS read-create
        STATUS current
        DESCRIPTION
            "DURABLE: { default=0:all }
             For a L2/L3 hybrid switch, this object contains the actual
             VLAN ID (VID) from 1 to 4094 or 0 if the VID is unassigned.
             For a L3 only switch, this object contains the actual switch
             interface from 1 to 4094 or 0 if unassigned.
             
             Changing this object for this row causes all rows with the same
             'tmsL3IpSubnetIfIndex' as this row to be changed to this new
             'tmsL3IpSubnetVidIface' value."
        ::= { tmsL3IpSubnetEntry 4 }

    tmsL3IpSubnetName  OBJECT-TYPE
        SYNTAX DisplayString (SIZE (0..16))
        MAX-ACCESS read-create
        STATUS current
        DESCRIPTION
            "DURABLE:  { '':all )
             A user reference name for this subnet."
        ::= { tmsL3IpSubnetEntry 5 }

    tmsL3IpSubnetRowStatus OBJECT-TYPE
        SYNTAX  RowStatus
        MAX-ACCESS  read-create
        STATUS  current
        DESCRIPTION
            "DURABLE:
             This object indicates the status of this entry.  A row in this
             table must be created using the createAndWait(5) action state
             (i.e., createAndGo(4) is not supported).  This object can only
             be set to active(1) after all objects for this row are valid.
             The 'tmsL3IpSubnetName' is optional.
             
             Note that the notInService(2) state is not supported.  Objects
             in this table row can be changed when this object is notReady(3)
             or active(1)."
        ::= { tmsL3IpSubnetEntry 6 }

------------------------------------------------------------------------------
--
--  tmsL3IpStatic:
--      This group is used to configure and retrieve static routes for both
--      host and subnet IP destinations.
--
--      This group is independent of the underlying switch hardware and
--      architecture.  It indicates how many Host IDs and Subnet IDs that
--      the hardware can directly support, if any.  In general, hardware
--      entries route much faster than software entries.
--      
--      The user can choose to reserve zero, some, or all of the available
--      hardware entries for use as static routes.  The remaining entries,
--      if any, are reserved for dynamic routes (e.g., RIP, OSPF, etc.).
--
--      Note that the default route entry (0.0.0.0) in this table is directly
--      mapped to the IP Gateway (i.e., next hop router) in the TMS Common MIB
--      (TMS-COMMON-MIB; i.e., tmsCommonIPGateAddress, tmsCommonIPNetMask).
--      This allows the agent to set the IP gateway using the serial console,
--      BOOTP, and/or DHCP.
--
------------------------------------------------------------------------------
--
    tmsL3IpStaticMaxHwHosts  OBJECT-TYPE
        SYNTAX Unsigned32
        MAX-ACCESS read-only
        STATUS current
        DESCRIPTION
            "The maximum number, if any, of hosts that the hardware
             can support in its routing table.
             
             Note that if the hardware supports both hosts and subnets
             in the same table, this number represents both and 
             'tmsL3IpStaticMaxHwSubnets' is zero (0)."
        ::= { tmsL3IpStatic 1 }

    tmsL3IpStaticNumStaticHwHosts  OBJECT-TYPE
        SYNTAX Unsigned32
        MAX-ACCESS read-write
        STATUS current
        DESCRIPTION
            "DURABLE:
             The number of 'tmsL3IpStaticMaxHwHosts' hosts that the user
             would like to reserve for static routes.  A SNMPv1 badValue
             or SNMPv2 wrongValue is returned if the user attempts to use
             a value less than zero or greater than 'tmsL3IpStaticMaxHwHosts'.
             
             WARNING: This value is only used during system initialization
             (i.e., after a reset)."
        ::= { tmsL3IpStatic 2 }

    tmsL3IpStaticMaxHwSubnets  OBJECT-TYPE
        SYNTAX Unsigned32
        MAX-ACCESS read-only
        STATUS current
        DESCRIPTION
            "The maximum number, if any, of subnets that the hardware
             can support in its routing table.

             Note that if the hardware supports both hosts and subnets
             in the same table, this value is zero (0)."
        ::= { tmsL3IpStatic 3 }

    tmsL3IpStaticNumStaticHwSubnets  OBJECT-TYPE
        SYNTAX Unsigned32
        MAX-ACCESS read-write
        STATUS current
        DESCRIPTION
            "DURABLE:
             The number of 'tmsL3IpStaticMaxHwSubnets' subnets that the user
             would like to reserve for static routes.  An A SNMPv1 badValue
             or SNMPv2 wrongValue is returned if the user attempts to use a
             value less than zero or greater than 'tmsL3IpStaticMaxHwSubnets'.
             
             WARNING: This value is only used during system initialization
             (i.e., after a reset)."
        ::= { tmsL3IpStatic 4 }

    tmsL3IpStaticRouteMaxRows  OBJECT-TYPE
        SYNTAX Unsigned32
        MAX-ACCESS read-only
        STATUS current
        DESCRIPTION
            "The maximum possible number of rows in the 
             'tmsL3IpStaticRouteTable'."
        ::= { tmsL3IpStatic 5 }

    tmsL3IpStaticRouteCurrentRows  OBJECT-TYPE
        SYNTAX Unsigned32
        MAX-ACCESS read-only
        STATUS current
        DESCRIPTION
            "The current number of rows in the 'tmsL3IpStaticRouteTable'."
        ::= { tmsL3IpStatic 6 }

    tmsL3IpStaticRouteFlags  OBJECT-TYPE
        SYNTAX Integer32 (0..1)
        MAX-ACCESS read-write
        STATUS current
        DESCRIPTION
            "DURABLE: { 0 }
             Normally, the Static Route table only contains static
             routes.  To assist development and debug, this option flags 
             object allows the 'tmsL3IpStaticRouteTable' to support
             non-traditional characteristics.
             
             The flags value is a sum, which initially takes on the value of
             zero.  Then for each supported option 'X' from 1 to N, 2 raised
             to (X - 1) is added to the sum.
             
             Available options include:
               1 :  Include dynamic routes in the static route table:
                    Note that with this option that the dynamic route objects
                    can be accessed and/or changed just like the static route
                    objects, except that they are not saved in NVM.
               
             For for the factory default of no options, this flags value
             is '0' (zero).

             For option '1', the flags value is:
               0 + 2^(1-1) = 1
               
             If 4 options were available and the user wanted to select
             options 1 and 4, the flags value would be:
               0 + 2^(1-1) + 2^(4-1) = 9

             Currently only one flags value is defined."
        ::= { tmsL3IpStatic 7 }

    tmsL3IpStaticRouteTable OBJECT-TYPE
        SYNTAX SEQUENCE OF TmsL3IpStaticRouteEntry
        MAX-ACCESS not-accessible
        STATUS current
        DESCRIPTION
            "A table of static routes."
        ::= { tmsL3IpStatic 8 }

    tmsL3IpStaticRouteEntry OBJECT-TYPE
        SYNTAX TmsL3IpStaticRouteEntry
        MAX-ACCESS not-accessible
        STATUS current
        DESCRIPTION
            "A list of static route parameters."
        INDEX { tmsL3IpStaticDestIpAddr }
        ::= { tmsL3IpStaticRouteTable 1 }

    TmsL3IpStaticRouteEntry ::= SEQUENCE {
        tmsL3IpStaticDestIpAddr     IpAddress,
        tmsL3IpStaticMask           IpAddress,
        tmsL3IpStaticNextHop        IpAddress,
        tmsL3IpStaticName           DisplayString,
        tmsL3IpStaticUseHw          TruthValue,
        tmsL3IpStaticInHw           TruthValue,
        tmsL3IpStaticRowStatus      RowStatus
    }

    tmsL3IpStaticDestIpAddr  OBJECT-TYPE
        SYNTAX IpAddress
        MAX-ACCESS not-accessible
        STATUS current
        DESCRIPTION
            "DURABLE:
             The static route host or subnet IP destination address.
             Note that TMS supports up to one default route (0.0.0.0) entry.
             All other IP destination addresses must be non-zero."
        ::= { tmsL3IpStaticRouteEntry 1 }

    tmsL3IpStaticMask  OBJECT-TYPE
        SYNTAX IpAddress
        MAX-ACCESS read-create
        STATUS current
        DESCRIPTION
            "DURABLE:
             The mask for this IP destination.  It contains 1's in the
             bit positions for the net and subnet IDs and 0's in the
             bit positions for host ID.  The 1's must be contiguous,
             starting with the left most bit.
             
             Note that a host route uses a 255.255.255.255 mask."
        ::= { tmsL3IpStaticRouteEntry 2 }

    tmsL3IpStaticNextHop OBJECT-TYPE
        SYNTAX  IpAddress
        MAX-ACCESS  read-create
        STATUS  current
        DESCRIPTION
            "The IP address of the next hop of this route.
            (In the case of a route bound to an interface
            which is realized via a broadcast media, the value
            of this field is the agent's IP address on that
            interface.)"
        ::= { tmsL3IpStaticRouteEntry 3 }

    tmsL3IpStaticName  OBJECT-TYPE
        SYNTAX DisplayString (SIZE (0..16))
        MAX-ACCESS read-create
        STATUS current
        DESCRIPTION
            "DURABLE:  { '':all )
             A user reference name for this Static Route."
        ::= { tmsL3IpStaticRouteEntry 4 }

    tmsL3IpStaticUseHw  OBJECT-TYPE
        SYNTAX TruthValue
        MAX-ACCESS read-create
        STATUS current
        DESCRIPTION
            "DURABLE: { false:all )
             By setting this object to true(1), the user indicates the
             desire to use hardware routing for this entry.  To disable
             hardware routing for this entry, set this object to false(2).
             If the underlying switch fabric does not support hardware
             routing, this object is ignored.

             There is usually limited space in the hardware routing table.
             Consequently, if the user enables hardware routing on 'too'
             many entries, the agent assigns routes on a first come, first
             serve basis (i.e., the user may not get the expected results)."
        ::= { tmsL3IpStaticRouteEntry 5 }

    tmsL3IpStaticInHw  OBJECT-TYPE
        SYNTAX TruthValue
        MAX-ACCESS read-only
        STATUS current
        DESCRIPTION
            "If this object is true(1), this static route is actually in
             the hardware Route Table.  Otherwise it is false(2)."
        ::= { tmsL3IpStaticRouteEntry 6 }

    tmsL3IpStaticRowStatus OBJECT-TYPE
        SYNTAX  RowStatus
        MAX-ACCESS  read-create
        STATUS  current
        DESCRIPTION
            "DURABLE:
             This object indicates the status of this entry.  A row in this
             table must be created using the createAndWait(5) action state
             (i.e., createAndGo(4) is not supported).  This object can only
             be set to active(1) after all objects for this row are valid.
             The 'tmsL3IpStaticName' is optional.
             
             Note that the notInService(2) state is not supported.  Objects
             in this table row can be changed when this object is notReady(3)
             or active(1)."
        ::= { tmsL3IpStaticRouteEntry 7 }

------------------------------------------------------------------------------
--
--  tmsL3IpRoute:
--      The MIB II Routing Table (ipRouteTable) does not include the 
--      information required to support the UNIX style "netstat -nr" command.
--      This group replicates some of the ipRouteTable objects and adds
--      additional objects to support the "netstat -nr" functionality.
--
--      Note that the "netstat -nr" functionality has not been implemented.
--
--      This table also provides 'RowStatus' support for the 'ipRouteTable'
--      objects contained in this table.
--
--      The ipRouteTable objects are not actually duplicated, but use the IDB
--      "alternate object" capability to point back to the MIB II ipRouteTable.
--      Note that the utilized ipRouteTable objects are presented here
--      in a more logical order (similar to RFC1354).
--
--      The software Routing Table is a superset of all route entries that
--      includes the hardware Routing Table entries.
--  
------------------------------------------------------------------------------
--
    tmsL3IpRouteTableCurrentSwEntries  OBJECT-TYPE
        SYNTAX Unsigned32
        MAX-ACCESS read-only
        STATUS current
        DESCRIPTION
            "The number of current entries in the software Routing Table."
        ::= { tmsL3IpRoute 1 }

    tmsL3IpRouteCurrentHwHosts  OBJECT-TYPE
        SYNTAX Unsigned32
        MAX-ACCESS read-only
        STATUS current
        DESCRIPTION
            "The number of hardware host routing table entries currently
             in use.  If the hardware does not have routing table support,
             this value is zero (0).
             
             If the hardware supports both hosts and subnets
             in the same table, this number represents both and
             'tmsL3IpRouteCurrentHwSubnets' is zero (0)."
        ::= { tmsL3IpRoute 2 }

    tmsL3IpRouteCurrentHwSubnets  OBJECT-TYPE
        SYNTAX Unsigned32
        MAX-ACCESS read-only
        STATUS current
        DESCRIPTION
            "The number of hardware subnet routing table entries currently
             in use.  If the hardware does not have routing table support,
             this value is zero (0).

             Note that if the hardware supports both hosts and subnets
             in the same table, this value is zero (0)."
        ::= { tmsL3IpRoute 3 }

    tmsL3IpRouteTable OBJECT-TYPE
        SYNTAX  SEQUENCE OF TmsL3IpRouteEntry
        MAX-ACCESS  not-accessible
        STATUS  current
        DESCRIPTION
            "Provides Routing Table access.  This table can be used to
             modify or add Routing Table entries.  Changes made with this
             table are not saved to NVM (nonvolatile memory).  To save
             static routes to NVM, use the tmsL3IpStaticRouteTable."
        ::= { tmsL3IpRoute 4 }

    tmsL3IpRouteEntry OBJECT-TYPE
        SYNTAX  TmsL3IpRouteEntry
        MAX-ACCESS  not-accessible
        STATUS  current
        DESCRIPTION
            "Provides enough routing information to support the UNIX style
             'netstat -nr' command and to support maintenance of the
             Routing Table."
        INDEX   { tmsL3IpRouteDest }
        ::= { tmsL3IpRouteTable 1 }

    TmsL3IpRouteEntry ::=
        SEQUENCE {
            tmsL3IpRouteDest        IpAddress,
            tmsL3IpRouteMask        IpAddress,
            tmsL3IpRouteNextHopIp   IpAddress,
            tmsL3IpRouteNextHopMac  MacAddress,
            tmsL3IpRouteIfIndex     Integer32,
            tmsL3IpRouteType        INTEGER,
            tmsL3IpRouteProto       INTEGER,
            tmsL3IpRouteAge         Unsigned32,
            tmsL3IpRouteMetric1     Integer32,
            tmsL3IpRouteUsingHw     TruthValue,
            tmsL3IpRouteIsStatic    TruthValue,
            tmsL3IpRouteFlags       Unsigned32,
            tmsL3IpRouteRef         Gauge32,
            tmsL3IpRouteUse         Counter32,
            tmsL3IpRouteRowStatus   RowStatus
        }

    tmsL3IpRouteDest OBJECT-TYPE
        SYNTAX  IpAddress
        MAX-ACCESS  not-accessible
        STATUS  current
        DESCRIPTION
            "The destination IP address of this route.  An
            entry with a value of 0.0.0.0 is considered a
            default route.  Multiple routes to a single
            destination can appear in the table, but access to
            such multiple entries is dependent on the table-
            access mechanisms defined by the network
            management protocol in use."
        ::= { tmsL3IpRouteEntry 1 }

    tmsL3IpRouteMask OBJECT-TYPE
        SYNTAX  IpAddress
        MAX-ACCESS  read-create
        STATUS  current
        DESCRIPTION
            "Indicate the mask to be logical-ANDed with the
            destination address before being compared to the
            value in the tmsL3IpRouteDest field.

            If the value of the tmsL3IpRouteDest is 0.0.0.0 (a
            default route), then the mask value is also
            0.0.0.0.  It should be noted that all IP routing
            subsystems implicitly use this mechanism."
        ::= { tmsL3IpRouteEntry 2 }
        
    tmsL3IpRouteNextHopIp OBJECT-TYPE
        SYNTAX  IpAddress
        MAX-ACCESS  read-create
        STATUS  current
        DESCRIPTION
            "The IP address of the next hop of this route.
            (In the case of a route bound to an interface
            which is realized via a broadcast media, the value
            of this field is the agent's IP address on that
            interface.)"
        ::= { tmsL3IpRouteEntry 3 }

    tmsL3IpRouteNextHopMac OBJECT-TYPE
        SYNTAX  MacAddress
        MAX-ACCESS  read-only
        STATUS  current
        DESCRIPTION
            "The six byte MAC address of the next hop of this
            route.  If the underlying hardware does not support this
            object, an octet string of zero length is returned."
        ::= { tmsL3IpRouteEntry 4 }

    tmsL3IpRouteIfIndex OBJECT-TYPE
        SYNTAX  Integer32
        MAX-ACCESS  read-only
        STATUS  current
        DESCRIPTION
            "The index value which uniquely identifies the
            local interface through which the next hop of this
            route should be reached.  The interface identified
            by a particular value of this index is the same
            interface as identified by the same value of
            ifIndex."
        ::= { tmsL3IpRouteEntry 5 }

    tmsL3IpRouteType OBJECT-TYPE
        SYNTAX  INTEGER {
            other(1),       -- none of the following
            invalid(2),     -- an invalidated route
            direct(3),      -- route to directly connected (sub-)network
            indirect(4)     -- route to a non-local 
                            -- host/network/sub-network
                }
        MAX-ACCESS  read-create
        STATUS  current
        DESCRIPTION
            "The type of route.  Note that the values
            direct(3) and indirect(4) refer to the notion of
            direct and indirect routing in the IP architecture.

            Setting this object to the value invalid(2) has
            the effect of invalidating the corresponding entry
            in the tmsL3IpRouteTable object.  That is, it
            effectively disassociates the destination
            identified with said entry from the route
            identified with said entry.  It is an
            implementation-specific matter as to whether the
            agent removes an invalidated entry from the table.
            Accordingly, management stations must be prepared
            to receive tabular information from agents that
            corresponds to entries not currently in use.
            Proper interpretation of such entries requires
            examination of the relevant tmsL3IpRouteType object."
        ::= { tmsL3IpRouteEntry 6 }

    tmsL3IpRouteProto OBJECT-TYPE
        SYNTAX  INTEGER {
            other(1),       -- none of the following

                            -- non-protocol information,
            local(2),       -- e.g., manually configured entries

            netmgmt(3),     -- set via a network management protocol

            icmp(4),        -- obtained via ICMP, e.g., Redirect

                            -- the remaining values are all gateway
                            -- routing protocols
            egp(5),
            ggp(6),
            hello(7),
            rip(8),
            is-is(9),
            es-is(10),
            ciscoIgrp(11),
            bbnSpfIgp(12),
            ospf(13),
            bgp(14)
                }
        MAX-ACCESS  read-only
        STATUS  current
        DESCRIPTION
            "The routing mechanism via which this route was
            learned.  Inclusion of values for gateway routing
            protocols is not intended to imply that hosts
            should support those protocols."
        ::= { tmsL3IpRouteEntry 7 }

    tmsL3IpRouteAge OBJECT-TYPE
        SYNTAX  Unsigned32
        MAX-ACCESS  read-only
        STATUS  current
        DESCRIPTION
            "The number of seconds since this route was last
            updated or otherwise determined to be correct.
            Note that no semantics of `too old' can be implied
            except through knowledge of the routing protocol
            by which the route was learned."
        ::= { tmsL3IpRouteEntry 8 }

    tmsL3IpRouteMetric1 OBJECT-TYPE
        SYNTAX  Integer32
        MAX-ACCESS  read-only
        STATUS  current
        DESCRIPTION
            "The primary routing metric for this route.  The
            semantics of this metric are determined by the
            routing-protocol specified in the route's
            tmsL3IpRouteProto value.  If this metric is not used,
            its value should be set to -1."
        ::= { tmsL3IpRouteEntry 9 }

    tmsL3IpRouteUsingHw OBJECT-TYPE
        SYNTAX  TruthValue
        MAX-ACCESS  read-only
        STATUS  current
        DESCRIPTION
            "This object is true(1) if this route is contained in
            the hardware routing table; otherwise, it is false(2)."
        ::= { tmsL3IpRouteEntry 10 }

    tmsL3IpRouteIsStatic OBJECT-TYPE
        SYNTAX  TruthValue
        MAX-ACCESS  read-only
        STATUS  current
        DESCRIPTION
            "This object is true(1) if this route is defined in the
            'tmsL3IpStaticRouteTable'.  This object is false(2) if this
            route was created dynamically (e.g., with RIP, OSPF) or was
            manually created using this table ('tmsL3IpRouteTable') or 
            the RFC1213 'ipRouteTable'."
        ::= { tmsL3IpRouteEntry 11 }

    tmsL3IpRouteFlags OBJECT-TYPE
        SYNTAX  Unsigned32
        MAX-ACCESS  read-only
        STATUS  current
        DESCRIPTION
            "Not implemented.  Returns '0'.
             
             Contains the information required for a netstat-like
             'Flags' field.
             
             The flags field represents a decimal value of the flags
             specified for a given route.  The following is a list of
             currently available flag values:
                 0x1     | - route is usable (that is, 'up')
                 0x2     | - destination is a gateway
                 0x4     | - host specific routing entry
                 0x8     | - host or net unreachable
                 0x10    | - created dynamically (by redirect)
                 0x20    | - modified dynamically (by redirect)
                 0x40    | - message confirmed
                 0x80    | - subnet mask present
                 0x100   | - generate new routes on use
                 0x200   | - external daemon resolves name
                 0x400   | - generated by ARP
                 0x800   | - manually added (static)
                 0x1000  | - just discard packets (during updates)
                 0x2000  | - modified by management protocol
                 0x4000  | - protocol specific routing flag
                 0x8000  | - protocol specific routing flag

            For example, if the entry in the Routing Table has a flag
            value of decimal 5, (0x1 OR'ed with 0x4), then this route
            is 'up' and usable and is host-specific."
        ::= { tmsL3IpRouteEntry 12 }

    tmsL3IpRouteRef OBJECT-TYPE
        SYNTAX  Gauge32
        MAX-ACCESS  read-only
        STATUS  current
        DESCRIPTION
            "Not implemented.  Returns '0'.
            
             Contains the information required for the netstat 'Ref'
             field, which indicates the number active uses for this
             route."
        ::= { tmsL3IpRouteEntry 13 }

    tmsL3IpRouteUse OBJECT-TYPE
        SYNTAX  Counter32
        MAX-ACCESS  read-only
        STATUS  current
        DESCRIPTION
            "Not implemented.  Returns '0'.
            
             Contains the information required for the netstat 'Use'
             field, which indicates the number of packets sent with
             this route."
        ::= { tmsL3IpRouteEntry 14 }

    tmsL3IpRouteRowStatus OBJECT-TYPE
        SYNTAX  RowStatus
        MAX-ACCESS  read-create
        STATUS  current
        DESCRIPTION
            "This object indicates the status of this entry.  A row in this
             table must be created using the createAndWait(5) action state
             (i.e., createAndGo(4) is not supported).  This object can only
             be set to active(1) for the specified 'tmsL3IpRouteDest' index
             value after the 'tmsL3IpRouteMask' and 'tmsL3IpRouteNextHop'
             objects for this row are valid.  Setting 'tmsL3IpRouteType' is
             optional.
             
             Note that the notInService(2) state is not supported.  Objects
             in this table row can be changed when this object is notReady(3)
             or active(1)."
        ::= { tmsL3IpRouteEntry 15 }


------------------------------------------------------------------------------
--  conformance information
------------------------------------------------------------------------------

--  --------------------------------------------------------------------------
--  units of conformance
--  --------------------------------------------------------------------------

    tmsL3IpMiscGroup    OBJECT-GROUP
        OBJECTS {
            tmsL3IpMiscNumLogicalPorts,
            tmsL3IpMiscRoutingProtocol,
            tmsL3IpMiscOspfv2Config
        }
        STATUS  current
        DESCRIPTION
           "This group configures and retrieves global, miscellaneous
            L3 objects."
        ::= { tmsL3MibGroups 1 }
    
    tmsL3IpSubnetGroup  OBJECT-GROUP
        OBJECTS {
            tmsL3IpSubnetMaxRows,
            tmsL3IpSubnetCurrentRows,
            tmsL3IpSubnetMask,
            tmsL3IpSubnetVidIface,
            tmsL3IpSubnetName,
            tmsL3IpSubnetRowStatus
        }
        STATUS  current
        DESCRIPTION
           "This group configures and retrieves IP subnet objects."
        ::= { tmsL3MibGroups 2 }
    
    tmsL3IpStaticGroup  OBJECT-GROUP
        OBJECTS {
            tmsL3IpStaticMaxHwHosts,
            tmsL3IpStaticNumStaticHwHosts,
            tmsL3IpStaticMaxHwSubnets,
            tmsL3IpStaticNumStaticHwSubnets,
            tmsL3IpStaticRouteMaxRows,
            tmsL3IpStaticRouteCurrentRows,
            tmsL3IpStaticRouteFlags,
            tmsL3IpStaticMask,
            tmsL3IpStaticNextHop,
            tmsL3IpStaticName,
            tmsL3IpStaticUseHw,
            tmsL3IpStaticInHw,
            tmsL3IpStaticRowStatus
        }
        STATUS  current
        DESCRIPTION
           "This group configures and retrieves IP static routes."
        ::= { tmsL3MibGroups 3 }

    tmsL3IpRouteGroup   OBJECT-GROUP
        OBJECTS {
            tmsL3IpRouteTableCurrentSwEntries,
            tmsL3IpRouteCurrentHwHosts,
            tmsL3IpRouteCurrentHwSubnets,
            tmsL3IpRouteMask,
            tmsL3IpRouteNextHopIp,
            tmsL3IpRouteNextHopMac,
            tmsL3IpRouteIfIndex,
            tmsL3IpRouteType,
            tmsL3IpRouteProto,
            tmsL3IpRouteAge,
            tmsL3IpRouteMetric1,
            tmsL3IpRouteUsingHw,
            tmsL3IpRouteIsStatic,
            tmsL3IpRouteFlags,
            tmsL3IpRouteRef,
            tmsL3IpRouteUse,
            tmsL3IpRouteRowStatus
        }
        STATUS  current
        DESCRIPTION
           "This group configures and retrieves IP routing info."
        ::= { tmsL3MibGroups 4 }

--  --------------------------------------------------------------------------
--  compliance statements
--  --------------------------------------------------------------------------

    tmsL3MibCompliance MODULE-COMPLIANCE
        STATUS  current
        DESCRIPTION
           "The compliance statement."
        MODULE  -- this module
        MANDATORY-GROUPS {
             tmsL3IpMiscGroup,
             tmsL3IpSubnetGroup,
             tmsL3IpStaticGroup,
             tmsL3IpRouteGroup
        }
        ::= { tmsL3MibCompliances 1 }

--
-- END of TMS-L3-MIB
--

END

------------------------------------------------------------------------------
------------------------------------------------------------------------------

    OEMMIB DEFINITIONS ::= BEGIN

    IMPORTS
        MODULE-IDENTITY, OBJECT-TYPE, NOTIFICATION-TYPE,
        Integer32, Counter64,TimeTicks,Counter32                    FROM SNMPv2-SMI
        
        DisplayString, TruthValue,               
        MacAddress                              FROM SNMPv2-TC
        
        MODULE-COMPLIANCE, OBJECT-GROUP         FROM SNMPv2-CONF
        oemProd                                 FROM WRS-MASTER-MIB;

    galnet MODULE-IDENTITY
        LAST-UPDATED    "0007120000Z"  -- July 12, 2000
        ORGANIZATION    "Wind River Systems, Inc."
        CONTACT-INFO    "Wind River Systems, Inc.
                         E-mail: support@windriver.com"

        DESCRIPTION     "TMS Broadcom GALNET StrataSwitch OEM-Product
                         Enterprise MIB definition."

        REVISION        "0007120000Z"  -- July 12, 2000
        DESCRIPTION     "Initial MIB creation."

        ::= { oemProd 2 }


------------------------------------------------------------------------------
-- Textual Conventions (i.e., these do not affect object encoding):
------------------------------------------------------------------------------
--
-- "DURABLE":
--    Objects that are saved across a system reset and/or power cycle
--    are noted as "DURABLE" for convenience in the DESCRIPTION
--    section of the object definition.  Code must be explicitly
--    written to implement these DURABLE objects.
--


------------------------------------------------------------------------------
--  define groups in OEM-GALNET-MIB
------------------------------------------------------------------------------
        
    
    oemArchIface            OBJECT IDENTIFIER ::= { galnet 1 }
    
    oemZxEdsl               OBJECT IDENTIFIER ::= { galnet 2 }

    oemZxEdslQos                    OBJECT IDENTIFIER ::= { galnet 3 }
    
    oemZxEdslLagTrunking                    OBJECT IDENTIFIER ::= { galnet 4 }
    
    oemZxGmrpApp            OBJECT IDENTIFIER ::= { galnet 5 }

    oemZxEndMib             OBJECT IDENTIFIER ::= { galnet 1000 }

    oemZxEdslBoard          OBJECT IDENTIFIER ::= { oemZxEdsl 1 }
    oemZxEdslTrap           OBJECT IDENTIFIER ::= { oemZxEdsl  2 }
    oemZxEdslSubBoard       OBJECT IDENTIFIER ::= { oemZxEdsl 4 }

    oemZxBSIU               OBJECT IDENTIFIER ::= { oemZxEdslSubBoard  1}
    oemZxFEIU               OBJECT IDENTIFIER ::= { oemZxEdslSubBoard  2 }
    oemZxFOIU               OBJECT IDENTIFIER ::= { oemZxEdslSubBoard  3 }
    oemZxGEIU               OBJECT IDENTIFIER ::= { oemZxEdslSubBoard  4 }
    oemZxSCB                OBJECT IDENTIFIER ::= { oemZxEdslSubBoard  5 }

------------------------------------------------------------------------------
   
PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING        
------------------------------------------------------------------------------


    oemArchIfaceTable OBJECT-TYPE
        SYNTAX SEQUENCE OF OemArchIfaceEntry
        MAX-ACCESS not-accessible
        STATUS current
        DESCRIPTION
            "A table of switch interfaces and associated properties.
            unit is always is 0 in EDSL device. "
        ::= { oemArchIface 1 }

    oemArchIfaceEntry OBJECT-TYPE
        SYNTAX OemArchIfaceEntry
        MAX-ACCESS not-accessible
        STATUS current
        DESCRIPTION
            "Table entry for switch interface control and status information."
--        INDEX { oemArchIfaceUnit, oemArchIfaceSlot,oemArchIfacePort }
      INDEX { oemArchIfacePort }
        ::= { oemArchIfaceTable 1 }

    OemArchIfaceEntry ::= SEQUENCE {
        oemArchIfaceSpeedDuplexSet      INTEGER, --oemArchIfaceUnit                Integer32,
        oemArchIfaceSpeedDuplexGet      INTEGER,  --oemArchIfaceSlot                Integer32,
        oemArchIfaceSubPort             Integer32,
        oemArchIfacePort                Integer32,        
        oemArchIfaceLLWHPort            Integer32,
        oemArchIfaceIfIndex             Integer32,
        oemArchIfaceName                DisplayString,
        oemArchIfaceEnable              TruthValue,
        oemArchIfaceSTPEnable           TruthValue,
        oemArchIfaceLink                INTEGER,
        oemDot1dGarpPortEnable          TruthValue,
        oemArchIfaceTrapEnable          INTEGER,
        oemArchIfacePaeEnable           INTEGER,
        oemArchIfaceRxIpInHdrErrors     Counter64,
        oemArchIfaceAutoNegotiateSet    INTEGER,
        oemArchIfaceAutoNegotiateGet    INTEGER,
          oemArchIfaceBroadcastRateLimit   Integer32
    }

    oemArchIfaceSpeedDuplexSet OBJECT-TYPE
        SYNTAX INTEGER 
        MAX-ACCESS read-write
        STATUS current
        DESCRIPTION
            "set speed and duplex value on the port. high word is speed, low word is duplex.
            speed have 10M(1),100M(2),1000M(3) and 10/100M(4); duplex have auto(1),half(2) 
            and full(3)."
        ::= { oemArchIfaceEntry 1 }

    oemArchIfaceSpeedDuplexGet OBJECT-TYPE
        SYNTAX INTEGER 
        MAX-ACCESS read-write
        STATUS current
        DESCRIPTION
            "Current speed and duplex value on the port. high word is speed, low word is duplex.
            speed have 10M(1),100M(2),1000M(3),auto-10M(4) and auto-100M(5); duplex have auto(1),half(2) 
            and full(3)."
        ::= { oemArchIfaceEntry 2 }

--    oemArchIfaceUnit OBJECT-TYPE
--        SYNTAX Integer32 (1..4)
--        MAX-ACCESS not-accessible
--        STATUS current
--        DESCRIPTION
--            "An index that uniquely identifies a unit in the TMS GALNET
--             stack.  If an invalid value is used for the index, a SNMP
--             'noSuchName' error (SNMPv1) or 'noSuchInstance' exception
--             (SNMPv2/v3) is returned.  For implementations that do not support
--             stacking, the same response is returned for any unit index other
--             than 1. In EDSL device ,the unit  always is 1."
--        ::= { oemArchIfaceEntry 1 }
--
--    oemArchIfaceSlot OBJECT-TYPE
--        SYNTAX Integer32 (1..12)
--        MAX-ACCESS not-accessible
--        STATUS current
--        DESCRIPTION
--            "An index that uniquely identifies the Slot."
--        ::= { oemArchIfaceEntry 2 }

    oemArchIfaceSubPort OBJECT-TYPE
        SYNTAX Integer32 (1..24)
        MAX-ACCESS not-accessible
        STATUS current
        DESCRIPTION
            "An index that uniquely identifies a slot port."
        ::= { oemArchIfaceEntry 3 }

    oemArchIfacePort OBJECT-TYPE
        SYNTAX Integer32 (1..248)
        MAX-ACCESS not-accessible
        STATUS current
        DESCRIPTION
            "An index that uniquely identifies a TMS Application 'logical port'
             (i.e., IEEE 802.3ad Aggregator) within the oemArchIfaceUnit."
        ::= { oemArchIfaceEntry 4 }

    oemArchIfaceLLWHPort OBJECT-TYPE
        SYNTAX Integer32 (8193..8296)
        MAX-ACCESS read-only
        STATUS current
        DESCRIPTION
            "A value that uniquely identifies a TMS Application 'logical port'
             (i.e., IEEE 802.3ad Aggregator) in the TMS GALNET stack.  This is
             a 'Layered Linear With Holes' (LLWH) port number that may may have
             holes for missing ports or units.  For this MIB, 26 port numbers
             are reserved for each unit in the stack.  For example, LLHW port
             8193 is unit 1, port 1 and LLHW 8228 is unit 2, port 10."
        ::= { oemArchIfaceEntry 5 }

    oemArchIfaceIfIndex OBJECT-TYPE
        SYNTAX Integer32
        MAX-ACCESS read-only
        STATUS current
        DESCRIPTION
            "The ifIndex of this TMS Application 'logical port' (i.e., IEEE
             802.3ad Aggregator).  Note that an ifIndex value of 34603009 
             (0x02100001) represents the Aggregator layer, unit 1, slot 0
             (base unit ports), port 1."
        ::= { oemArchIfaceEntry 6 }

    oemArchIfaceName OBJECT-TYPE
        SYNTAX DisplayString (SIZE (0..16))
        MAX-ACCESS read-write
        STATUS current
        DESCRIPTION
            "DURABLE:
             The textual name of this interface, e.g., 'John'."
        ::= { oemArchIfaceEntry 7 }
   
    oemArchIfaceEnable OBJECT-TYPE
        SYNTAX TruthValue
        MAX-ACCESS read-write
        STATUS current
        DESCRIPTION
            "DURABLE: { true:all }
             This object is true(1) when this interface is enabled and
             false(1) when it is disabled.  For this product, this is the
             ONLY way to enable or disable this interface.  Note that
             'ifAdminStatus' in RFC1213 and RFC2233 and 'dot1dStpPortEnable'
             in RFC1493 are each implemented as 'read-only'."
        ::= { oemArchIfaceEntry 8 }

    oemArchIfaceSTPEnable OBJECT-TYPE
        SYNTAX TruthValue
        MAX-ACCESS read-write
        STATUS current
        DESCRIPTION
            "DURABLE: { true:all }
             This object is true(1) when Spanning Tree operation is enabled
             for this interface and false(2) when it is disabled."
        ::= { oemArchIfaceEntry 9 }

    oemArchIfaceLink OBJECT-TYPE
        SYNTAX INTEGER {
             up(1), 
             down(2),
             invalid(3)
        }
        MAX-ACCESS read-only
        STATUS current
        DESCRIPTION
            "The state of Link Detect on this interface."
        ::= { oemArchIfaceEntry 10 }

    
--    oemDot1dGarpPortEnable OBJECT-TYPE
--      SYNTAX TruthValue 
--      MAX-ACCESS read-write
--      STATUS current
--      DESCRIPTION
--          "Enable/disable Garp on a port."
--      ::= { oemArchIfaceEntry 11 }

    oemArchIfaceTrapEnable OBJECT-TYPE
        SYNTAX INTEGER{
                enable(1),
                disable(2)
                }    
        MAX-ACCESS read-write
        STATUS current
        DESCRIPTION
            "Enable/disable send trap of linkup or linkdown."
        ::= { oemArchIfaceEntry 12 }

    oemArchIfacePaeEnable OBJECT-TYPE
        SYNTAX INTEGER{
                enable(1),
                disable(2)
                }   
        MAX-ACCESS read-write
        STATUS current
        DESCRIPTION
            "Enable/disable 802.1x on this interface."
        ::= { oemArchIfaceEntry 13 }

    oemArchIfaceRxIpInHdrErrors OBJECT-TYPE
        SYNTAX Counter64 
        MAX-ACCESS read-only
        STATUS current
        DESCRIPTION
            "The number of Layer 3 packets received on this interface that
             were discarded due to IP header errors (e.g., bad checksum,
             invalid versions, format errors)."
        ::= { oemArchIfaceEntry 14 }

    oemArchIfaceAutoNegotiateSet OBJECT-TYPE
        SYNTAX INTEGER 
        MAX-ACCESS read-write
        STATUS current
        DESCRIPTION
            "Set auto-negotiate speed and duplex value on the port. 1 for enalbe auto-negotiate, 2 for disalbe auto-negotiate."
        ::= { oemArchIfaceEntry 15 }
     
    oemArchIfaceAutoNegotiateGet OBJECT-TYPE
        SYNTAX INTEGER 
        MAX-ACCESS read-only
        STATUS current
        DESCRIPTION
            "Get auto-negotiate speed and duplex value on the port."
        ::= { oemArchIfaceEntry 16 }   

   oemArchIfaceBroadcastRateLimit    OBJECT-TYPE
          SYNTAX         Integer32
          MAX-ACCESS     read-write
          STATUS         current
          DESCRIPTION
           "At present, only ADSL port support it.
           The range is 0~65535 pps(package/s).
           If the value is 0, broadcast packets will not be allowed to pass.
           If the value is 0xFFFFFFFF, there will be no limit."
          ::= { oemArchIfaceEntry 17}



------------------------------------------------------------------------------------
------------------------------------------------------------------------------------

oemPortLocationDhcpRelay   OBJECT-TYPE
           SYNTAX     INTEGER
           {
            disable(0),
            standard(1),
            option60(2)
          }
        MAX-ACCESS read-write
        STATUS current
        DESCRIPTION
            ""
        ::= { oemArchIface 2}


 dhcpL3IfaceTable OBJECT-TYPE
        SYNTAX SEQUENCE OF DhcpL3IfaceEntry
        MAX-ACCESS not-accessible
        STATUS current
        DESCRIPTION
            ""
        ::= { oemArchIface 3 }
        
   dhcpL3IfaceEntry OBJECT-TYPE
        SYNTAX DhcpL3IfaceEntry
        MAX-ACCESS not-accessible
        STATUS current
        DESCRIPTION
            ""
      INDEX { dhcpL3IfaceIndex }
        ::= { dhcpL3IfaceTable 1 }      


    DhcpL3IfaceEntry ::= SEQUENCE {
        dhcpL3IfaceIndex            INTEGER,
        dhcpL3IfaceIpAddress        IpAddress,
        dhcpL3IfaceIpMask           IpAddress,
        dhcpL3IfacePrimDhcpServerIp IpAddress,
        dhcpL3IfaceSecndDhcpServerIp IpAddress,
        dhcpL3Ifacerowstatus        INTEGER
    }  

  dhcpL3IfaceIndex OBJECT-TYPE
        SYNTAX      INTEGER
        MAX-ACCESS  read-write
        STATUS      current
        DESCRIPTION
            ""
        REFERENCE
            ""
          ::= { dhcpL3IfaceEntry 1}   

    dhcpL3IfaceIpAddress OBJECT-TYPE
        SYNTAX      IpAddress
        MAX-ACCESS  read-write
        STATUS      current
        DESCRIPTION
            ""
        REFERENCE
            ""
          ::= { dhcpL3IfaceEntry 2}  
      
    dhcpL3IfaceIpMask OBJECT-TYPE
        SYNTAX      IpAddress
        MAX-ACCESS  read-write
        STATUS      current
        DESCRIPTION
            ""
        REFERENCE
            ""
          ::= { dhcpL3IfaceEntry 3}    

    dhcpL3IfacePrimDhcpServerIp OBJECT-TYPE
        SYNTAX      IpAddress
        MAX-ACCESS  read-write
        STATUS      current
        DESCRIPTION
            ""
        REFERENCE
            "Primary ServerIp of L3 interface "
          ::= { dhcpL3IfaceEntry 4}  

    dhcpL3IfaceSecndDhcpServerIp OBJECT-TYPE
        SYNTAX      IpAddress
        MAX-ACCESS  read-write
        STATUS      current
        DESCRIPTION
            "Secondary ServerIp of L3 interface "
        REFERENCE
            ""
          ::= { dhcpL3IfaceEntry 5}  
          
    dhcpL3Ifacerowstatus OBJECT-TYPE
        SYNTAX      INTEGER
        MAX-ACCESS  read-write
        STATUS      current
        DESCRIPTION
            ""
        REFERENCE
            ""
          ::= { dhcpL3IfaceEntry 6}   
          
------------------------------------------------------------------------------------
------------------------------------------------------------------------------------
--  the slot table

   -- The slot table contains card information on the device's
   -- slot.  

    oemZxEdslCardNum    OBJECT-TYPE
        SYNTAX          Integer32
        MAX-ACCESS      read-only
        STATUS          current
        DESCRIPTION
                        "The number of slot in the EDSL device. 
                        In EDSL device the slot number is 12."
        ::= { oemZxEdslBoard 1 }

  
    oemZxEdslCardTable      OBJECT-TYPE
        SYNTAX SEQUENCE OF OemZxEdslCardEntry
        MAX-ACCESS not-accessible
        STATUS current
        DESCRIPTION
            "A list of card entries."
        ::= { oemZxEdslBoard 2 }

    oemZxEdslCardEntry OBJECT-TYPE
        SYNTAX OemZxEdslCardEntry 
        MAX-ACCESS not-accessible
        STATUS current
        DESCRIPTION
            "An card entry containing objects 
            describing the card in some slot."
        INDEX { oemZxEdslCardIndex }
        ::= { oemZxEdslCardTable 1 }

    OemZxEdslCardEntry ::= SEQUENCE {
        oemZxEdslCardIndex              Integer32,
        oemZxEdslCardType               INTEGER,
        oemZxEdslCardDescr              DisplayString,
        oemZxEdslCardSlot               Integer32,
        oemZxEdslCardPortNum            Integer32,
        oemZxEdslCardPortType           INTEGER,
        oemZxEdslCardState              INTEGER,
        oemZxEdslCardVersion            Integer32,
        oemZxEdslCardLastChange         TimeTicks,
        oemZxEdslCardSoftVersion        Integer32,
        oemZxEdslCardName            DisplayString,
        oemZxEdslPortName               DisplayString,
        oemZxEdslnewCardVersion        OCTET STRING,
        oemZxEdslnewCardSoftVersion    OCTET STRING
    }
        
        
    oemZxEdslCardIndex  OBJECT-TYPE
        SYNTAX          Integer32 (1..12)
        MAX-ACCESS      read-only
        STATUS          current
        DESCRIPTION
                "A unique value  for each slot interface.  It is 
                recommended that values are assigned contiguously
                 starting from 1. "
        ::= { oemZxEdslCardEntry 1 }

    oemZxEdslCardType   OBJECT-TYPE
        SYNTAX          INTEGER
        MAX-ACCESS      read-write
        STATUS          current
        DESCRIPTION
                "The type of card, distinguished according 
                to service type carried or function."
        ::= { oemZxEdslCardEntry 2 }

    oemZxEdslCardDescr  OBJECT-TYPE
        SYNTAX          DisplayString (SIZE (0..255)) 
        MAX-ACCESS      read-only
        STATUS          current
        DESCRIPTION
                "A textual string containing information about 
                the card. This string should include the manufacturer, 
                the product name, type, function and version of the 
                hardware."
        ::= { oemZxEdslCardEntry 3 }

    oemZxEdslCardSlot   OBJECT-TYPE
        SYNTAX          Integer32(1..12) 
        MAX-ACCESS      read-only
        STATUS          current
        DESCRIPTION
                "The number of slot which contained this card."
        ::= { oemZxEdslCardEntry 4 }

    oemZxEdslCardPortNum        OBJECT-TYPE
        SYNTAX          Integer32(2..24) 
        MAX-ACCESS      read-only
        STATUS          current
        DESCRIPTION
                "The number of port which the card contain."
        ::= { oemZxEdslCardEntry 5 }

    oemZxEdslCardPortType       OBJECT-TYPE
        SYNTAX          INTEGER {  
            port10BASES(1),     -- VDSL port.
            port10-100ME(2),    -- 10/100M Ethernet port.
            port100MO(3),       -- 100M  optical Ethernet port.
            port1000MO(4),      -- 1000M optical Ethernet port.
            portVTHERNET(5),    -- VTHERNET port.
            portSHDSL(6),       -- SHDSL port.
            portADSL(7),        -- ADSL port.
            portMULTI(8),      --  10/100M Ethernet port and 100M  optical Ethernet port.
            unknown(10)         --unknown port type.            
        }
        MAX-ACCESS      read-only
        STATUS          current
        DESCRIPTION
                "The type of port which the card contain."
        ::= { oemZxEdslCardEntry 6 }

    oemZxEdslCardState  OBJECT-TYPE
        SYNTAX          INTEGER {
            up(1),      --ready.
            down(2),    --deactiivate.
            testing(3),         --in some test mode.
            master(4),  --
            slave(5)    --
        }
        
        MAX-ACCESS      read-only
        STATUS          current
        DESCRIPTION
                "The state of the card. "
        ::= { oemZxEdslCardEntry 7 }

    oemZxEdslCardVersion        OBJECT-TYPE
        SYNTAX          Integer32 
        MAX-ACCESS      read-only
        STATUS          current
        DESCRIPTION
                "The hardware version of the card."
        ::= { oemZxEdslCardEntry 8 }

    oemZxEdslCardLastChange     OBJECT-TYPE
        SYNTAX          TimeTicks 
        MAX-ACCESS      read-only
        STATUS          current
        DESCRIPTION
                "The value of sysUpTime at the time the card 
                entered its current operational state. If the 
                current state was entered prior to the last 
                reinitialization of the local network management 
                subsystem, then this object contains a zero value."
        ::= { oemZxEdslCardEntry 9 }

    oemZxEdslCardSoftVersion    OBJECT-TYPE
        SYNTAX          Integer32 
        MAX-ACCESS      read-only
        STATUS          current
        DESCRIPTION
                "The software version of the card.
                high word is main version,
                high byte in low word is slave version,
                low byte in low word is patch version"
        ::= { oemZxEdslCardEntry 10 }

    oemZxEdslCardName    OBJECT-TYPE
        SYNTAX          DisplayString (SIZE (0..255)) 
        MAX-ACCESS      read-only
        STATUS          current
        DESCRIPTION
                "display card name"
        ::= { oemZxEdslCardEntry 11 }

    oemZxEdslPortName    OBJECT-TYPE
        SYNTAX          DisplayString (SIZE (0..255)) 
        MAX-ACCESS      read-only
        STATUS          current
        DESCRIPTION
                "display port name"
        ::= { oemZxEdslCardEntry 12 }

    oemZxEdslnewCardVersion    OBJECT-TYPE
        SYNTAX          OCTET STRING (SIZE (0..16)) 
        MAX-ACCESS      read-write
        STATUS          current
        DESCRIPTION
                "the new type of card version"
        ::= { oemZxEdslCardEntry 13 }

    oemZxEdslnewCardSoftVersion    OBJECT-TYPE
        SYNTAX          OCTET STRING (SIZE (0..16)) 
        MAX-ACCESS      read-write
        STATUS          current
        DESCRIPTION
                "the new type of card software version"
        ::= { oemZxEdslCardEntry 14 }

--  
--      vdsl Config Table 
--
   oemZxVdslConfigTable OBJECT-TYPE
        SYNTAX  SEQUENCE OF OemZxVdslCfgEntry
        MAX-ACCESS  not-accessible
        STATUS  current
        DESCRIPTION
              "A table that contains general config information 
              about every VDSL port that is associated with this switch."
        ::= { oemZxBSIU 1 }
        
   oemZxVdslCfgEntry  OBJECT-TYPE
        SYNTAX  OemZxVdslCfgEntry
        MAX-ACCESS  not-accessible
        STATUS  current
        DESCRIPTION
                "A list of general VDSL information for each port."
        INDEX  { oemVdslCfgIndex  }
        ::= { oemZxVdslConfigTable 1 }


   OemZxVdslCfgEntry ::=
        SEQUENCE {
            oemVdslCfgIndex             INTEGER,
            oemVdslCfgState             INTEGER,

            oemVdslCfgLTReset           INTEGER,
            oemVdslCfgLTActive          INTEGER,
            oemVdslCfgLTLcLoop          INTEGER,
            oemVdslCfgLTLnLoop          INTEGER,
            oemVdslCfgLTTransOnOff      INTEGER,

            oemVdslCfgNTReset           INTEGER,
            oemVdslCfgNTLnLoop          INTEGER,

            oemVdslLinkUpInterp         INTEGER,
            oemVdslLinkDownInterp       INTEGER,
            oemVdslLinkUpConste         INTEGER,
            oemVdslLinkDownConste       INTEGER,
            oemVdslLinkUpRate           INTEGER,
            oemVdslLinkDownRate         INTEGER,
            oemVdslLinkUpFreq           INTEGER,
            oemVdslLinkDownFreq         INTEGER,
            oemVdslLinkTrapEnable       INTEGER,
            oemVdslLinkPowerBack        INTEGER,
            oemVdslLinkLTMaxPSD         INTEGER,
            oemVdslLinkNTMaxPSD         INTEGER,
            oemVdslLinkNTMinPSD         INTEGER,
            oemVdslLinkLTTransNotch     INTEGER,
            oemVdslLinkNTTransNotch     INTEGER,
            oemVdslLinkLTInterDepth     INTEGER,
            oemVdslLinkNTInterDepth     INTEGER,
            
                oemVdslCfgRead                  INTEGER,
                oemVdslLinkRead                 INTEGER,                        
                oemVdslLinkUpdate         INTEGER,
                oemVdslLinkSaveReset      INTEGER,
                oemVdslLinkAutochg        INTEGER       ,
                oemVdslLinkCurUSRate      INTEGER,
                 oemVdslLinkCurDSRate      INTEGER,
                 oemVdslLinkConfAuto         INTEGER,

                 oemVdslLinkReserved1      INTEGER,
                 oemVdslLinkReserved2      INTEGER,
                 oemVdslLinkReserved3      INTEGER,
                 oemVdslLinkReserved4      INTEGER,
                 oemVdslLinkReserved5      INTEGER,
                 oemVdslLinkReserved6      INTEGER,
                 oemVdslLinkReserved7      INTEGER,
                 oemVdslLinkReserved8      INTEGER,
                 oemVdslLinkReserved9      INTEGER,
                 oemVdslLinkReserved10      INTEGER

        }
        
   oemVdslCfgIndex OBJECT-TYPE
          SYNTAX        INTEGER (1..244)
          MAX-ACCESS      not-accessible
          STATUS        current
          DESCRIPTION
                  "The index of the VDSL config table. it associate 
                  with port."
          ::= { oemZxVdslCfgEntry 1 }
        
   oemVdslCfgState OBJECT-TYPE
          SYNTAX        INTEGER {
                valid(1),       
                invalid(2),
                unknown(3)
                }
          MAX-ACCESS    read-only
          STATUS        current
          DESCRIPTION
                  "The port is VDSL port or not. if the port is not VDSL
                  the items below are invalid."
          ::= { oemZxVdslCfgEntry 2 }

   oemVdslCfgLTReset OBJECT-TYPE
          SYNTAX  INTEGER {
                        reset(1)                      
                  }
          MAX-ACCESS  read-write
          STATUS  current
          DESCRIPTION
                  "Reset the LT of the port."
          ::= { oemZxVdslCfgEntry 3 }
          
   oemVdslCfgLTActive OBJECT-TYPE
          SYNTAX  INTEGER {
                      activate(1),
                      deactivate(2)
                  }
          MAX-ACCESS  read-write
          STATUS  current
          DESCRIPTION
                  "Activate/deactivate the LT of the port."
          ::= { oemZxVdslCfgEntry 4 }
          
   oemVdslCfgLTLcLoop OBJECT-TYPE
          SYNTAX  INTEGER {
                      loop(1),  -- set and get operation.
                                  noloop(2),
                                  unknown(3)
                  }
          MAX-ACCESS  read-write
          STATUS  current
          DESCRIPTION
                  "LT local loop test on the port."
          ::= { oemZxVdslCfgEntry 5 }

   oemVdslCfgLTLnLoop OBJECT-TYPE
          SYNTAX  INTEGER {
                      loop(1),  -- set and get operation.
                                  noloop(2),
                                  unknown(3)
                  }
          MAX-ACCESS  read-write
          STATUS  current
          DESCRIPTION
                  "LT line loop test on the port."
          ::= { oemZxVdslCfgEntry 6 }

   oemVdslCfgLTTransOnOff OBJECT-TYPE
          SYNTAX  INTEGER {
                      enable(1),
                      disable(2),
                      unknown(3)
                  }
          MAX-ACCESS  read-write
          STATUS  current
          DESCRIPTION
                  "Enable/disable Transmitter of the port
                  when link deactivation."
          ::= { oemZxVdslCfgEntry 7 }


   oemVdslCfgNTReset OBJECT-TYPE
          SYNTAX  INTEGER {
                      reset(1)                      
                  }
          MAX-ACCESS  read-write
          STATUS  current
          DESCRIPTION
                  "NT reset on the port.."
          ::= { oemZxVdslCfgEntry 8 }

   oemVdslCfgNTLnLoop OBJECT-TYPE
          SYNTAX  INTEGER {
                      loop(1),  -- set and get operation.
                                  noloop(2),
                                  unknown(3)
                  }
          MAX-ACCESS  read-write
          STATUS  current
          DESCRIPTION
                  "NT line loop test on the port."
          ::= { oemZxVdslCfgEntry 9 }

   oemVdslLinkUpInterp OBJECT-TYPE
          SYNTAX  INTEGER 
          MAX-ACCESS  read-write
          STATUS  current
          DESCRIPTION
                  "Linkup interpolation of the port. the value is 
                  4,6,8,10,12,14,16,24,32,48,64."
          ::= { oemZxVdslCfgEntry 10 }

   oemVdslLinkDownInterp OBJECT-TYPE
          SYNTAX  INTEGER 
          MAX-ACCESS  read-write
          STATUS  current
          DESCRIPTION
                  "Linkdown interpolation of the port.The value is
                  4,6,8,10,12,14,16,24,32,48 or 64."
          ::= { oemZxVdslCfgEntry 11 }

   oemVdslLinkUpConste OBJECT-TYPE
          SYNTAX  INTEGER 
          MAX-ACCESS  read-write
          STATUS  current
          DESCRIPTION
                  "Linkup constellation of the port. The value is 
                  4,8,16,32,64,128 or 256 ."
          ::= { oemZxVdslCfgEntry 12 }

   oemVdslLinkDownConste OBJECT-TYPE
          SYNTAX  INTEGER 
          MAX-ACCESS  read-write
          STATUS  current
          DESCRIPTION
                  "Linkdown constellation of the port. The value is 
                  4,8,16,32,64,128 or 256 ."
          ::= { oemZxVdslCfgEntry 13 }

   oemVdslLinkUpRate OBJECT-TYPE
          SYNTAX  INTEGER 
          MAX-ACCESS  read-only
          STATUS  current
          DESCRIPTION
                  "Linkup Rate of the port."
          ::= { oemZxVdslCfgEntry 14 }

   oemVdslLinkDownRate OBJECT-TYPE
          SYNTAX  INTEGER 
          MAX-ACCESS  read-only
          STATUS  current
          DESCRIPTION
                  "Linkdown rate of the port."
          ::= { oemZxVdslCfgEntry 15 }

   oemVdslLinkUpFreq OBJECT-TYPE
          SYNTAX  INTEGER(0..800) 
          MAX-ACCESS  read-write
          STATUS  current
          DESCRIPTION
                  "Linkup frequence of the port."
          ::= { oemZxVdslCfgEntry 16 }

   oemVdslLinkDownFreq OBJECT-TYPE
          SYNTAX  INTEGER(0..800) 
          MAX-ACCESS  read-write
          STATUS  current
          DESCRIPTION
                  "Linkdown frequence of the port."
          ::= { oemZxVdslCfgEntry 17 }

   oemVdslLinkTrapEnable OBJECT-TYPE
          SYNTAX  INTEGER {
                       enable(1),
                       disable(2)
                  }
          MAX-ACCESS  read-write
          STATUS  current
          DESCRIPTION
                  "Enable/disable vdsl trap ."
          ::= { oemZxVdslCfgEntry 18 }

   oemVdslLinkPowerBack OBJECT-TYPE
          SYNTAX  INTEGER {
                       enable(1),
                       disable(2)
                  }
          MAX-ACCESS  read-write
          STATUS  current
          DESCRIPTION
                  "power back off mode enable/disable of the port."
          ::= { oemZxVdslCfgEntry 19 }

   oemVdslLinkLTMaxPSD OBJECT-TYPE
          SYNTAX  INTEGER(55..100) 
          MAX-ACCESS  read-write
          STATUS  current
          DESCRIPTION 
                "Max PSD of the port."
          ::= { oemZxVdslCfgEntry 20 }

   oemVdslLinkNTMaxPSD OBJECT-TYPE
          SYNTAX  INTEGER(55..100)
          MAX-ACCESS  read-write
          STATUS  current
          DESCRIPTION
                  "NT MAX PSD of the port."
          ::= { oemZxVdslCfgEntry 21 }

   oemVdslLinkNTMinPSD OBJECT-TYPE
          SYNTAX  INTEGER(55..100)
          MAX-ACCESS  read-write
          STATUS  current
          DESCRIPTION
                  "NT MIN PSD of the port."
          ::= { oemZxVdslCfgEntry 22 }

   oemVdslLinkLTTransNotch OBJECT-TYPE
          SYNTAX  INTEGER{
                       enable(1),
                       disable(2)
                  }
          MAX-ACCESS  read-write
          STATUS  current
          DESCRIPTION
                  "LT transmit notch of the port."
          ::= { oemZxVdslCfgEntry 23 }

   oemVdslLinkNTTransNotch OBJECT-TYPE
          SYNTAX  INTEGER {
                       enable(1),
                       disable(2)
                  }
          MAX-ACCESS  read-write
          STATUS  current
          DESCRIPTION
                  "NT transmit notch of the port."
          ::= { oemZxVdslCfgEntry 24 }

   oemVdslLinkLTInterDepth OBJECT-TYPE
          SYNTAX  INTEGER 
          MAX-ACCESS  read-write
          STATUS  current
          DESCRIPTION
                  "LT interleaver depth of the port. The value is
                  0,1,2,8 or 16."
          ::= { oemZxVdslCfgEntry 25 }

   oemVdslLinkNTInterDepth OBJECT-TYPE
          SYNTAX  INTEGER 
          MAX-ACCESS  read-write
          STATUS  current
          DESCRIPTION
                  "LT interleaver depth of the port. The value is
                  0,1,2,8 or 16."
          ::= { oemZxVdslCfgEntry 26 }

   oemVdslCfgRead OBJECT-TYPE
          SYNTAX  INTEGER {
                     readreg(1)
                                                } 
          MAX-ACCESS  read-write
          STATUS  current
          DESCRIPTION
                  "Gen conf reg read operation."
          ::= { oemZxVdslCfgEntry 27 }

   oemVdslLinkRead OBJECT-TYPE
          SYNTAX  INTEGER{
                          readsetval(1),
                         readcurval(2) 
                                        } 
          MAX-ACCESS  read-write
          STATUS  current
          DESCRIPTION
                  "lnk conf register read operation."
          ::= { oemZxVdslCfgEntry 28 }

   oemVdslLinkUpdate OBJECT-TYPE
          SYNTAX  INTEGER{
                         update1s1p(1),  -- update one port of one slot
                          update1sap(2),   -- update all port of one slot
                         updateas1p(3),   -- update one same port of all slot
                         updateasap(4)    -- update all port of all slot
                                } 
          MAX-ACCESS  read-write
          STATUS  current
          DESCRIPTION
                  "lnk conf register update operation."
          ::= { oemZxVdslCfgEntry 29 }

   oemVdslLinkSaveReset OBJECT-TYPE
          SYNTAX  INTEGER{
                         savereg(1)
                                } 
          MAX-ACCESS  read-write
          STATUS  current
          DESCRIPTION
                  "lnk conf register save operation and LTNT reset."
          ::= { oemZxVdslCfgEntry 30 }

   oemVdslLinkAutochg OBJECT-TYPE
          SYNTAX  INTEGER{
                      enable(1),
                       disable(2)
                                } 
          MAX-ACCESS  read-write
          STATUS  current
          DESCRIPTION
                  "Link speed auto change enable/disable of the port."
          ::= { oemZxVdslCfgEntry 31 }

   oemVdslLinkCurUSRate OBJECT-TYPE
          SYNTAX  INTEGER
          MAX-ACCESS  read-only
          STATUS  current
          DESCRIPTION
                  "Current  US rate of the port."
          ::= { oemZxVdslCfgEntry 32 }

   oemVdslLinkCurDSRate OBJECT-TYPE
          SYNTAX  INTEGER
          MAX-ACCESS  read-only
          STATUS  current
          DESCRIPTION
                  "Current  DS rate of the port."
          ::= { oemZxVdslCfgEntry 33 }
   
    oemVdslLinkConfAuto OBJECT-TYPE
          SYNTAX  INTEGER{
                       enable(1),
                       disable(2)
                  }
          MAX-ACCESS  read-write
          STATUS  current
          DESCRIPTION
                  "auto set link of all ports ."
          ::= { oemZxVdslCfgEntry 34 }
   
           
   oemVdslLinkReserved1 OBJECT-TYPE
          SYNTAX  INTEGER
          MAX-ACCESS  read-only
          STATUS  current
          DESCRIPTION
                  "Current  DS rate of the port."
          ::= { oemZxVdslCfgEntry 35 }

   oemVdslLinkReserved2 OBJECT-TYPE
          SYNTAX  INTEGER
          MAX-ACCESS  read-only
          STATUS  current
          DESCRIPTION
                  "Reserved."
          ::= { oemZxVdslCfgEntry 36 }

   oemVdslLinkReserved3 OBJECT-TYPE
          SYNTAX  INTEGER
          MAX-ACCESS  read-only
          STATUS  current
          DESCRIPTION
                  "Reserved."
          ::= { oemZxVdslCfgEntry 37 }
          
   oemVdslLinkReserved4 OBJECT-TYPE
          SYNTAX  INTEGER
          MAX-ACCESS  read-only
          STATUS  current
          DESCRIPTION
                  "Reserved."
          ::= { oemZxVdslCfgEntry 38 }

   oemVdslLinkReserved5 OBJECT-TYPE
          SYNTAX  INTEGER
          MAX-ACCESS  read-only
          STATUS  current
          DESCRIPTION
                  "Reserved."
          ::= { oemZxVdslCfgEntry 39 }
   
   oemVdslLinkReserved6 OBJECT-TYPE
          SYNTAX  INTEGER
          MAX-ACCESS  read-only
          STATUS  current
          DESCRIPTION
                  "Reserved."
          ::= { oemZxVdslCfgEntry 40 }
   
   oemVdslLinkReserved7 OBJECT-TYPE
          SYNTAX  INTEGER
          MAX-ACCESS  read-only
          STATUS  current
          DESCRIPTION
                  "Reserved."
          ::= { oemZxVdslCfgEntry 41 }

   oemVdslLinkReserved8 OBJECT-TYPE
          SYNTAX  INTEGER
          MAX-ACCESS  read-only
          STATUS  current
          DESCRIPTION
                  "Reserved."
          ::= { oemZxVdslCfgEntry 42 }

   oemVdslLinkReserved9 OBJECT-TYPE
          SYNTAX  INTEGER
          MAX-ACCESS  read-only
          STATUS  current
          DESCRIPTION
                  "Reserved."
          ::= { oemZxVdslCfgEntry 43 }

   oemVdslLinkReserved10 OBJECT-TYPE
          SYNTAX  INTEGER
          MAX-ACCESS  read-only
          STATUS  current
          DESCRIPTION
                  "Reserved."
          ::= { oemZxVdslCfgEntry 44 }

--
-- This is VDSL statisitc table
--
   oemZxVdslStatTable OBJECT-TYPE
        SYNTAX  SEQUENCE OF OemZxVdslStatEntry
        MAX-ACCESS  not-accessible
        STATUS  current
        DESCRIPTION
              "A table that contains general status information 
              about every VDSL port that is associated with this switch."
        ::= { oemZxBSIU 2 }

   oemZxVdslStatEntry  OBJECT-TYPE
        SYNTAX   OemZxVdslStatEntry
        MAX-ACCESS  not-accessible
        STATUS  current
        DESCRIPTION
                "A list of general VDSL information for each port."
        INDEX  { oemVdslCfgIndex  }
        ::= { oemZxVdslStatTable 1 }


   OemZxVdslStatEntry ::=
        SEQUENCE {

            oemVdslStatSNR              INTEGER,
            oemVdslStatMSE              INTEGER,
            oemVdslStatCRSE             INTEGER,
            oemVdslStatTPower           INTEGER,
            oemVdslStatLnkStat          INTEGER,
            oemVdslStatLnkFail          INTEGER,
            oemVdslStatPMDStat          BITS,
            
            oemVdslNTStatSNR            INTEGER,
            oemVdslNTStatMSE            INTEGER,
            oemVdslNTStatCRSE           INTEGER,
            oemVdslNTStatTPower         INTEGER,
            oemVdslRecvPauseFrames      INTEGER,
            oemVdslRecvBroadcastFrames  INTEGER,
            oemVdslCollisionCounters    INTEGER,
            oemVdslSingleCollision      INTEGER,
            oemVdslMultipleCollision    INTEGER,
            oemVdslLateCollision        INTEGER,
            oemVdslExcessiveCollision   Counter32,
            oemVdslErrorCounters        Counter32,
            oemVdslReceivedError        Counter32,
            oemVdslCarrierError         Counter32,
            oemVdslFrameTooLongError    Counter32,
            oemVdslFrameCRCError        Counter32
        }       

   oemVdslStatSNR OBJECT-TYPE
          SYNTAX        INTEGER
          MAX-ACCESS    read-only
          STATUS        current
          DESCRIPTION
                  "The SNR of recv signal of the port ."
          ::= { oemZxVdslStatEntry 1 }

   oemVdslStatMSE OBJECT-TYPE
          SYNTAX        INTEGER
          MAX-ACCESS    read-only
          STATUS        current
          DESCRIPTION
                  "The mean square error of the port ."
          ::= { oemZxVdslStatEntry 2 }

   oemVdslStatCRSE OBJECT-TYPE
          SYNTAX        INTEGER 
          MAX-ACCESS    read-only
          STATUS        current
          DESCRIPTION
                  "The corrected rs error of the port ."
          ::= { oemZxVdslStatEntry 3 }

   oemVdslStatTPower OBJECT-TYPE
          SYNTAX        INTEGER 
          MAX-ACCESS    read-only
          STATUS        current
          DESCRIPTION
                  "The tramsmit power of the port ."
          ::= { oemZxVdslStatEntry 4 }

   oemVdslStatLnkStat OBJECT-TYPE
          SYNTAX        INTEGER {
               up(1),
               down(2),
               testing(3)
          }
          MAX-ACCESS    read-only
          STATUS        current
          DESCRIPTION
                  "The vdsl link state of the port ."
          ::= { oemZxVdslStatEntry 5 }

   oemVdslStatLnkFail OBJECT-TYPE
          SYNTAX        INTEGER 
          MAX-ACCESS    read-only
          STATUS        current
          DESCRIPTION
                  "The link fail count of the port ."
          ::= { oemZxVdslStatEntry 6 }

   oemVdslStatPMDStat OBJECT-TYPE
          SYNTAX        BITS {
              microInter(0),
              agcConverged(1),
              timConverged(2),
              adcSaturation(3)
          }
          MAX-ACCESS    read-only
          STATUS        current
          DESCRIPTION
                  "The PMD state of the port ."
          ::= { oemZxVdslStatEntry 7 }

   oemVdslNTStatSNR OBJECT-TYPE
          SYNTAX        INTEGER
          MAX-ACCESS    read-only
          STATUS        current
          DESCRIPTION
                  " ."
          ::= { oemZxVdslStatEntry 8 }

   oemVdslNTStatMSE OBJECT-TYPE
          SYNTAX        INTEGER 
          MAX-ACCESS    read-only
          STATUS        current
          DESCRIPTION
                  " ."
          ::= { oemZxVdslStatEntry 9 }

   oemVdslNTStatCRSE OBJECT-TYPE
          SYNTAX        INTEGER 
          MAX-ACCESS    read-only
          STATUS        current
          DESCRIPTION
                  "."
          ::= { oemZxVdslStatEntry 10 }

   oemVdslNTStatTPower OBJECT-TYPE
          SYNTAX        INTEGER 
          MAX-ACCESS    read-only
          STATUS        current
          DESCRIPTION
                  "."
          ::= { oemZxVdslStatEntry 11 }

   oemVdslRecvPauseFrames OBJECT-TYPE
          SYNTAX        INTEGER
          MAX-ACCESS    read-only
          STATUS        current
          DESCRIPTION
                  "Received pause frame couter ."
          ::= { oemZxVdslStatEntry 12 }

   oemVdslRecvBroadcastFrames OBJECT-TYPE
          SYNTAX        INTEGER 
          MAX-ACCESS    read-only
          STATUS        current
          DESCRIPTION
                  "Received broadcast frame couter."
          ::= { oemZxVdslStatEntry 13 }

   oemVdslCollisionCounters OBJECT-TYPE
          SYNTAX        INTEGER 
          MAX-ACCESS    read-only
          STATUS        current
          DESCRIPTION
                  ""
          ::= { oemZxVdslStatEntry 14 }

   oemVdslSingleCollision OBJECT-TYPE
          SYNTAX        INTEGER 
          MAX-ACCESS    read-only
          STATUS        current
          DESCRIPTION
                  ""
          ::= { oemZxVdslStatEntry 15 }

   oemVdslMultipleCollision OBJECT-TYPE
          SYNTAX        INTEGER 
          MAX-ACCESS    read-only
          STATUS        current
          DESCRIPTION
                  ""
          ::= { oemZxVdslStatEntry 16 }

   oemVdslLateCollision OBJECT-TYPE
          SYNTAX        INTEGER 
          MAX-ACCESS    read-only
          STATUS        current
          DESCRIPTION
                  ""
          ::= { oemZxVdslStatEntry 17 }

   oemVdslExcessiveCollision OBJECT-TYPE
          SYNTAX        Counter32
          MAX-ACCESS    read-only
          STATUS        current
          DESCRIPTION
                  ""
          ::= { oemZxVdslStatEntry 18 }

   oemVdslErrorCounters OBJECT-TYPE
          SYNTAX        Counter32
          MAX-ACCESS    read-only
          STATUS        current
          DESCRIPTION
                  "Error frame couter."
          ::= { oemZxVdslStatEntry 19 }

   oemVdslReceivedError OBJECT-TYPE
          SYNTAX        Counter32
          MAX-ACCESS    read-only
          STATUS        current
          DESCRIPTION
                  "Received error frame couter ."
          ::= { oemZxVdslStatEntry 20 }

   oemVdslCarrierError OBJECT-TYPE
          SYNTAX        Counter32
          MAX-ACCESS    read-only
          STATUS        current
          DESCRIPTION
                  "Error frame couter due to carrier error."
          ::= { oemZxVdslStatEntry 21 }

   oemVdslFrameTooLongError OBJECT-TYPE
          SYNTAX        Counter32
          MAX-ACCESS    read-only
          STATUS        current
          DESCRIPTION
                  "Error frame couter due to frame too long."
          ::= { oemZxVdslStatEntry 22 }

   oemVdslFrameCRCError OBJECT-TYPE
          SYNTAX        Counter32
          MAX-ACCESS    read-only
          STATUS        current
          DESCRIPTION
                  "Error frame couter due to CRC error. "
          ::= { oemZxVdslStatEntry 23 }

  oemVdslethernetTable OBJECT-TYPE
        SYNTAX  SEQUENCE OF OemVdslEthernetEntry
        MAX-ACCESS  not-accessible
        STATUS  current
        DESCRIPTION
              "A table that contains vdsl ethnet control information 
              about every port that is associated with this switch."
        ::= { oemZxBSIU  3 }
  
  oemVdslEthernetEntry OBJECT-TYPE
        SYNTAX  OemVdslEthernetEntry
        MAX-ACCESS  not-accessible
        STATUS  current
        DESCRIPTION
                "A list of ethernet control information for each port."
        INDEX  { oemVdslCfgIndex  }
        ::= { oemVdslethernetTable 1 }

   OemVdslEthernetEntry ::=
        SEQUENCE {        
            oemVdslEthTrigAutonego   INTEGER, 
            oemVdslEthad100full      INTEGER,
            oemVdslEthad100half      INTEGER,
            oemVdslEthad10full       INTEGER,
            oemVdslEthad10half       INTEGER,
            oemVdslEthTrigForce      INTEGER,
            oemVdslEthForceSpeed     INTEGER,
             oemVdslEthForceDuplex    INTEGER,
            oemVdslEthphylink        INTEGER,
            oemVdslEthphyNegoDone    INTEGER,
             oemVdslEthNtSpeed        INTEGER,
            oemVdslEthNtDuplex       INTEGER,
            oemVdslEthLtSpeed        INTEGER,
            oemVdslEthLtDuplex       INTEGER    
        }

  oemVdslEthTrigAutonego OBJECT-TYPE
          SYNTAX  INTEGER {
                          trigautonego(1)
                  }
          MAX-ACCESS  read-write
          STATUS  current
          DESCRIPTION
                 "trig autonego process of remote modem of the port."
          ::= { oemVdslEthernetEntry 3 }

  oemVdslEthad100full OBJECT-TYPE
          SYNTAX  INTEGER {
                    adenable(1),
                    addisable(2)
                  }
          MAX-ACCESS  read-write
          STATUS  current
          DESCRIPTION
                 "advertise ability of nt mac of the port."
          ::= { oemVdslEthernetEntry 4 }
  
  oemVdslEthad100half OBJECT-TYPE
          SYNTAX  INTEGER {
                    adenable(1),
                    addisable(2)
                  }
          MAX-ACCESS  read-write
          STATUS  current
          DESCRIPTION
                 "advertise ability of nt mac of the port."
          ::= { oemVdslEthernetEntry 5 }
  
  oemVdslEthad10full OBJECT-TYPE
          SYNTAX  INTEGER {
                    adenable(1),
                    addisable(2)
                  }
          MAX-ACCESS  read-write
          STATUS  current
          DESCRIPTION
                 "advertise ability of nt mac of the port."
          ::= { oemVdslEthernetEntry 6 }
  
  oemVdslEthad10half OBJECT-TYPE
          SYNTAX  INTEGER {
                    adenable(1),
                    addisable(2)
                  }
          MAX-ACCESS  read-write
          STATUS  current
          DESCRIPTION
                 "advertise ability of nt mac of the port."
          ::= { oemVdslEthernetEntry 7 }
  
  oemVdslEthTrigForce OBJECT-TYPE
          SYNTAX  INTEGER {
                          trigforce(1)                    
                  }
          MAX-ACCESS  read-write
          STATUS  current
          DESCRIPTION
                 "trig force process of remote modem of the port."
          ::= { oemVdslEthernetEntry 8 }

  oemVdslEthForceSpeed OBJECT-TYPE
          SYNTAX  INTEGER {
                          vforce10M(1),
                          vforce100M(2)
                  }
          MAX-ACCESS  read-write
          STATUS  current
          DESCRIPTION
                 "speed used with force process of remote modem of the port."
          ::= { oemVdslEthernetEntry 9 }

  oemVdslEthForceDuplex OBJECT-TYPE
          SYNTAX  INTEGER {
                          vforcehalf(1),
                          vforcefull(2)
                  }
          MAX-ACCESS  read-write
          STATUS  current
          DESCRIPTION
                 "duplex mode used with force process of NT of the port."
          ::= { oemVdslEthernetEntry 10 }

 oemVdslEthphylink OBJECT-TYPE
          SYNTAX  INTEGER {
                          ethlinking(1),
                          ethbroken(2) 
                  }
          MAX-ACCESS  read-only
          STATUS  current
          DESCRIPTION
                 "ether link state of NT of the port."
          ::= { oemVdslEthernetEntry 11 }

 oemVdslEthphyNegoDone OBJECT-TYPE
          SYNTAX  INTEGER {
                          negodone(1),
                          negonotdone(2)
                  }
          MAX-ACCESS  read-only
          STATUS  current
          DESCRIPTION
                 "autonego complete state of NT of the port."
          ::= { oemVdslEthernetEntry 12 }

oemVdslEthNtSpeed OBJECT-TYPE
          SYNTAX  INTEGER {
                          v10M(1),
                          v100M(2)
                  }
          MAX-ACCESS  read-only
          STATUS  current
          DESCRIPTION
                 "speed of nt phy of the port."
          ::= { oemVdslEthernetEntry 13 }

  oemVdslEthNtDuplex OBJECT-TYPE
          SYNTAX  INTEGER {
                          vhalf(1),
                          vfull(2)
                  }
          MAX-ACCESS  read-only
          STATUS  current
          DESCRIPTION
                 "duplex mode of nt phy of the port."
          ::= { oemVdslEthernetEntry 14 }

oemVdslEthLtSpeed OBJECT-TYPE
          SYNTAX  INTEGER {
                          v10M(1),
                          v100M(2)
                  }
          MAX-ACCESS  read-only
          STATUS  current
          DESCRIPTION
                 "speed of lt smi reg of the port."
          ::= { oemVdslEthernetEntry 15 }

  oemVdslEthLtDuplex OBJECT-TYPE
          SYNTAX  INTEGER {
                          vhalf(1),
                          vfull(2)
                  }
          MAX-ACCESS  read-only
          STATUS  current
          DESCRIPTION
                 "duplex mode of lt smi reg of the port."
          ::= { oemVdslEthernetEntry 16 }

-- ----------------------------------------------------------------------------------
  oemZxEdslQosGlobalTable OBJECT-TYPE
        SYNTAX  SEQUENCE OF OemZxEdslQosGlobalEntry
        MAX-ACCESS  not-accessible
        STATUS  current
        DESCRIPTION
              "A table that contains Qos config parameter on 
              every port that is associated with this switch."
          ::= { oemZxEdslQos 1 }

   oemZxEdslQosGlobalEntry  OBJECT-TYPE
        SYNTAX   OemZxEdslQosGlobalEntry
        MAX-ACCESS  not-accessible
        STATUS  current
        DESCRIPTION
                "A list of Qos config parameter for each port."
        INDEX  { oemZxEdslQosPortIndex  }
        ::= { oemZxEdslQosGlobalTable 1 }

   OemZxEdslQosGlobalEntry ::=
        SEQUENCE {
        oemZxEdslQosCPUPriorityWeight           INTEGER,                
        oemZxEdslQosPortPriorityWeight          INTEGER,                
        oemZxEdslQosDMALowEnable                        INTEGER,                
        oemZxEdslQosDMAHighEnable               INTEGER,                
        oemZxEdslQosRecEnable                           INTEGER,                
        oemZxEdslQosForwNewAdd2CPU              INTEGER,                
        oemZxEdslQosFwdUnkwn2CPU                        INTEGER,                
        oemZxEdslQosFwdMulti2CPU                        INTEGER,                
        oemZxEdslQosMaskMulticastCPU            INTEGER,                
        oemZxEdslQosPortGLinkFCEnable           INTEGER,                
        oemZxEdslQosRxBufThrd                   INTEGER,                
        oemZxEdslQosPortTxQueThrd                       INTEGER,                
        oemZxEdslQosBufReqQueThrdEnable INTEGER,                
        oemZxEdslQosBufReqQueThrd                       INTEGER,                
        oemZxEdslQosPortGlinkGlobalBufThrd      INTEGER,
        oemZxEdslQosPortGlinkUCBufThrd          INTEGER,
        oemZxEdslQosPortGlinkMCBufThrd          INTEGER,
        oemZxEdslQosMaskGlinkBufThrd            INTEGER,
        oemZxEdslQosLimit16Data                 INTEGER,
        oemZxEdslQosPortGlobalLimit                     INTEGER,
        oemZxEdslQosXOffLimit                           INTEGER,
        oemZxEdslQosXOnLimit                            INTEGER,
        oemZxEdslQosHOLlowPrio                  INTEGER,
        oemZxEdslQosPacketRejectQueueEnable     INTEGER,
        oemZxEdslQosFlushCPUQueue                       INTEGER,
        oemZxEdslQosIPGCPU                              INTEGER,
        oemZxEdslQosHolLimitCPU                 INTEGER,
        oemZxEdslQosHolEnableCPULow             INTEGER,
        oemZxEdslQosHolEnableCPUHigh            INTEGER,
        oemZxEdslQosAgingMode                   INTEGER,
        oemZxEdslQosAgingScrubTimer             INTEGER,
        oemZxEdslQosAgingFastAging                      INTEGER,
        oemZxEdslQosAgingBufferAging            INTEGER
        }


  oemZxEdslQosCPUPriorityWeight OBJECT-TYPE
          SYNTAX                INTEGER(0..7)
          MAX-ACCESS    read-write
          STATUS        current
          DESCRIPTION
                "The Priority Weight in the round-robin between high
                and low priority tx-DMAs to the CPU:
                000 - 1 pkt transmitted from HIGH, 1 pkt from LOW
                001 - 2 pkt transmitted from HIGH, 1 pkt from LOW
                010 - 4 pkt transmitted from HIGH, 1 pkt from LOW
                011 - 6 pkt transmitted from HIGH, 1 pkt from LOW
                100 - 8 pkt transmitted from HIGH, 1 pkt from LOW
                101 - 10 pkt transmitted from HIGH, 1 pkt from  LOW
                110 - 12 pkt transmitted from HIGH, 1 pkt from  LOW
                111 - all pkt transmitted from HIGH, 0 pkt from LOW.
                LOW will be served only if HIGH is empty.
                If HIGH queue is emptied before finishing the
                count, the count will be reset until next HIGH
                comes in.
                defalut:0x0   Global_Control<CPU_Priority_Weight>"
          ::= { oemZxEdslQosGlobalEntry 1 }

  oemZxEdslQosPortPriorityWeight OBJECT-TYPE
          SYNTAX                INTEGER(0..7)
          MAX-ACCESS    read-write
          STATUS                current
          DESCRIPTION
                "The Priority Weight in the round-robin between high
                and low priority tx queues on the 10/100 Mbps   ports:
                000 - 1 pkt transmitted from HIGH, 1 pkt from LOW
                001 - 2 pkt transmitted from HIGH, 1 pkt from LOW
                010 - 4 pkt transmitted from HIGH, 1 pkt from LOW
                011 - 6 pkt transmitted from HIGH, 1 pkt from LOW
                100 - 8 pkt transmitted from HIGH, 1 pkt from LOW
                101 - 10 pkt transmitted from HIGH, 1 pkt from  LOW
                110 - 12 pkt transmitted from HIGH, 1 pkt from  LOW
                111 - all pkt transmitted from HIGH, 0 pkt from LOW.
                LOW will be served only if HIGH is empty.
                If HIGH queue is emptied before finishing the
                count, the count will be reset until next HIGH
                comes in.
                default: 0x0  Global_Control<Ports_Priority_Weight>"
          ::= { oemZxEdslQosGlobalEntry 2 }

  oemZxEdslQosDMALowEnable OBJECT-TYPE
          SYNTAX                INTEGER{
                                        enable(1),
                                        disable(2)
                                        }
          MAX-ACCESS    read-write
          STATUS        current
          DESCRIPTION
                "Enable LOW priority DMA channel (when set to '1'),
                or Request stopping LOW priority DMA channel,
                after current packet transfer.
                2 - Stop Request pending
                1 - Enable channel
                default: 0x2  Global_Control<DMA_LOW_En>(0,1)"
          ::= { oemZxEdslQosGlobalEntry 3 }

  oemZxEdslQosDMAHighEnable OBJECT-TYPE
          SYNTAX                INTEGER{
                                        enable(1),
                                        disable(2)
                                        }
          MAX-ACCESS    read-write
          STATUS        current
          DESCRIPTION
                "Enable HIGH priority DMA channel (when set to
                '1'), or Request stopping HIGH priority DMA chan-nel,
                after current packet transfer.
                2 - Stop Request pending
                1 - Enable channel
                default: 0x2  Global_Control<DMA_HIGH_En>(0,1)"
          ::= { oemZxEdslQosGlobalEntry 4 }

  oemZxEdslQosRecEnable OBJECT-TYPE
          SYNTAX                INTEGER{
                                        enable(1),
                                        disable(2)
                                        }
          MAX-ACCESS    read-write
          STATUS        current
          DESCRIPTION
                "It defines whether initiating sending of
                New_Address message with Recovery question is
                enabled or not (answering a recovery question is
                always enabled).
                2 - Disabled
                1 - Enabled
                default: 0x1  Global_Control<RecEn>(0,1)"
          ::= { oemZxEdslQosGlobalEntry 5 }
                
  oemZxEdslQosForwNewAdd2CPU OBJECT-TYPE
          SYNTAX                INTEGER{
                                        enable(1),
                                        disable(2)
                                        }
          MAX-ACCESS    read-write
          STATUS        current
          DESCRIPTION
                "It defines whether the GT-48350 will forward new
                address messages to the CPU or not.
                2 -Donotforward NA to CPU.
                1 -Forward NA to CPU.
                default: 0x2  Global_Control<ForwNewAdd>(0,1)"
          ::= { oemZxEdslQosGlobalEntry 6 }
                
 oemZxEdslQosFwdUnkwn2CPU OBJECT-TYPE
          SYNTAX                INTEGER{
                                        enable(1),
                                        disable(2)
                                        }
          MAX-ACCESS    read-write
          STATUS        current
          DESCRIPTION
                "Enables forwarding Unknown destination Packets to CPU 
                2 - Disables forwarding unknown destination pack-ets    to CPU.
                1 - Enables forwarding unknown destination pack-ets
                to CPU (in addition to other devices/ports).
                default: 0x2  Global_Control<ForwUnk>(0,1)"
          ::= { oemZxEdslQosGlobalEntry 7 }
                
  oemZxEdslQosFwdMulti2CPU OBJECT-TYPE
          SYNTAX                INTEGER{
                                        onlytoCPU(1),
                                        normal(2)
                                        }
          MAX-ACCESS    read-write
          STATUS        current
          DESCRIPTION
                "Enables forwarding of Multicast packets to CPU.
                2 - Multicast destination packets are forwarded as usual.
                1 - Multicast packets are forwarded ONLY to CPU.
                default: 0x2  Global_Control<ForwMulti>(0,1)"           
          ::= { oemZxEdslQosGlobalEntry 8 }

  oemZxEdslQosMaskMulticastCPU  OBJECT-TYPE
          SYNTAX                INTEGER{
                                        enable(1),
                                        disable(2)
                                        }
          MAX-ACCESS    read-write
          STATUS        current
          DESCRIPTION
                "Mask Multicast from forwarding to CPU.
                2 - Enable forwarding also to CPU.
                1 -Donotforward toCPU.
                default: 0   CPU_and_Sniffer<MaskMultiCPU>(0,1)"
          ::= { oemZxEdslQosGlobalEntry 9 }
         
  oemZxEdslQosPortGLinkFCEnable   OBJECT-TYPE
          SYNTAX                INTEGER{
                                        enable(1),
                                        disable(2)
                                        }
          MAX-ACCESS    read-write
          STATUS        current
          DESCRIPTION
                "Flow_Control enable/disable threshold level in G.Link input
                FIFO in the Rx-port.
                counts in 8 words multiple (for 256 words FIFOs).
                Default disbale value is when 136 words are free.
                fault enable value is 160 when words are free.
                0x11<GLink_FC_Disable>  0x14<GLink_FC_Enable> "
          ::= { oemZxEdslQosGlobalEntry 10 }
                
  oemZxEdslQosRxBufThrd  OBJECT-TYPE
          SYNTAX                INTEGER(0..127)
          MAX-ACCESS    read-write
          STATUS        current
          DESCRIPTION
                " Receive Buffer for the 100 Mbps ports. The thresh-old
                is: Rx_buf_threshold
                0x1C  <Rx_buf_threshold>"
          ::= { oemZxEdslQosGlobalEntry 11 }

  oemZxEdslQosPortTxQueThrd  OBJECT-TYPE
          SYNTAX                INTEGER(0..127)
          MAX-ACCESS    read-write
          STATUS        current
          DESCRIPTION
                "Transmit Queue Threshold, for Head Of Line Block-ing
                prevention. 0x5 (12 packets) 
                <TxQueThr>"
          ::= { oemZxEdslQosGlobalEntry 12 }
                
  oemZxEdslQosBufReqQueThrdEnable  OBJECT-TYPE
          SYNTAX                INTEGER{
                                        enable(1),
                                        disable(2)
                                        }
          MAX-ACCESS    read-write
          STATUS        current
          DESCRIPTION
                "Enables the buffer request queue threshold:
                2 = Disable
                1 = Enable
                0x2 <BufReqQueThrEn>"
          ::= { oemZxEdslQosGlobalEntry 13 }
        
  oemZxEdslQosBufReqQueThrd  OBJECT-TYPE
          SYNTAX                INTEGER(1..4095)
          MAX-ACCESS    read-write
          STATUS        current
          DESCRIPTION
                "Buffer request queue threshold
                0x26A  <BufReqQueThr>"
          ::= { oemZxEdslQosGlobalEntry 14 }
        
  oemZxEdslQosPortGlinkGlobalBufThrd  OBJECT-TYPE
          SYNTAX                INTEGER(0..255)
          MAX-ACCESS    read-write
          STATUS        current
          DESCRIPTION
                " Total number of buffers allocated to G.Link port.
                  0x1F <G_GlobalBufThr>"
          ::= { oemZxEdslQosGlobalEntry 15 }
                  
  oemZxEdslQosPortGlinkUCBufThrd   OBJECT-TYPE
          SYNTAX                INTEGER(0..127)
          MAX-ACCESS    read-write
          STATUS        current
          DESCRIPTION
                "Buffer Threshold for Unicast Rx packets on the
                G.Link per destination port.
                0x04      <G_UCBufThr>"
          ::= { oemZxEdslQosGlobalEntry 16 }

  oemZxEdslQosPortGlinkMCBufThrd   OBJECT-TYPE
          SYNTAX                INTEGER(0..127)
          MAX-ACCESS    read-write
          STATUS        current
          DESCRIPTION
                "Buffer Threshold for Multicast/Unknown packets on
                the G.Link.
                0x1F <G_MCBufThr>"      
          ::= { oemZxEdslQosGlobalEntry 17 }

                
  oemZxEdslQosMaskGlinkBufThrd  OBJECT-TYPE
          SYNTAX                INTEGER{
                                        enable(1),
                                        disable(2)
                                        }
          MAX-ACCESS    read-write
          STATUS        current
          DESCRIPTION
                "Ignore the per-queue G.Link buffer threshold:
                1 = Enable (Donot ignore G_UCBufThr,
                G_MCBufThr)
                2 =Disable
                0x1 <maskGlinkBufThr>(0,1)"
          ::= { oemZxEdslQosGlobalEntry 18 }

  oemZxEdslQosLimit16Data  OBJECT-TYPE
          SYNTAX                INTEGER{
                                        all(1),
                                        some(2)
                                        }
          MAX-ACCESS    read-write
          STATUS        current
          DESCRIPTION
                "Limit Packet_Transfer message length on G_Link
                Tx port:
                2 - Limit number of data words to 16 for: CPU and
                all devices on Target_DevicePortPCI. Limit to 32 for
                all devices on Target_Device_Port0/1/2/3/4/5/6/7.
                1 - Limit number of data words to 16 for all Target
                0x2  CPU_and_Sniffer<Limit_16_Data>(0,1)"
          ::= { oemZxEdslQosGlobalEntry 19 }
        
  oemZxEdslQosPortGlobalLimit  OBJECT-TYPE
          SYNTAX                INTEGER(0..127)
          MAX-ACCESS    read-write
          STATUS        current
          DESCRIPTION
                "Port Global Limit 0x40 (128 Limit)     
                <PortGlobalLimit>"
          ::= { oemZxEdslQosGlobalEntry 20 }

  oemZxEdslQosXOffLimit  OBJECT-TYPE
          SYNTAX                INTEGER(0..127)
          MAX-ACCESS    read-write
          STATUS        current
          DESCRIPTION
                "X-OFF Limit - When Flow control is enabled, GT-48350
                will send X-OFF packet when the number of
                buffers for this port is> (XOffLimit) value
                0x06    <XOffLimit >"
          ::= { oemZxEdslQosGlobalEntry 21 }

  oemZxEdslQosXOnLimit  OBJECT-TYPE
          SYNTAX                INTEGER(0..127)
          MAX-ACCESS    read-write
          STATUS        current
          DESCRIPTION
                "X-ON Limit - When Flow control is enabled, GT-48350
                will send X-ON packet when the number of
                buffers for this port is< (XOnLimit) value
                0x04 <XOnLimit>"
          ::= { oemZxEdslQosGlobalEntry 22 }

oemZxEdslQosHOLlowPrio  OBJECT-TYPE
          SYNTAX                INTEGER{
                                enable(1),
                                disable(2)
                                }               
          MAX-ACCESS    read-write
          STATUS        current
          DESCRIPTION
                "Head-Of-Line blocking on Low priority packets only.
                2 =Normal
                1 = When HOL Low is enabled, leave as low-prior-ity
                packet.
                0x2 <HOLlowPrio>"
          ::= { oemZxEdslQosGlobalEntry 23 }

oemZxEdslQosPacketRejectQueueEnable  OBJECT-TYPE
          SYNTAX                INTEGER{
                                enable(1),
                                disable(2)
                                }               
          MAX-ACCESS    read-write
          STATUS        current
          DESCRIPTION
                "This field reserves the fourth Start Of Packet queue
                for Packet Reject messages (see Section 19.1 on
                page 67.
                2 - Disable
                1 - Enable
                0x2 <Packet_Reject_Queue_En>"
          ::= { oemZxEdslQosGlobalEntry 24 }
                                
oemZxEdslQosFlushCPUQueue   OBJECT-TYPE
          SYNTAX                INTEGER{
                                        no(0),
                                        flush(1)
                                        }
          MAX-ACCESS    read-write
          STATUS        current
          DESCRIPTION
                "Flush the cpu queue.
                0 - Do not flush cpu queue.
                1- Flush CPU queue.
                When flush_cpu_queue is enabled, the GT-48350
                will flush the high/low queue according to
                DMA_LOW_EN,DMA_HIGH_EN in the Global
                Control register (bits 29,30), by freeing all the buff-ers
                and empty the CPU queue.
                0x0 <flush_cpu_queue >" 
          ::= { oemZxEdslQosGlobalEntry 25 }
                
oemZxEdslQosIPGCPU   OBJECT-TYPE
          SYNTAX                INTEGER(0..65535)
          MAX-ACCESS    read-write
          STATUS        current
          DESCRIPTION
                "IPG_CPU counter and Enable: Forces a delay from
                the last End_of_packet message to the CPU until
                the first packet_transfer message to the CPU. In
                multiples of 16 clock cycles.
                Valid values are 0 (no delay between packets to
                CPU), through 0xFFFE (1,048,544 Clk cycles).
                0xFFFF - has same effect as 0.
                0xFFFF <IPG_CPU>"
          ::= { oemZxEdslQosGlobalEntry 26 }
        
oemZxEdslQosHolLimitCPU   OBJECT-TYPE
          SYNTAX                INTEGER(0..127)
          MAX-ACCESS    read-write
          STATUS        current
          DESCRIPTION
                "Transmit Queue Threshold, for Head Of Line
                Blocking prevention to the CPU. 0x6 <hol_limit_cpu>"
          ::= { oemZxEdslQosGlobalEntry 27 }

oemZxEdslQosHolEnableCPULow   OBJECT-TYPE
          SYNTAX                INTEGER{
                                enable(1),
                                disable(2)
                                }               
          MAX-ACCESS    read-write
          STATUS        current
          DESCRIPTION
                "Enable CPU HOL blocking prevention for low
                priority packets:
                2 = Disable
                1 =Enable
                0x2 <hol_enable_cpu_low>"
          ::= { oemZxEdslQosGlobalEntry 28 }
        
oemZxEdslQosHolEnableCPUHigh   OBJECT-TYPE
          SYNTAX                INTEGER{
                                enable(1),
                                disable(2)
                                }               
          MAX-ACCESS    read-write
          STATUS        current
          DESCRIPTION
                "Enable CPU HOL blocking prevention for high
                priority packets:
                2 = Disable
                1 =Enable
                0x2 <hol_enable_cpu_high>"
          ::= { oemZxEdslQosGlobalEntry 29 }

oemZxEdslQosAgingMode   OBJECT-TYPE
          SYNTAX                INTEGER{
                                noAging(0),
                                autoAging(1),
                                triggerAging(2)
                                }               
          MAX-ACCESS    read-write
          STATUS        current
          DESCRIPTION
                "Aging Mode:
                0 - No Aging support
                1 - Automatic aging
                2 - Aging via trigger
                3 -Reserved
                0x1 <AgingMode>"
          ::= { oemZxEdslQosGlobalEntry 30 }


oemZxEdslQosAgingScrubTimer   OBJECT-TYPE
          SYNTAX                INTEGER(0..3)
          MAX-ACCESS    read-write
          STATUS        current
          DESCRIPTION
                " Time window for checking old buffers in any single
                group of 32 buffers, before moving to the next
                group of 32 buffers:
                00 - 1 second (Total 5 seconds for all buffers in
                embedded memory).
                01 - 2 second (Total 10 seconds for all buffers in
                embedded memory).
                10 - 3 second (Total 15 seconds for all buffers in
                embedded memory).
                11 - 4 second (Total 20 seconds for all buffers in
                embedded memory).
                0x0 <Scrub_timer>"
          ::= { oemZxEdslQosGlobalEntry 31 }


oemZxEdslQosAgingFastAging   OBJECT-TYPE
          SYNTAX                INTEGER{
                                fast(1),
                                normal(2)
                                }               
          MAX-ACCESS    read-write
          STATUS        current
          DESCRIPTION
                "Fast aging enable
                2=Normal Aging mode (as described in <Aging-Timer>)
                1=Fast aging mode
                0x2 <Fast Aging >(0,1)"
          ::= { oemZxEdslQosGlobalEntry 32 }

oemZxEdslQosAgingBufferAging   OBJECT-TYPE
          SYNTAX                INTEGER{
                                enable(1),
                                disable(2)
                                }               
          MAX-ACCESS    read-write
          STATUS                current
          DESCRIPTION
                "Buffer Aging Enable
                2 - Disable
                1 - Enable
                0x2<BufferAging>"
          ::= { oemZxEdslQosGlobalEntry 33 }
                

  oemZxEdslQosPortTable OBJECT-TYPE
        SYNTAX  SEQUENCE OF OemZxEdslQosPortEntry
        MAX-ACCESS  not-accessible
        STATUS  current
        DESCRIPTION
              "A table that contains Qos config parameter on 
              every port that is associated with this switch."
          ::= { oemZxEdslQos 2 }

   oemZxEdslQosPortEntry  OBJECT-TYPE
        SYNTAX   OemZxEdslQosPortEntry
        MAX-ACCESS  not-accessible
        STATUS  current
        DESCRIPTION
                "A list of Qos config parameter for each port."
        INDEX  { oemZxEdslQosPortIndex  }
        ::= { oemZxEdslQosPortTable 1 }

   OemZxEdslQosPortEntry ::=
        SEQUENCE {
        oemZxEdslQosPortIndex                           INTEGER,                
        oemZxEdslQosPortPriorityOverride                INTEGER,                
        oemZxEdslQosPortPriorityDefault         INTEGER,                
        oemZxEdslQosPortVPT2PrioLow             INTEGER,                
        oemZxEdslQosPortVPT2PrioHigh            INTEGER,                
        oemZxEdslQosPortVPT2priority            INTEGER,                
        oemZxEdslQosPortTos2PrioEnable          INTEGER,                
        oemZxEdslQosPortTos2Prio                        OCTET STRING,           

        oemZxEdslQosPortFlowControl                     INTEGER,                
        oemZxEdslQosPortAutonegFlowControlEnable        INTEGER,                
        oemZxEdslQosPortBackpressureEnable      INTEGER,                
        oemZxEdslQosPortHOLEnable                       INTEGER,                
        oemZxEdslQosPortFilterBroadcast         INTEGER,                
        oemZxEdslQosPortForwUnknown             INTEGER,                
        oemZxEdslQosPortDropOnLockedEnable      INTEGER
        }

        oemZxEdslQosPortIndex   OBJECT-TYPE
          SYNTAX                INTEGER(1..248)
          MAX-ACCESS    not-accessible
          STATUS                current
          DESCRIPTION
                "index for the table"
          ::= { oemZxEdslQosPortEntry 1 }

        oemZxEdslQosPortPriorityOverride        OBJECT-TYPE
          SYNTAX        INTEGER{
                                enable(1),
                                disable(2)
                                }                               
          MAX-ACCESS    read-write
          STATUS        current
          DESCRIPTION
                "Override priority for packets received on this port.
                2-Donotoverride
                1 - Override with <Default_Priority> field.     
                default 2 .Port_Control<Priority_Override> (0,1)"
          ::= { oemZxEdslQosPortEntry 2 }
                
        oemZxEdslQosPortPriorityDefault         OBJECT-TYPE
          SYNTAX        INTEGER{
                                high(1),
                                low(2)
                                }
          MAX-ACCESS    read-write
          STATUS        current
          DESCRIPTION
                "Default priority for packets received on this port.
                2- Low priority
                1 -HighPriority
                default 2       Port_Control<Default_Priority>(0,1)"
          ::= { oemZxEdslQosPortEntry 3 }

        oemZxEdslQosPortVPT2PrioLow     OBJECT-TYPE
          SYNTAX        INTEGER(0..7)
          MAX-ACCESS    read-write
          STATUS        current
          DESCRIPTION
                "The 802.1p user priority assigned to untagged
                received packets to be transmitted as tagged from
                the priority queue 0.
                0x0   Port Control Extend<VPT_prio0>"
          ::= { oemZxEdslQosPortEntry 4 }
                
        oemZxEdslQosPortVPT2PrioHigh    OBJECT-TYPE
          SYNTAX        INTEGER(0..7)
          MAX-ACCESS    read-write
          STATUS        current
          DESCRIPTION
                "The 802.1p user priority assigned to untagged
                received packets to be transmitted as tagged from
                the priority queue 1.
                0x7  Port Control Extend<VPT_prio1>"
          ::= { oemZxEdslQosPortEntry 5 }

oemZxEdslQosPortVPT2priority    OBJECT-TYPE
          SYNTAX        INTEGER(0..255)
          MAX-ACCESS    read-write
          STATUS        current
          DESCRIPTION
                "The priority assigned to packets with 802.1q tag.
                every bit is indicate a priority of 802.1q tag , if it's
                1 , the 802.1q tag assign to high receive queue; other-
                wise the 802.1q tag assign to low  queue.
                0xF0  Port Control Extend<VPT2prio>"
          ::= { oemZxEdslQosPortEntry 6 }
                
        oemZxEdslQosPortTos2PrioEnable  OBJECT-TYPE
          SYNTAX        INTEGER{
                                enable(1),
                                disable(2)
                                }
          MAX-ACCESS    read-write
          STATUS        current
          DESCRIPTION
                " Enable Type of Service,
                0X2  Port_Control_Extend<En_tos2_prio>"
          ::= { oemZxEdslQosPortEntry 7 }
                
        oemZxEdslQosPortTos2Prio        OBJECT-TYPE
          SYNTAX                OCTET STRING (SIZE (8))
          MAX-ACCESS    read-write
          STATUS        current
          DESCRIPTION
                " This value is make up with  tos2prio0 and  tos2prio1.
                Each bit in tos2prio0 [31:0] and tos2prio0 [31:0] 
                corresponds to one
                value of the 6-bit DSCP field (6 most significant bits
                of the IPv4 TOS byte). The priority of the DSCP
                field is defined as follows:
                0 - Low priority
                1 - High priority
                0x0 TOS <tos2prio0><tos2prio0>"
          ::= { oemZxEdslQosPortEntry 8 }

        oemZxEdslQosPortFlowControl     OBJECT-TYPE
          SYNTAX        INTEGER{
                                enable(1),
                                disable(2)
                                }
          MAX-ACCESS    read-write
          STATUS        current
          DESCRIPTION
                "Enables IEEE 802.3x Flow_Control (in Full-Duplex).
                2 - Not enable Flow_Control
                 1 - Enable Flow_Control.
                default:2   Port_Control<Flow_Control>(0,1)"
          ::= { oemZxEdslQosPortEntry 9}

        oemZxEdslQosPortBackpressureEnable      OBJECT-TYPE
          SYNTAX        INTEGER{
                                enable(1),
                                disable(2)
                                }
          MAX-ACCESS    read-write
          STATUS        current
          DESCRIPTION
                "Enables backpressure (in Half-Duplex):
                2 - Do not backpressure
                1 - Enable backpressure
                default 2  Port_Control<En_Backpressure>(0,1)"
          ::= { oemZxEdslQosPortEntry 10 }
                
        oemZxEdslQosPortAutonegFlowControlEnable        OBJECT-TYPE
          SYNTAX        INTEGER{
                                enable(1),
                                disable(2)
                                }
          MAX-ACCESS    read-write
          STATUS        current
          DESCRIPTION
                "Enable Auto-Negotiation for flow control:
                1 - enable
                2 - disable
                0x2  Port_Control<Enable_Autoneg_FlowControl>(0,1)"
          ::= { oemZxEdslQosPortEntry 11 }
                
        oemZxEdslQosPortHOLEnable       OBJECT-TYPE
          SYNTAX        INTEGER{
                                enable(1),
                                disable(2)
                                }
          MAX-ACCESS    read-write
          STATUS        current
          DESCRIPTION
                "Enable HOL blocking protection for destination port
                2 = Disables (Not checking TxQueThr on port 0 as
                destination).
                1 = Enable discard based on TxQueThr
                0x2  HOL_Blocking<HOL_Portn_En>(0,1)"
          ::= { oemZxEdslQosPortEntry 12 }

        oemZxEdslQosPortFilterBroadcast OBJECT-TYPE
          SYNTAX        INTEGER{
                                enable(1),
                                disable(2)
                                }
          MAX-ACCESS    read-write
          STATUS        current
          DESCRIPTION
                "Filter Broadcast.
                2 - Broadcast packets received on this port are forwarded
                normally (according to Basic/Tag mode)
                1 - Discards Broadcast packets.
                default 0x2  Port_Control<FilBroad>(0,1)"
          ::= { oemZxEdslQosPortEntry 13 }
                
        oemZxEdslQosPortForwUnknown     OBJECT-TYPE
          SYNTAX        INTEGER{
                                enable(1),
                                disable(2)
                                }
          MAX-ACCESS    read-write
          STATUS        current
          DESCRIPTION
                "Enable Forwarding packets with Unknown destination.
                1 - Unknown packets can be transmitted by GT-
                48350 on this port.
                2 - GT-48350 will not forward Unknown packets to
                this port.
                0x1  Port_Control<ForwUnk>(0,1)"
          ::= { oemZxEdslQosPortEntry 14 }
                
        oemZxEdslQosPortDropOnLockedEnable      OBJECT-TYPE
          SYNTAX        INTEGER{
                                enable(1),
                                disable(2)
                                }
          MAX-ACCESS    read-write
          STATUS                current
          DESCRIPTION
                "Enables dropping unknown/changed SA packets
                received on locked port. Has effect only if     <locked>=1. 
                2 - Do not drop (forward as usual)
                1 - Drop unknown packets.
                 0x2  Port_Control<En_Drop_On_Locked>(0,1)"
          ::= { oemZxEdslQosPortEntry 15 }
                

  oemZxEdslQosPortMacLockTable OBJECT-TYPE
        SYNTAX  SEQUENCE OF OemZxEdslQosPortMacLockEntry
        MAX-ACCESS  not-accessible
        STATUS  current
        DESCRIPTION
              "A table that contains binding Macaddress and port 
               config parameter on  every port that is associated with
                this switch."
          ::= { oemZxEdslQos 3 }

   oemZxEdslQosPortMacLockEntry  OBJECT-TYPE
        SYNTAX   OemZxEdslQosPortMacLockEntry
        MAX-ACCESS  not-accessible
        STATUS  current
        DESCRIPTION
                "A list of Qos config parameter for each port."
        INDEX  { oemZxEdslQosPortIndex  }
        ::= { oemZxEdslQosPortMacLockTable 1 }

   OemZxEdslQosPortMacLockEntry ::=
        SEQUENCE {
--      oemZxEdslQosPortVlan                            INTEGER,                
        oemZxEdslQosPortMacLock                 MacAddress
        }

--      oemZxEdslQosPortVlan    OBJECT-TYPE
--          SYNTAX              INTEGER(1..4095)
--          MAX-ACCESS          read-write
--          STATUS              current
--          DESCRIPTION
--              "Assign Vlan Id to the macaddress-binding port. must
--              be set before macaddress."
--          ::= { oemZxEdslQosPortMacLockEntry 1 }

        oemZxEdslQosPortMacLock OBJECT-TYPE
          SYNTAX                MacAddress
          MAX-ACCESS    read-write
          STATUS                current
          DESCRIPTION
                "Assign a Macaddress to the port, and this port will not
                learn new macaddress. if Macaddress is 00:00:00:00:00:00,
                it mean to delete this macaddress from the port."
          ::= { oemZxEdslQosPortMacLockEntry 2 }



-- ----------------------------------------------------------------------------


        oemZxEdslTrunkingAgList OBJECT-TYPE
                SYNTAX  PortList
                MAX-ACCESS read-only
                STATUS current
                DESCRIPTION
                        "This item is indicate Ag portlist ."
        ::= { oemZxEdslLagTrunking 1 }
        
        oemZxEdslTrunkingTable OBJECT-TYPE
                SYNTAX SEQUENCE OF OemZxEdslTrunkingEntry
                MAX-ACCESS not-accessible
                STATUS current
                DESCRIPTION
                        "A table that contains the Trunk Group Table Entry rule
                        that defines the distribution algorithm for every Link Aggregator
                        that is associated with this System."
        ::= { oemZxEdslLagTrunking 2 }

        oemZxEdslTrunkingEntry OBJECT-TYPE
                SYNTAX OemZxEdslTrunkingEntry
                MAX-ACCESS not-accessible
                STATUS current
                DESCRIPTION
                        "A list of the rules applied to the entries of the Trunk Group 
                        Table parameters. This is indexed by the ifIndex of the 
                        Aggregator, which is also the dot3adAggIndex."
                INDEX { oemZxEdslTrunkingIndex }
        ::= { oemZxEdslTrunkingTable 1 }

        OemZxEdslTrunkingEntry ::=
                SEQUENCE {
                        oemZxEdslTrunkingIndex          INTEGER,
                        oemZxEdslTrunkingAp2Ag          INTEGER,
                                oemZxEdslTrunkingApList         PortList
                }

        oemZxEdslTrunkingIndex OBJECT-TYPE
                SYNTAX INTEGER(1..248)
                MAX-ACCESS not-accessible
                STATUS current
                DESCRIPTION
                        "The unique identifier allocated to this Aggregator by the 
                        local System. This attribute identifies an Aggregator instance 
                        among the subordinate managed objects of the containing object.
                        This value is read-only. This is the same value as the 
                        dot3adAggIndex in the dot3adAggTable."
                REFERENCE
                        "IEEE 802.3 Section 30.7.1.1.1"
        ::= { oemZxEdslTrunkingEntry 1 }

        oemZxEdslTrunkingAp2Ag  OBJECT-TYPE
                SYNTAX INTEGER 
                MAX-ACCESS read-write
                STATUS current
                DESCRIPTION
                        "This item is use to add ap port ( index ) to ag port (the value ).
                          It will delete ap from ag if this item is 0. 
                         The Rule to be applied to this Link Aggregator's Trunk Group
                        Table. The rules are based on the following selections SrcMAC (1),
                        means that the last three bits of the Source MAC Address are used to
                        index the Trunk Group to get the destination port. DestMAC (2), means
                        the last three bits of the Destination MAC Address are used to index 
                        into the Trunk Group to get the destination port. SrcXORDestMAC (3),
                        means that the last three bits of the Source MAC Address are logically
                        XORed with the last three bits of the Destination MAC Address and used
                        to index into the Trunk Group to get the destination port. SrcIP (4),
                        means the last three bits of the Source IP Address are used to index
                        into the Trunk Group to get the destination port. DestIP (5), means
                        the last three bits of the Destination IP Address are used to index
                        into the Trunk Group to get the destination port. SrcXORDestIP (6),
                        means the last three bits of the Source IP Address are logically XORed
                        with the last three bits of the Destination IP Address and used to 
                        index into the Trunk Group to get the destination port. This rule
                        defines the distribution algorithm applied to the aggregated link."
        ::= { oemZxEdslTrunkingEntry 2 }

        oemZxEdslTrunkingApList  OBJECT-TYPE
                SYNTAX  PortList
                MAX-ACCESS read-only
                STATUS  current
                DESCRIPTION
                        " This item is indicate the ap portlist included in Ag port ( index ).
                        A table that contains the Link State Table Entry
                        that defines the state of each ports link."
        ::= { oemZxEdslTrunkingEntry 3 }

-- ----------------------------------------------------------------------------

        oemZxGmrpAppTable OBJECT-TYPE
                SYNTAX SEQUENCE OF OemZxGmrpAppEntry
                MAX-ACCESS not-accessible
                STATUS current
                DESCRIPTION
                        ""
        ::= { oemZxGmrpApp 1 }

        oemZxGmrpAppEntry OBJECT-TYPE
                SYNTAX OemZxGmrpAppEntry
                MAX-ACCESS not-accessible
                STATUS current
                DESCRIPTION
                        ""
                INDEX { oemVlanIndex }
        ::= { oemZxGmrpAppTable 1 }

        OemZxGmrpAppEntry ::=
                SEQUENCE {
                        oemVlanIndex            INTEGER,
                oemZxGmrpAppPortlist    PortList
                }

        oemVlanIndex OBJECT-TYPE
                SYNTAX INTEGER(1..2047)
                MAX-ACCESS not-accessible
                STATUS current
                DESCRIPTION
                        ""
        ::= { oemZxGmrpAppEntry 1 }

        oemZxGmrpAppPortlist  OBJECT-TYPE
                SYNTAX  PortList
                MAX-ACCESS read-write
                STATUS  current
                DESCRIPTION
                        " "
        ::= { oemZxGmrpAppEntry 3 }


-- ----------------------------------------------------------------------------

    oemZxEdslEndMib OBJECT-TYPE
        SYNTAX  INTEGER
        MAX-ACCESS read-only
        STATUS current
        DESCRIPTION
            "This item is end of all mibview ."
    ::= { oemZxEndMib 1 }

------------------------------------------------------------------------------------
------------------------------------------------------------------------------------
   zxEdslMaxCfgProfileNum OBJECT-TYPE
          SYNTAX  INTEGER 
          MAX-ACCESS  read-only
          STATUS  current
          DESCRIPTION
                  "The maximum number of profiles."
          ::= { oemZxBSIU 6}

--    edsl line Config Profile Table 
--
   zxEdslLineConfProfileTable OBJECT-TYPE
        SYNTAX  SEQUENCE OF ZxEdslLineCfgProfEntry
        MAX-ACCESS  not-accessible
        STATUS  current
        DESCRIPTION
              "A table that contains general config information profiles
          about every VDSL port that is associated with this switch."
        ::= { oemZxBSIU 7 }
        
   zxEdslLineCfgProfEntry  OBJECT-TYPE
        SYNTAX  ZxEdslLineCfgProfEntry
        MAX-ACCESS  not-accessible
        STATUS  current
        DESCRIPTION
                "A list of general VDSL information profiles for each port."
        INDEX  { zxEdslCfgProfName  }
        ::= { zxEdslLineConfProfileTable 1 }

   ZxEdslLineCfgProfEntry ::=
        SEQUENCE {
            zxEdslCfgProfName       DisplayString,
            zxEdslLinkUpInterp      INTEGER,
            zxEdslLinkDownInterp      INTEGER,
            zxEdslLinkUpConste      INTEGER,
            zxEdslLinkDownConste      INTEGER,
            zxEdslLinkUpFreq          INTEGER,
            zxEdslLinkDownFreq      INTEGER,
            zxEdslLinkTrapEnable      INTEGER,
            zxEdslLinkPowerBack      INTEGER,
            zxEdslLinkLTMaxPSD      INTEGER,
            zxEdslLinkNTMaxPSD      INTEGER,
            zxEdslLinkNTMinPSD      INTEGER,
            zxEdslLinkLTTransNotch     INTEGER,
            zxEdslLinkNTTransNotch     INTEGER,
            zxEdslLinkLTInterDepth    INTEGER,
            zxEdslLinkNTInterDepth    INTEGER,

            zxEdslCfgRead              INTEGER,
            zxEdslLinkRead              INTEGER,            
            zxEdslLinkUpdate         INTEGER,
            zxEdslLinkSaveReset      INTEGER,
            zxEdslLinkAutochg        INTEGER,
            zxEdslLinkConfAuto       INTEGER,

            zxEdslLinkReserved1      INTEGER,
            zxEdslLinkReserved2      INTEGER,
            zxEdslLinkReserved3      INTEGER,
            zxEdslLinkReserved4      INTEGER,
            zxEdslLinkReserved5      INTEGER,
            zxEdslCfgProfRowStatus   RowStatus
        }

   zxEdslCfgProfName OBJECT-TYPE
      SYNTAX      DisplayString (SIZE(1..32))
      MAX-ACCESS  not-accessible
      STATUS      current
      DESCRIPTION
        "This object is the unique index associated with this profile.
         Entries in this table are referenced via the object
         zxVdslCfgProfile in zxVdslCfgEntry."
      ::= { zxEdslLineCfgProfEntry 1 }
        

   zxEdslLinkUpInterp OBJECT-TYPE
          SYNTAX  INTEGER 
          MAX-ACCESS  read-create
          STATUS  current
          DESCRIPTION
                  "Linkup interpolation of the port. the value is 
                  4,6,8,10,12,14,16,24,32,48,64."
          ::= { zxEdslLineCfgProfEntry 2 }

   zxEdslLinkDownInterp OBJECT-TYPE
          SYNTAX  INTEGER 
          MAX-ACCESS  read-create
          STATUS  current
          DESCRIPTION
                  "Linkdown interpolation of the port.The value is
                  4,6,8,10,12,14,16,24,32,48 or 64."
          ::= { zxEdslLineCfgProfEntry 3 }

   zxEdslLinkUpConste OBJECT-TYPE
          SYNTAX  INTEGER 
          MAX-ACCESS  read-create
          STATUS  current
          DESCRIPTION
                  "Linkup constellation of the port. The value is 
                  4,8,16,32,64,128 or 256 ."
          ::= { zxEdslLineCfgProfEntry 4 }

   zxEdslLinkDownConste OBJECT-TYPE
          SYNTAX  INTEGER 
          MAX-ACCESS  read-create
          STATUS  current
          DESCRIPTION
                  "Linkdown constellation of the port. The value is 
                  4,8,16,32,64,128 or 256 ."
          ::= { zxEdslLineCfgProfEntry 5 }

   zxEdslLinkUpFreq OBJECT-TYPE
          SYNTAX  INTEGER(0..800) 
          MAX-ACCESS  read-create
          STATUS  current
          DESCRIPTION
                  "Linkup frequence of the port."
          ::= { zxEdslLineCfgProfEntry 6 }

   zxEdslLinkDownFreq OBJECT-TYPE
          SYNTAX  INTEGER(0..800) 
          MAX-ACCESS  read-create
          STATUS  current
          DESCRIPTION
                  "Linkdown frequence of the port."
          ::= { zxEdslLineCfgProfEntry 7 }

   zxEdslLinkTrapEnable OBJECT-TYPE
          SYNTAX  INTEGER {
                   enable(1),
               disable(2)
                  }
          MAX-ACCESS  read-create
          STATUS  current
          DESCRIPTION
                  "Enable/disable vdsl trap ."
          ::= { zxEdslLineCfgProfEntry 8 }

   zxEdslLinkPowerBack OBJECT-TYPE
          SYNTAX  INTEGER {
                   enable(1),
               disable(2)
                  }
          MAX-ACCESS  read-create
          STATUS  current
          DESCRIPTION
                  "power back off mode enable/disable of the port."
          ::= { zxEdslLineCfgProfEntry 9 }

   zxEdslLinkLTMaxPSD OBJECT-TYPE
          SYNTAX  INTEGER(55..100) 
          MAX-ACCESS  read-create
          STATUS  current
          DESCRIPTION 
              "Max PSD of the port."
          ::= { zxEdslLineCfgProfEntry 10 }

   zxEdslLinkNTMaxPSD OBJECT-TYPE
          SYNTAX  INTEGER(55..100)
          MAX-ACCESS  read-create
          STATUS  current
          DESCRIPTION
                  "NT MAX PSD of the port."
          ::= { zxEdslLineCfgProfEntry 11 }

   zxEdslLinkNTMinPSD OBJECT-TYPE
          SYNTAX  INTEGER(55..100)
          MAX-ACCESS  read-create
          STATUS  current
          DESCRIPTION
                  "NT MIN PSD of the port."
          ::= { zxEdslLineCfgProfEntry 12 }

   zxEdslLinkLTTransNotch OBJECT-TYPE
          SYNTAX  INTEGER{
                   enable(1),
               disable(2)
                  }
          MAX-ACCESS  read-create
          STATUS  current
          DESCRIPTION
                  "LT transmit notch of the port."
          ::= { zxEdslLineCfgProfEntry 13 }

   zxEdslLinkNTTransNotch OBJECT-TYPE
          SYNTAX  INTEGER {
                   enable(1),
               disable(2)
                  }
          MAX-ACCESS  read-create
          STATUS  current
          DESCRIPTION
                  "NT transmit notch of the port."
          ::= { zxEdslLineCfgProfEntry 14 }

   zxEdslLinkLTInterDepth OBJECT-TYPE
          SYNTAX  INTEGER 
          MAX-ACCESS  read-create
          STATUS  current
          DESCRIPTION
                  "LT interleaver depth of the port. The value is
                  0,1,2,8 or 16."
          ::= { zxEdslLineCfgProfEntry 15 }

   zxEdslLinkNTInterDepth OBJECT-TYPE
          SYNTAX  INTEGER 
          MAX-ACCESS  read-create
          STATUS  current
          DESCRIPTION
                  "LT interleaver depth of the port. The value is
                  0,1,2,8 or 16."
          ::= { zxEdslLineCfgProfEntry 16 }

   zxEdslCfgRead OBJECT-TYPE
          SYNTAX  INTEGER {
                     readreg(1)
                          } 
          MAX-ACCESS  read-create
          STATUS  current
          DESCRIPTION
                  "Gen conf reg read operation."
          ::= { zxEdslLineCfgProfEntry 17 }

   zxEdslLinkRead OBJECT-TYPE
          SYNTAX  INTEGER{
                  readsetval(1),
             readcurval(2) 
                          } 
          MAX-ACCESS  read-create
          STATUS  current
          DESCRIPTION
                  "lnk conf register read operation."
          ::= { zxEdslLineCfgProfEntry 18 }

   zxEdslLinkUpdate OBJECT-TYPE
          SYNTAX  INTEGER{
                 update1s1p(1),  -- update one port of one slot
                          update1sap(2),   -- update all port of one slot
             updateas1p(3),   -- update one same port of all slot
             updateasap(4)    -- update all port of all slot
                      } 
          MAX-ACCESS  read-create
          STATUS  current
          DESCRIPTION
                  "lnk conf register update operation."
          ::= { zxEdslLineCfgProfEntry 19 }

   zxEdslLinkSaveReset OBJECT-TYPE
          SYNTAX  INTEGER{
                 savereg(1)
                      } 
          MAX-ACCESS  read-create
          STATUS  current
          DESCRIPTION
                  "lnk conf register save operation and LTNT reset."
          ::= { zxEdslLineCfgProfEntry 20 }

   zxEdslLinkAutochg OBJECT-TYPE
          SYNTAX  INTEGER{
                      enable(1),
               disable(2)
                      } 
          MAX-ACCESS  read-create
          STATUS  current
          DESCRIPTION
                  "Link speed auto change enable/disable of the port."
          ::= { zxEdslLineCfgProfEntry 21 }

    zxEdslLinkConfAuto OBJECT-TYPE
          SYNTAX  INTEGER{
                   enable(1),
               disable(2)
                  }
          MAX-ACCESS  read-create
          STATUS  current
          DESCRIPTION
                  "auto set link of all ports ."
          ::= { zxEdslLineCfgProfEntry 22 }
   
           
   zxEdslLinkReserved1 OBJECT-TYPE
          SYNTAX  INTEGER
          MAX-ACCESS  read-create
          STATUS  current
          DESCRIPTION
                  "Current  DS rate of the port."
          ::= { zxEdslLineCfgProfEntry 23 }

   zxEdslLinkReserved2 OBJECT-TYPE
          SYNTAX  INTEGER
          MAX-ACCESS  read-create
          STATUS  current
          DESCRIPTION
                  "Reserved."
          ::= { zxEdslLineCfgProfEntry 24 }

   zxEdslLinkReserved3 OBJECT-TYPE
          SYNTAX  INTEGER
          MAX-ACCESS  read-create
          STATUS  current
          DESCRIPTION
                  "Reserved."
          ::= { zxEdslLineCfgProfEntry 25 }
          
   zxEdslLinkReserved4 OBJECT-TYPE
          SYNTAX  INTEGER
          MAX-ACCESS  read-create
          STATUS  current
          DESCRIPTION
                  "Reserved."
          ::= { zxEdslLineCfgProfEntry 26 }

   zxEdslLinkReserved5 OBJECT-TYPE
          SYNTAX  INTEGER
          MAX-ACCESS  read-create
          STATUS  current
          DESCRIPTION
                  "Reserved."
          ::= { zxEdslLineCfgProfEntry 27 }

   zxEdslCfgProfRowStatus OBJECT-TYPE
          SYNTAX  RowStatus
          MAX-ACCESS  read-create
          STATUS  current
          DESCRIPTION
                  "This object is used to create and delete rows in the
                   zxVdslConfProfileTable."
          ::= { zxEdslLineCfgProfEntry 28 }   
          
--    edsl Config Table 
--
   zxEdslConfigTable OBJECT-TYPE
        SYNTAX  SEQUENCE OF ZxEdslCfgEntry
        MAX-ACCESS  not-accessible
        STATUS  current
        DESCRIPTION
              "A table that contains general config information 
          about every VDSL port that is associated with this switch."
        ::= { oemZxBSIU 8 }
        
   zxEdslCfgEntry  OBJECT-TYPE
        SYNTAX  ZxEdslCfgEntry
        MAX-ACCESS  not-accessible
        STATUS  current
        DESCRIPTION
                "A list of general VDSL information for each port."
        INDEX  { zxEdslCfgIndex  }
        ::= { zxEdslConfigTable 1 }


   ZxEdslCfgEntry ::=
        SEQUENCE {
            zxEdslCfgIndex               INTEGER,
            zxEdslCfgProfile              DisplayString,
            zxEdslCfgBak1                INTEGER,
            zxEdslCfgBak2                INTEGER            
        }       

   zxEdslCfgIndex OBJECT-TYPE
          SYNTAX      INTEGER (1..1024)
          MAX-ACCESS      not-accessible
          STATUS      current
          DESCRIPTION
                  "The index of the VDSL config table. it associate 
                  with port."
          ::= { zxEdslCfgEntry 1 }

   zxEdslCfgProfile OBJECT-TYPE
      SYNTAX      DisplayString (SIZE(1..32))
      MAX-ACCESS  read-write
      STATUS      current
      DESCRIPTION
        "This object is a pointer to a VDSL configuration profile in 
        the zxVdslConfProfileTable.  The value of this object is the
        index of the referenced profile in the zxVdslConfProfileTable.
        Note that VDSL configuration profiles are only applicable to 
        VDSL lines.  
        Any attempt to set this object to a value that is not the value
        of the index for an active entry in the profile table,
        zxVdslConfProfileTable, MUST be rejected."
      ::= { zxEdslCfgEntry 2 }

   zxEdslCfgBak1 OBJECT-TYPE
          SYNTAX  INTEGER
          MAX-ACCESS  read-write
          STATUS  current
          DESCRIPTION
                  "Reserved."
          ::= { zxEdslCfgEntry 3 }

   zxEdslCfgBak2 OBJECT-TYPE
          SYNTAX  INTEGER
          MAX-ACCESS  read-write
          STATUS  current
          DESCRIPTION
                  "Reserved."
          ::= { zxEdslCfgEntry 4 }
                          

-- This is EDSL statisitc table
--
   zxEdslStatTable OBJECT-TYPE
        SYNTAX  SEQUENCE OF ZxEdslStatEntry
        MAX-ACCESS  not-accessible
        STATUS  current
        DESCRIPTION
              "A table that contains general status information 
          about every VDSL port that is associated with this switch."
        ::= { oemZxBSIU 9 }

   zxEdslStatEntry  OBJECT-TYPE
        SYNTAX   ZxEdslStatEntry
        MAX-ACCESS  not-accessible
        STATUS  current
        DESCRIPTION
                "A list of general VDSL information for each port."
        INDEX  { zxEdslCfgIndex  }
        ::= { zxEdslStatTable 1 }

   ZxEdslStatEntry ::=
        SEQUENCE {

            zxEdslLinkUpRate          INTEGER,
            zxEdslLinkDownRate      INTEGER,
            zxEdslLinkCurUSRate      INTEGER,
            zxEdslLinkCurDSRate      INTEGER,

            zxEdslStatSNR              INTEGER,
            zxEdslStatMSE             INTEGER,
            zxEdslStatCRSE           INTEGER,
            zxEdslStatTPower        INTEGER,
            zxEdslStatLnkStat       INTEGER,
            zxEdslStatLnkFail         INTEGER,
            zxEdslStatPMDStat       BITS,

            zxEdslTransFrames       INTEGER,
            zxEdslTransPauseFrames  INTEGER,
            zxEdslTransOctets       INTEGER,
            zxEdslRecvFrames          INTEGER,
            zxEdslRecvPauseFrames     INTEGER,
            zxEdslRecvBroadcastFrames     INTEGER,
            zxEdslCollisionCounters       INTEGER,
            zxEdslSingleCollision       INTEGER,
            zxEdslMultipleCollision       INTEGER,
            zxEdslLateCollision           INTEGER,
            zxEdslExcessiveCollision      Counter32,
            zxEdslErrorCounters           Counter32,
            zxEdslReceivedError           Counter32,
            zxEdslCarrierError           Counter32,
            zxEdslFrameTooLongError       Counter32,
            zxEdslFrameCRCError           Counter32
    }    

   zxEdslLinkUpRate OBJECT-TYPE
          SYNTAX  INTEGER 
          MAX-ACCESS  read-only
          STATUS  current
          DESCRIPTION
                  "Linkup Rate of the port."
          ::= { zxEdslStatEntry 1 }

   zxEdslLinkDownRate OBJECT-TYPE
          SYNTAX  INTEGER 
          MAX-ACCESS  read-only
          STATUS  current
          DESCRIPTION
                  "Linkdown rate of the port."
          ::= { zxEdslStatEntry 2 }

   zxEdslLinkCurUSRate OBJECT-TYPE
          SYNTAX  INTEGER
          MAX-ACCESS  read-only
          STATUS  current
          DESCRIPTION
                  "Current  US rate of the port."
          ::= { zxEdslStatEntry 3 }

   zxEdslLinkCurDSRate OBJECT-TYPE
          SYNTAX  INTEGER
          MAX-ACCESS  read-only
          STATUS  current
          DESCRIPTION
                  "Current  DS rate of the port."
          ::= { zxEdslStatEntry 4 }
          
   zxEdslStatSNR OBJECT-TYPE
          SYNTAX      INTEGER
          MAX-ACCESS      read-only
          STATUS      current
          DESCRIPTION
                  "The SNR of recv signal of the port ."
          ::= { zxEdslStatEntry 5 }

   zxEdslStatMSE OBJECT-TYPE
          SYNTAX      INTEGER
          MAX-ACCESS      read-only
          STATUS      current
          DESCRIPTION
                  "The mean square error of the port ."
          ::= { zxEdslStatEntry 6 }

   zxEdslStatCRSE OBJECT-TYPE
          SYNTAX      INTEGER 
          MAX-ACCESS      read-only
          STATUS      current
          DESCRIPTION
                  "The corrected rs error of the port ."
          ::= { zxEdslStatEntry 7 }

   zxEdslStatTPower OBJECT-TYPE
          SYNTAX      INTEGER 
          MAX-ACCESS      read-only
          STATUS      current
          DESCRIPTION
                  "The tramsmit power of the port ."
          ::= { zxEdslStatEntry 8 }

   zxEdslStatLnkStat OBJECT-TYPE
          SYNTAX      INTEGER {
           up(1),
               down(2),
               testing(3)
      }
          MAX-ACCESS      read-only
          STATUS      current
          DESCRIPTION
                  "The vdsl link state of the port ."
          ::= { zxEdslStatEntry 9 }

   zxEdslStatLnkFail OBJECT-TYPE
          SYNTAX      INTEGER 
          MAX-ACCESS      read-only
          STATUS      current
          DESCRIPTION
                  "The link fail count of the port ."
          ::= { zxEdslStatEntry 10 }

   zxEdslStatPMDStat OBJECT-TYPE
          SYNTAX      BITS {
          microInter(0),
              agcConverged(1),
              timConverged(2),
              adcSaturation(3)
          }
          MAX-ACCESS      read-only
          STATUS      current
          DESCRIPTION
                  "The PMD state of the port ."
          ::= { zxEdslStatEntry 11 }

   zxEdslTransFrames OBJECT-TYPE
          SYNTAX      INTEGER
          MAX-ACCESS      read-only
          STATUS      current
          DESCRIPTION
                  "Transmited frame couter."
          ::= { zxEdslStatEntry 12 }

   zxEdslTransPauseFrames OBJECT-TYPE
          SYNTAX      INTEGER 
          MAX-ACCESS      read-only
          STATUS      current
          DESCRIPTION
                  "Transmited pause frame couter."
          ::= { zxEdslStatEntry 13 }

   zxEdslTransOctets OBJECT-TYPE
          SYNTAX      INTEGER 
          MAX-ACCESS      read-only
          STATUS      current
          DESCRIPTION
                  "Transmited octet couter."
          ::= { zxEdslStatEntry 14 }

   zxEdslRecvFrames OBJECT-TYPE
          SYNTAX      INTEGER 
          MAX-ACCESS      read-only
          STATUS      current
          DESCRIPTION
                  "Received frame couter."
          ::= { zxEdslStatEntry 15 }

   zxEdslRecvPauseFrames OBJECT-TYPE
          SYNTAX      INTEGER
          MAX-ACCESS      read-only
          STATUS      current
          DESCRIPTION
                  "Received pause frame couter ."
          ::= { zxEdslStatEntry 16 }

   zxEdslRecvBroadcastFrames OBJECT-TYPE
          SYNTAX      INTEGER 
          MAX-ACCESS      read-only
          STATUS      current
          DESCRIPTION
                  "Received broadcast frame couter."
          ::= { zxEdslStatEntry 17 }

   zxEdslCollisionCounters OBJECT-TYPE
          SYNTAX      INTEGER 
          MAX-ACCESS      read-only
          STATUS      current
          DESCRIPTION
                  ""
          ::= { zxEdslStatEntry 18 }

   zxEdslSingleCollision OBJECT-TYPE
          SYNTAX      INTEGER 
          MAX-ACCESS      read-only
          STATUS      current
          DESCRIPTION
                  ""
          ::= { zxEdslStatEntry 19 }

   zxEdslMultipleCollision OBJECT-TYPE
          SYNTAX      INTEGER 
          MAX-ACCESS      read-only
          STATUS      current
          DESCRIPTION
                  ""
          ::= { zxEdslStatEntry 20 }

   zxEdslLateCollision OBJECT-TYPE
          SYNTAX      INTEGER 
          MAX-ACCESS      read-only
          STATUS      current
          DESCRIPTION
                  ""
          ::= { zxEdslStatEntry 21 }

   zxEdslExcessiveCollision OBJECT-TYPE
          SYNTAX      Counter32
          MAX-ACCESS      read-only
          STATUS      current
          DESCRIPTION
                  ""
          ::= { zxEdslStatEntry 22 }

   zxEdslErrorCounters OBJECT-TYPE
          SYNTAX      Counter32
          MAX-ACCESS      read-only
          STATUS      current
          DESCRIPTION
                  "Error frame couter."
          ::= { zxEdslStatEntry 23 }

   zxEdslReceivedError OBJECT-TYPE
          SYNTAX      Counter32
          MAX-ACCESS      read-only
          STATUS      current
          DESCRIPTION
                  "Received error frame couter ."
          ::= { zxEdslStatEntry 24 }

   zxEdslCarrierError OBJECT-TYPE
          SYNTAX      Counter32
          MAX-ACCESS      read-only
          STATUS      current
          DESCRIPTION
                  "Error frame couter due to carrier error."
          ::= { zxEdslStatEntry 25 }

   zxEdslFrameTooLongError OBJECT-TYPE
          SYNTAX      Counter32
          MAX-ACCESS      read-only
          STATUS      current
          DESCRIPTION
                  "Error frame couter due to frame too long."
          ::= { zxEdslStatEntry 26 }

   zxEdslFrameCRCError OBJECT-TYPE
          SYNTAX      Counter32
          MAX-ACCESS      read-only
          STATUS      current
          DESCRIPTION
                  "Error frame couter due to CRC error. "
          ::= { zxEdslStatEntry 27 }

-- This is EDSL port command table
--
   zxEdslPortCmdTable OBJECT-TYPE
        SYNTAX  SEQUENCE OF ZxEdslPortCmdEntry
        MAX-ACCESS  not-accessible
        STATUS  current
        DESCRIPTION
              "A table that contains general command
          about every VDSL port that is associated with this switch."
        ::= { oemZxBSIU 10 }

   zxEdslPortCmdEntry  OBJECT-TYPE
        SYNTAX   ZxEdslPortCmdEntry
        MAX-ACCESS  not-accessible
        STATUS  current
        DESCRIPTION
                "A list of general VDSL information for each port."
        INDEX  { zxEdslCfgIndex  }
        ::= { zxEdslPortCmdTable 1 }


   ZxEdslPortCmdEntry ::=
        SEQUENCE {
            zxEdslCfgLTActive             INTEGER,
            zxEdslCfgLTLcLoop           INTEGER,
            zxEdslCfgLTLnLoop           INTEGER,
            zxEdslCfgLTTransOnOff         INTEGER,
            zxEdslCfgNTReset              INTEGER,
            zxEdslCfgNTLnLoop           INTEGER,        
            zxEdslCfgLTReset              INTEGER

        }

   zxEdslCfgLTActive OBJECT-TYPE
          SYNTAX  INTEGER {
                      activate(1),
              deactivate(2)
                  }
          MAX-ACCESS  read-write
          STATUS  current
          DESCRIPTION
                  "Activate/deactivate the LT of the port."
          ::= { zxEdslPortCmdEntry 1 }
          
   zxEdslCfgLTLcLoop OBJECT-TYPE
          SYNTAX  INTEGER {
                      loop(1),  -- set and get operation.
                        noloop(2),
                        unknown(3)
          }
          MAX-ACCESS  read-write
          STATUS  current
          DESCRIPTION
                  "LT local loop test on the port."
          ::= { zxEdslPortCmdEntry 2 }

   zxEdslCfgLTLnLoop OBJECT-TYPE
          SYNTAX  INTEGER {
                      loop(1),  -- set and get operation.
                        noloop(2),
                        unknown(3)
          }
          MAX-ACCESS  read-write
          STATUS  current
          DESCRIPTION
                  "LT line loop test on the port."
          ::= { zxEdslPortCmdEntry 3 }

   zxEdslCfgLTTransOnOff OBJECT-TYPE
          SYNTAX  INTEGER {
                      enable(1),
              disable(2),
              unknown(3)
          }
          MAX-ACCESS  read-write
          STATUS  current
          DESCRIPTION
                  "Enable/disable Transmitter of the port
          when link deactivation."
          ::= { zxEdslPortCmdEntry 4 }

   zxEdslCfgNTReset OBJECT-TYPE
          SYNTAX  INTEGER {
                      reset(1)                      
                  }
          MAX-ACCESS  read-write
          STATUS  current
          DESCRIPTION
                  "NT reset on the port.."
          ::= { zxEdslPortCmdEntry 5 }

   zxEdslCfgNTLnLoop OBJECT-TYPE
          SYNTAX  INTEGER {
                      loop(1),  -- set and get operation.
                        noloop(2),
                        unknown(3)
          }
          MAX-ACCESS  read-write
          STATUS  current
          DESCRIPTION
                  "NT line loop test on the port."
          ::= { zxEdslPortCmdEntry 6 }

   zxEdslCfgLTReset OBJECT-TYPE
          SYNTAX  INTEGER {
                      loop(1),  -- set and get operation.
                        noloop(2),
                        unknown(3)
          }
          MAX-ACCESS  read-write
          STATUS  current
          DESCRIPTION
                  "NT line loop test on the port."
          ::= { zxEdslPortCmdEntry 7 }
        

-- -----------------------------------------------------------------
--   Trap 
-- -----------------------------------------------------------------

oemZxEdslCardUp NOTIFICATION-TYPE
    OBJECTS   { oemZxEdslCardIndex, oemZxEdslCardType }
    STATUS    current
    DESCRIPTION "A cardUp trap signifies that the SNMP agent has detectd that
                 the card has transitioned out of the down state. This trap 
                 indicates that some card has recovered from fault or been 
                 inserted into one switch slot"
     ::= { oemZxEdslTrap 0 1 }

oemZxEdslCardDown       NOTIFICATION-TYPE
    OBJECTS   { oemZxEdslCardIndex, oemZxEdslCardType }
    STATUS    current
    DESCRIPTION "A cardDown trap signifies that the SNMP agent has detected that
                the card has transitioned into the down state. This trap indicates 
                that some card has occured fault or been pulled out from one 
                switch slot."
     ::= { oemZxEdslTrap 0 2 }


oemZxVdslLinkUp NOTIFICATION-TYPE
    OBJECTS   { oemVdslCfgIndex, oemVdslStatLnkStat }
    STATUS    current
    DESCRIPTION 
        "Trap for VDSL linkup."
     ::= { oemZxEdslTrap 0 3 }

oemZxVdslLinkDown       NOTIFICATION-TYPE
    OBJECTS   { oemVdslCfgIndex, oemVdslStatLnkStat }
    STATUS    current
    DESCRIPTION 
        "Trap for VDSL linkdown."
     ::= { oemZxEdslTrap 0 4 }

oemZxEdslCardTestingAbnormal       NOTIFICATION-TYPE
    OBJECTS   { oemZxEdslCardIndex, oemZxEdslCardType }
    STATUS    current
    DESCRIPTION 
        "A cardTesting Abnormal trap signifies that the SNMP agent has detected that
                there is something wrong with the card during testing."
     ::= { oemZxEdslTrap 0 5 }

oemZxEdslCardTestingAbnormalCleared  NOTIFICATION-TYPE
    OBJECTS   { oemZxEdslCardIndex, oemZxEdslCardType }
    STATUS    current
    DESCRIPTION 
        "A oemZxEdslCardTestingAbnormalCleard trap indicates that the 
        oemZxEdslCardTestingAbnormal has cleared."
     ::= { oemZxEdslTrap 0 6 }
                          
   END
   
-- ----------------------------------------------------------------------------
-- OEMZXEDSL
-- ----------------------------------------------------------------------------

    OEMZXEDSL DEFINITIONS ::= BEGIN

    IMPORTS
        MODULE-IDENTITY, OBJECT-TYPE, NOTIFICATION-TYPE,
        Integer32, Counter64,TimeTicks,Counter32,
        IpAddress                            FROM SNMPv2-SMI
        
        DisplayString, TruthValue, RowStatus,TEXTUAL-CONVENTION,              
        MacAddress            FROM SNMPv2-TC
       SnmpAdminString                   FROM SNMP-FRAMEWORK-MIB
        
        MODULE-COMPLIANCE, OBJECT-GROUP         FROM SNMPv2-CONF
        oemProd                                 FROM WRS-MASTER-MIB       
        PortList                               FROM Q-BRIDGE-MIB;     
--      Note:
--         RowStatus: active(1),notInService(2),notReady(3),createAndGo(4),
--                    createAndWait(5),destroy(6)
--
--

    oemZxEdslMib MODULE-IDENTITY
        LAST-UPDATED    "0212110000Z"  -- Dec 11, 2002
        ORGANIZATION    "ZTE."
        CONTACT-INFO    "ZTE."

        DESCRIPTION     "Description of several ZXDSL9210 stack. "

        REVISION        "0212110000Z"  -- Dec 11, 2002
        DESCRIPTION     "Initial MIB creation."

        ::= { oemProd 6 }

    oemZxEdslStack                 OBJECT IDENTIFIER ::= { oemZxEdslMib 1 }
    oemZxEdslDhcpRelay          OBJECT IDENTIFIER ::= { oemZxEdslMib 2 }
    oemZxEdslRadius             OBJECT IDENTIFIER ::= { oemZxEdslMib 3 }
    oemZxEdslAtmPVC             OBJECT IDENTIFIER ::= { oemZxEdslMib 4 }
    
    oemZxEdslService            OBJECT IDENTIFIER ::= { oemZxEdslMib 10 }
    oemZxEdslLNP                OBJECT IDENTIFIER ::= { oemZxEdslMib 11 }
    oemZxEdslPortLocation       OBJECT IDENTIFIER ::= { oemZxEdslMib 12 }  
    oemZxEdslMVR                OBJECT IDENTIFIER ::= { oemZxEdslMib 13 }
    oemZxEdslFdb                OBJECT IDENTIFIER ::= { oemZxEdslMib 15 }
    oemZxEdslLoopCheck          OBJECT IDENTIFIER ::= { oemZxEdslMib 16 }

    oemZxEdslMibEnd             OBJECT IDENTIFIER ::= { oemZxEdslMib 1000 }

    oemZxEdslRadiusClientAuthSvr        OBJECT IDENTIFIER ::= { oemZxEdslRadius 1 }
    oemZxEdslRadiusClientAccSvr         OBJECT IDENTIFIER ::= { oemZxEdslRadius 2 }

    
-- ----------------------------------------------------------------------------
-- Textual Conventions
-- ---------------------------------------------------------------------------


Vlanlist ::= TEXTUAL-CONVENTION
    STATUS      current
    DESCRIPTION
        "Each octet within this value specifies a set of eight
        ports, with the first octet specifying ports 1 through
        8, the second octet specifying ports 9 through 16, etc.
        Within each octet, the most significant bit represents
        the lowest numbered vlan, and the least significant bit
        represents the highest numbered vlan.  Thus, each vlan
        of the bridge is represented by a single bit within the
        value of this object.  If that bit has a value of '1'
        then that vlan is included in the set of vlans; the vlan
        is not included if its bit has a value of '0'."
    SYNTAX      OCTET STRING

------------------------------------------------------------------------------
    
    oemZxEdslStackModuleNum OBJECT-TYPE
        SYNTAX Integer32 (1..8)
        MAX-ACCESS read-write
        STATUS current
        DESCRIPTION
            "all ZXDSL9210 number in this stack system."
        ::= { oemZxEdslStack 1 }

    oemZxEdslStackModuleId OBJECT-TYPE
        SYNTAX Integer32 (1..8)
        MAX-ACCESS read-write
        STATUS current
        DESCRIPTION
            "Module Id of this ZXDSL9210 in this stack system."
        ::= { oemZxEdslStack 2 }
       
    oemZxEdslStackModuleRole OBJECT-TYPE
        SYNTAX INTEGER{
                        master(1),
                        slave(2)
                        }
        MAX-ACCESS read-write
        STATUS current
        DESCRIPTION
            "role of this ZXDSL9210 in this stack system."
        ::= { oemZxEdslStack 3 }
       
       
    oemZxEdslStackTable OBJECT-TYPE
        SYNTAX SEQUENCE OF OemZxEdslStackEntry
        MAX-ACCESS not-accessible
        STATUS current
        DESCRIPTION
            "A table that contains all ZXDSL informations in this stack system.
             It is allowed to get in master module."
        ::= { oemZxEdslStack 10 }

    oemZxEdslStackEntry OBJECT-TYPE
        SYNTAX OemZxEdslStackEntry
        MAX-ACCESS not-accessible
        STATUS current
        DESCRIPTION
            "A list of  entries of all ZXDSL information."
        INDEX { oemZxEdslStackIndex }
    ::= { oemZxEdslStackTable 1 }

    OemZxEdslStackEntry ::=
        SEQUENCE {
            oemZxEdslStackIndex                INTEGER,
            oemZxEdslStackIpAddr               IpAddress,
            oemZxEdslStackState              INTEGER
                           
        }

    oemZxEdslStackIndex OBJECT-TYPE
        SYNTAX INTEGER(1..8)
        MAX-ACCESS not-accessible
        STATUS current
        DESCRIPTION
            "The Module Id ."
        
    ::= { oemZxEdslStackEntry 1 }

    oemZxEdslStackIpAddr OBJECT-TYPE
        SYNTAX IpAddress
        MAX-ACCESS read-write
        STATUS current
        DESCRIPTION
            "The Ipaddress of the Module to transport information between master
            module and slave module. this is inner Ipaddress, and Snmp is not allowed
            to get."
        
    ::= { oemZxEdslStackEntry 2 }

    oemZxEdslStackState OBJECT-TYPE
        SYNTAX INTEGER{
                        master(1),
                        slave(2),
                        down(3)
                        }
        MAX-ACCESS read-only
        STATUS current
        DESCRIPTION
            "The Module's state ."
        
    ::= { oemZxEdslStackEntry 3 }

------------------------------------------------------------------------------
------------------------------------------------------------------------------

    oemZxEdslDhcpRelayEnable OBJECT-TYPE
        SYNTAX INTEGER{
                        enable(1),
                        disable(2)
                        }
        MAX-ACCESS read-write
        STATUS current
        DESCRIPTION
            "Enable/disable DHCP-Relay in this system."
        ::= { oemZxEdslDhcpRelay 1 }

    oemZxEdslDhcpRelayFirstHop OBJECT-TYPE
        SYNTAX INTEGER{
                        enable(1),
                        disable(2)
                        }
        MAX-ACCESS read-write
        STATUS current
        DESCRIPTION
            "DHCP relay agent will untouch the RAI options if it is not the 
             first hop of the clients' requests"
        ::= { oemZxEdslDhcpRelay 2 }
       
    oemZxEdslDhcpRelayAddRAI OBJECT-TYPE
        SYNTAX INTEGER{
                        enable(1),
                        disable(2)
                        }
        MAX-ACCESS read-write
        STATUS current
        DESCRIPTION
            "DHCP relay agent will not add the RAI options if it is not configured
             to do so."
        ::= { oemZxEdslDhcpRelay 3 }

    oemZxEdslDhcpRelayMaxLen OBJECT-TYPE
        SYNTAX INTEGER (300..1500)
        MAX-ACCESS read-write
        STATUS current
        DESCRIPTION
            "DHCP packets larger than the configuration will not have the RAI added."
        ::= { oemZxEdslDhcpRelay 4 }

    oemZxEdslDhcpRelayUnicast OBJECT-TYPE
        SYNTAX INTEGER{
                        enable(1),
                        disable(2)
                        }
        MAX-ACCESS read-write
        STATUS current
        DESCRIPTION
            "If this configuration is enabled, the relay agent will process unicast
             DHCP packets also."
        ::= { oemZxEdslDhcpRelay 5 }

       
    oemZxEdslDhcpRelayTable OBJECT-TYPE
        SYNTAX SEQUENCE OF OemZxEdslDhcpRelayEntry
        MAX-ACCESS not-accessible
        STATUS current
        DESCRIPTION
            "A table that contains all ZXDSL informations in this stack system.
         It is allowed to get in master module."
        ::= { oemZxEdslDhcpRelay 10 }

    oemZxEdslDhcpRelayEntry OBJECT-TYPE
        SYNTAX OemZxEdslDhcpRelayEntry
        MAX-ACCESS not-accessible
        STATUS current
        DESCRIPTION
            "A list of  entries of all ZXDSL information."
        INDEX { oemZxEdslDhcpRelayInterface }
        ::= { oemZxEdslDhcpRelayTable 1 }

    OemZxEdslDhcpRelayEntry ::=
        SEQUENCE {
            oemZxEdslDhcpRelayInterface    INTEGER,
            oemZxEdslDhcpRelayTrust        INTEGER,
            oemZxEdslDhcpRelayHops         INTEGER,
            oemZxEdslDhcpRelaySecs         INTEGER,
            oemZxEdslDhcpRelayCircuitId    DisplayString,
            oemZxEdslDhcpRelayRemoteId     DisplayString                           
        }

    oemZxEdslDhcpRelayInterface OBJECT-TYPE
        SYNTAX INTEGER(1..4095)
        MAX-ACCESS not-accessible
        STATUS current
        DESCRIPTION
            "Interface ."
        ::= { oemZxEdslDhcpRelayEntry 1 }

    oemZxEdslDhcpRelayTrust OBJECT-TYPE
        SYNTAX INTEGER{
                        enable(1),
                        disable(2)
                        }
        MAX-ACCESS read-write
        STATUS current
        DESCRIPTION
            "DHCP packets with RAI options from untrust Interface
             will be silently discarded. Otherwise the packet should
             be forwarded as normal with the RAI options untouched."
        ::= { oemZxEdslDhcpRelayEntry 2 }

    oemZxEdslDhcpRelayHops OBJECT-TYPE
        SYNTAX INTEGER(1..16)
        MAX-ACCESS read-write
        STATUS current
        DESCRIPTION
            "DHCP clients set this field to zero, and the relay agent
            increase it. A packet with hops larger than the configuration
            should be silently discarded."
        ::= { oemZxEdslDhcpRelayEntry 3 }

    oemZxEdslDhcpRelaySecs OBJECT-TYPE
        SYNTAX INTEGER(1..86400)
        MAX-ACCESS read-write
        STATUS current
        DESCRIPTION
            "The relay agent will delay for the 'secs' before it forward packet"
        ::= { oemZxEdslDhcpRelayEntry 4 }

    oemZxEdslDhcpRelayCircuitId OBJECT-TYPE
        SYNTAX DisplayString(SIZE(0..64))
        MAX-ACCESS read-write
        STATUS current
        DESCRIPTION
            "Identification of local ciruit which recieving the DHCP packets."
        ::= { oemZxEdslDhcpRelayEntry 5 }

    oemZxEdslDhcpRelayRemoteId OBJECT-TYPE
        SYNTAX DisplayString(SIZE(0..64))
        MAX-ACCESS read-write
        STATUS current
        DESCRIPTION
            "The identification of the peer side of a local circuit."
        ::= { oemZxEdslDhcpRelayEntry 6 }

    oemZxEdslDhcpServerTable OBJECT-TYPE
        SYNTAX SEQUENCE OF OemZxEdslDhcpServerEntry
        MAX-ACCESS not-accessible
        STATUS current
        DESCRIPTION
            "A table that contains all ZXDSL informations in this stack system.
            It is allowed to get in master module."
        ::= { oemZxEdslDhcpRelay 11 }

    oemZxEdslDhcpServerEntry OBJECT-TYPE
        SYNTAX OemZxEdslDhcpServerEntry
        MAX-ACCESS not-accessible
        STATUS current
        DESCRIPTION
            "A list of  entries of all ZXDSL information."
        INDEX { oemZxEdslDhcpServerIpaddr,oemZxEdslDhcpServerPort }
        ::= { oemZxEdslDhcpServerTable 1 }

    OemZxEdslDhcpServerEntry ::=
        SEQUENCE {
            oemZxEdslDhcpServerIpaddr      IpAddress,
            oemZxEdslDhcpServerPort        Integer32,
            oemZxEdslDhcpServerStatus      RowStatus
        }

    oemZxEdslDhcpServerIpaddr OBJECT-TYPE
        SYNTAX       IpAddress
        MAX-ACCESS   not-accessible
        STATUS       current
        DESCRIPTION
            "The ip address of the DHCP server."
        ::= { oemZxEdslDhcpServerEntry 1 }

    oemZxEdslDhcpServerPort OBJECT-TYPE
        SYNTAX      Integer32
        MAX-ACCESS  not-accessible
        STATUS      current
        DESCRIPTION
            "The port number of the DHCP server"
       ::= { oemZxEdslDhcpServerEntry 2 }

    oemZxEdslDhcpServerStatus OBJECT-TYPE
        SYNTAX     RowStatus
        MAX-ACCESS read-create
        STATUS     current
        DESCRIPTION
            "."
        ::= { oemZxEdslDhcpServerEntry 3 }

--    oemZxEdslDhcpRelayStaticsTable OBJECT-TYPE

-- show dhcprelay interface
-- set dhcprelay interface [n] [ena/dis]
-- set dhcprelay interface [n] trust [ena/dis] hops [1~16] secs [0~65535]
-- set dhcprelay interface [n] circuitid [string] remoteid [string]

-- show dhcprelay server
-- set dhcprelay server [ipaddress] [port] add/del

-- show dhcprelay statistics
        
------------------------------------------------------------------------------
------------------------------------------------------------------------------
        
    
    
    oemZxEdslRadiusClientAuthSvrTable OBJECT-TYPE
          SYNTAX     SEQUENCE OF OemZxEdslRadiusClientAuthSvrEntry
          MAX-ACCESS not-accessible
          STATUS     current
          DESCRIPTION
                "The (conceptual) table listing the RADIUS accounting
                 servers with which the client shares a secret."
          ::= { oemZxEdslRadiusClientAuthSvr 1 }

    oemZxEdslRadiusClientAuthSvrEntry OBJECT-TYPE
          SYNTAX     OemZxEdslRadiusClientAuthSvrEntry
          MAX-ACCESS not-accessible
          STATUS     current
          DESCRIPTION
                "An entry (conceptual row) representing a RADIUS
                 accounting server with which the client shares a secret."
          INDEX      { oemZxEdslRadiusClientAuthSvrAddress,oemZxEdslRadiusClientAuthSvrPortNumber }
          ::= { oemZxEdslRadiusClientAuthSvrTable 1 }

    OemZxEdslRadiusClientAuthSvrEntry ::= SEQUENCE {
          oemZxEdslRadiusClientAuthSvrAddress              IpAddress,
          oemZxEdslRadiusClientAuthSvrPortNumber           Integer32,
          oemZxEdslRadiusClientAuthSecret                  SnmpAdminString,
          oemZxEdslRadiusClientAuthRowStatus               RowStatus
    }
    
    
    oemZxEdslRadiusClientAuthSvrAddress OBJECT-TYPE
          SYNTAX     IpAddress
          MAX-ACCESS not-accessible
          STATUS     current
          DESCRIPTION
                "The IP address of the RADIUS accounting server
                 referred to in this table entry."
          ::= { oemZxEdslRadiusClientAuthSvrEntry 1 }
    
    oemZxEdslRadiusClientAuthSvrPortNumber  OBJECT-TYPE
          SYNTAX     Integer32 (0..65535)
          MAX-ACCESS not-accessible
          STATUS     current
          DESCRIPTION
                "The UDP port the client is using to send requests to
                 this server."
          ::= { oemZxEdslRadiusClientAuthSvrEntry 2 }
    
    oemZxEdslRadiusClientAuthSecret OBJECT-TYPE
        SYNTAX      SnmpAdminString (SIZE (0..32))
        MAX-ACCESS  read-create
        STATUS      current
        DESCRIPTION
            ""
        REFERENCE
            "1"
        ::= { oemZxEdslRadiusClientAuthSvrEntry 3}
        
        
       oemZxEdslRadiusClientAuthRowStatus OBJECT-TYPE
        SYNTAX      RowStatus
        MAX-ACCESS  read-create
        STATUS      current
        DESCRIPTION
            "This object indicates the status of this entry."
        ::= { oemZxEdslRadiusClientAuthSvrEntry 4 }
        
    
--    ///////////////////////////////////////////////////////////////////
    
    
    oemZxEdslRadiusClientAccSvrTable OBJECT-TYPE
          SYNTAX SEQUENCE OF OemZxEdslRadiusClientAccSvrEntry
          MAX-ACCESS not-accessible
          STATUS     current
          DESCRIPTION
                "The (conceptual) table listing the RADIUS accounting
                 servers with which the client shares a secret."
          ::= { oemZxEdslRadiusClientAccSvr 2 }
    
    oemZxEdslRadiusClientAccSvrEntry OBJECT-TYPE
          SYNTAX     OemZxEdslRadiusClientAccSvrEntry
          MAX-ACCESS not-accessible
          STATUS     current
          DESCRIPTION
                "An entry (conceptual row) representing a RADIUS
                 accounting server with which the client shares a secret."
          INDEX      { oemZxEdslRadiusClientAccSvrAddress,oemZxEdslRadiusClientAccSvrPortNumber }
          ::= { oemZxEdslRadiusClientAccSvrTable 1 }
    
    OemZxEdslRadiusClientAccSvrEntry ::= SEQUENCE {
          oemZxEdslRadiusClientAccSvrAddress                   IpAddress,
          oemZxEdslRadiusClientAccSvrPortNumber                Integer32,
          oemZxEdslRadiusClientAccSecret                       SnmpAdminString,
          oemZxEdslRadiusClientAccRowStatus                    RowStatus
    }
   
    oemZxEdslRadiusClientAccSvrAddress OBJECT-TYPE
          SYNTAX     IpAddress
          MAX-ACCESS not-accessible
          STATUS     current
          DESCRIPTION
                "The IP address of the RADIUS accounting server
                 referred to in this table entry."
          ::= { oemZxEdslRadiusClientAccSvrEntry 1 }
    
    oemZxEdslRadiusClientAccSvrPortNumber  OBJECT-TYPE
          SYNTAX     Integer32 (0..65535)
          MAX-ACCESS not-accessible
          STATUS     current
          DESCRIPTION
                "The UDP port the client is using to send requests to
                 this server."
          ::= { oemZxEdslRadiusClientAccSvrEntry 2 }
    
    oemZxEdslRadiusClientAccSecret OBJECT-TYPE
        SYNTAX      SnmpAdminString (SIZE (0..32))
        MAX-ACCESS  read-create
        STATUS      current
        DESCRIPTION
            ""
        REFERENCE
            "1"
        ::= { oemZxEdslRadiusClientAccSvrEntry 3}
        
    oemZxEdslRadiusClientAccRowStatus OBJECT-TYPE
        SYNTAX      RowStatus
        MAX-ACCESS  read-create
        STATUS      current
        DESCRIPTION
            "This object indicates the status of this entry."
        ::= { oemZxEdslRadiusClientAccSvrEntry 4 }

------------------------------------------------------------------------------
------------------------------------------------------------------------------
     oemZxEdslAtmPVCTable         OBJECT-TYPE
          SYNTAX         SEQUENCE OF OemZxEdslAtmPVCEntry
          MAX-ACCESS     not-accessible
          STATUS         current
          DESCRIPTION
              "The PVC table."
          ::= { oemZxEdslAtmPVC 1 }

     oemZxEdslAtmPVCEntry         OBJECT-TYPE
          SYNTAX         OemZxEdslAtmPVCEntry
          MAX-ACCESS     not-accessible
          STATUS         current
          DESCRIPTION
              "An entry in the PVC table."
          INDEX  {oemZxEdslAtmPort,oemZxEdslAtmVpi,oemZxEdslAtmVci}
          ::= { oemZxEdslAtmPVCTable  1}

     OemZxEdslAtmPVCEntry    ::= SEQUENCE  {
          oemZxEdslAtmPort              Integer32,
          oemZxEdslAtmVpi               INTEGER,
          oemZxEdslAtmVci               Integer32,
          oemZxEdslAtmVclReserve1       Integer32,
          oemZxEdslAtmStatus            RowStatus,
          oemZxEdslAtmPVCDescription    OCTET STRING,
          oemZxEdslAtmPVCStatus         Integer32
     }
     
     oemZxEdslAtmPort          OBJECT-TYPE
          SYNTAX         Integer32
          MAX-ACCESS     not-accessible
          STATUS         current
          DESCRIPTION
              "The port of ADSL."
          ::= { oemZxEdslAtmPVCEntry 1}
          
     oemZxEdslAtmVpi           OBJECT-TYPE
          SYNTAX         INTEGER(1..8)
          MAX-ACCESS     not-accessible
          STATUS         current
          DESCRIPTION
              "VPI on an ADSL port."
          ::= { oemZxEdslAtmPVCEntry 2}

     oemZxEdslAtmVci           OBJECT-TYPE
          SYNTAX         Integer32
          MAX-ACCESS     not-accessible
          STATUS         current
          DESCRIPTION
              "VCI on an ADSL port."
          ::= { oemZxEdslAtmPVCEntry 3}

     oemZxEdslAtmVclReserve1   OBJECT-TYPE
          SYNTAX         Integer32
          MAX-ACCESS     read-write
          STATUS         current
          DESCRIPTION
              " "
          ::= { oemZxEdslAtmPVCEntry 4}

     oemZxEdslAtmStatus     OBJECT-TYPE
          SYNTAX         RowStatus
          MAX-ACCESS     read-create
          STATUS         current
          DESCRIPTION
              ""
          ::= {oemZxEdslAtmPVCEntry 5}

    oemZxEdslAtmPVCDescription      OBJECT-TYPE
          SYNTAX         OCTET STRING
          MAX-ACCESS     read-write
          STATUS         current
          DESCRIPTION
              ""
          ::= {oemZxEdslAtmPVCEntry 6}    

     oemZxEdslAtmPVCStatus      OBJECT-TYPE
          SYNTAX         Integer32
          MAX-ACCESS     read-write
          STATUS         current
          DESCRIPTION
              ""
          ::= {oemZxEdslAtmPVCEntry 7}

------------------------------------------------------------------------------
------------------------------------------------------------------------------
     oemZxEdslMacLockTable         OBJECT-TYPE
          SYNTAX         SEQUENCE OF OemZxEdslMacLockEntry
          MAX-ACCESS     not-accessible
          STATUS         current
          DESCRIPTION
              "The MAC lock table. bind a Macaddress on a port."
          ::= { oemZxEdslService 1 }

     oemZxEdslMacLockEntry         OBJECT-TYPE
          SYNTAX         OemZxEdslMacLockEntry
          MAX-ACCESS     not-accessible
          STATUS         current
          DESCRIPTION
              "An entry in the Mac lock table."
          INDEX  {oemZxEdslMacLockPort,oemZxEdslMacLockMacaddress,oemZxEdslMacLockVid}
          ::= { oemZxEdslMacLockTable  1}

     OemZxEdslMacLockEntry    ::= SEQUENCE  {
          oemZxEdslMacLockPort              Integer32,
          oemZxEdslMacLockMacaddress        MacAddress,
          oemZxEdslMacLockRowStatus         RowStatus,
          oemZxEdslMacLockVid               Integer32          
     }
     
     oemZxEdslMacLockPort            OBJECT-TYPE
          SYNTAX         Integer32
          MAX-ACCESS     not-accessible
          STATUS         current
          DESCRIPTION
              "The port to MAC bind."
          ::= { oemZxEdslMacLockEntry 1}
          
     oemZxEdslMacLockMacaddress             OBJECT-TYPE
          SYNTAX         MacAddress
          MAX-ACCESS     not-accessible
          STATUS         current
          DESCRIPTION
              "The MAC to bind to."
          ::= { oemZxEdslMacLockEntry 2}

     oemZxEdslMacLockRowStatus     OBJECT-TYPE
          SYNTAX         RowStatus
          MAX-ACCESS     read-create
          STATUS         current
          DESCRIPTION
              "This object is used to create, delete or modify a row in this
               table."
          ::= {oemZxEdslMacLockEntry 3}

     oemZxEdslMacLockVid            OBJECT-TYPE
          SYNTAX         Integer32
          MAX-ACCESS     not-accessible
          STATUS         current
          DESCRIPTION
              "The Vlan Id."
          ::= { oemZxEdslMacLockEntry 4}

------------------------------------------------------------------------------
          
     oemZxEdslIpLockTable         OBJECT-TYPE
          SYNTAX         SEQUENCE OF OemZxEdslIpLockEntry
          MAX-ACCESS     not-accessible
          STATUS         current
          DESCRIPTION
              "The Ip lock table. bind a Ip address on a port."
          ::= { oemZxEdslService 2 }

     oemZxEdslIpLockEntry         OBJECT-TYPE
          SYNTAX         OemZxEdslIpLockEntry
          MAX-ACCESS     not-accessible
          STATUS         current
          DESCRIPTION
              "An entry in the Ip lock table."
          INDEX  {oemZxEdslIpLockPort,oemZxEdslIpLockIpaddress}
          ::= { oemZxEdslIpLockTable  1}

     OemZxEdslIpLockEntry    ::= SEQUENCE  {
          oemZxEdslIpLockPort              Integer32,
          oemZxEdslIpLockIpaddress         IpAddress,
          oemZxEdslIpLockRowStatus         RowStatus
     }
     
     oemZxEdslIpLockPort            OBJECT-TYPE
          SYNTAX         Integer32
          MAX-ACCESS     not-accessible
          STATUS         current
          DESCRIPTION
              "The port to IP bind."
          ::= { oemZxEdslIpLockEntry 1}
          
     oemZxEdslIpLockIpaddress             OBJECT-TYPE
          SYNTAX         IpAddress
          MAX-ACCESS     not-accessible
          STATUS         current
          DESCRIPTION
              "The IP to bind to."
          ::= { oemZxEdslIpLockEntry 2}

     oemZxEdslIpLockRowStatus     OBJECT-TYPE
          SYNTAX         RowStatus
          MAX-ACCESS     read-create
          STATUS         current
          DESCRIPTION
              "This object is used to create, delete or modify a row in this
               table."
          ::= {oemZxEdslIpLockEntry 3}

------------------------------------------------------------------------------
          
     oemZxEdslAclTable         OBJECT-TYPE
          SYNTAX         SEQUENCE OF OemZxEdslAclEntry
          MAX-ACCESS     not-accessible
          STATUS         current
          DESCRIPTION
              "The Acl table."
          ::= { oemZxEdslService 3 }

     oemZxEdslAclEntry         OBJECT-TYPE
          SYNTAX         OemZxEdslAclEntry
          MAX-ACCESS     not-accessible
          STATUS         current
          DESCRIPTION
              "An entry in the Acl table."
          INDEX  {oemZxEdslAclSrcIp,oemZxEdslAclDestIp,oemZxEdslAclSrcMask,oemZxEdslAclDestMask}
          ::= { oemZxEdslAclTable  1}

     OemZxEdslAclEntry    ::= SEQUENCE  {
          oemZxEdslAclSrcIp                     IpAddress,
          oemZxEdslAclDestIp                    IpAddress,  -- delete
          oemZxEdslAclSrcMask                   IpAddress,  
          oemZxEdslAclDestMask                  IpAddress,  -- delete
          oemZxEdslAclMethod                    INTEGER,
          oemZxEdslAclRowStatus                 RowStatus
     }
     
     oemZxEdslAclSrcIp             OBJECT-TYPE
          SYNTAX         IpAddress
          MAX-ACCESS     not-accessible
          STATUS         current
          DESCRIPTION
              "source Ip."
          ::= { oemZxEdslAclEntry 1}

     oemZxEdslAclDestIp             OBJECT-TYPE
          SYNTAX         IpAddress
          MAX-ACCESS     not-accessible
          STATUS         current
          DESCRIPTION
              "Dest Ip."
          ::= { oemZxEdslAclEntry 2}

     oemZxEdslAclSrcMask             OBJECT-TYPE
          SYNTAX         IpAddress
          MAX-ACCESS     not-accessible
          STATUS         current
          DESCRIPTION
              "source Ip Mask."
          ::= { oemZxEdslAclEntry 3}

     oemZxEdslAclDestMask             OBJECT-TYPE
          SYNTAX         IpAddress
          MAX-ACCESS     not-accessible
          STATUS         current
          DESCRIPTION
              "Dest Ip Mask."
          ::= { oemZxEdslAclEntry 4}

     oemZxEdslAclMethod             OBJECT-TYPE
          SYNTAX         INTEGER{
                            deny(1),
                            permit(2)
                            }
          MAX-ACCESS     read-write
          STATUS         current
          DESCRIPTION
              "deny or permit transfering between src and dest Ip."
          ::= { oemZxEdslAclEntry 5}

     oemZxEdslAclRowStatus     OBJECT-TYPE
          SYNTAX         RowStatus
          MAX-ACCESS     read-create
          STATUS         current
          DESCRIPTION
              "This object is used to create, delete or modify a row in this
               table."
          ::= {oemZxEdslAclEntry 6}
          
------------------------------------------------------------------------------

     oemZxEdslPortTable         OBJECT-TYPE
          SYNTAX         SEQUENCE OF OemZxEdslPortEntry
          MAX-ACCESS     not-accessible
          STATUS         current
          DESCRIPTION
              "The port setting  table."
          ::= { oemZxEdslService 4 }

     oemZxEdslPortEntry         OBJECT-TYPE
          SYNTAX         OemZxEdslPortEntry
          MAX-ACCESS     not-accessible
          STATUS         current
          DESCRIPTION
              "An entry in the Ip lock table."
          INDEX  {oemZxEdslPortIndex}
          ::= { oemZxEdslPortTable  1}

     OemZxEdslPortEntry    ::= SEQUENCE  {
          oemZxEdslPortIndex                 Integer32,
          oemZxEdslPortMirror                PortList,
          oemZxEdslPortBandwidthIn           Integer32,
          oemZxEdslPortBandwidthOut          Integer32, -- only support in 9426.
          oemZxEdslPortQosPriority           Integer32, -- 2 queue .
          oemZxEdslPortVlanProtect           INTEGER, -- ony support in 9426.
          oemZxEdslPortBroadLimit            Integer32, -- only support in 9426.
          oemZxEdslPortMirrorOut             PortList, -- delete !!!
          oemZxEdslPortMcastLimit            Integer32,
          oemZxEdslClearStatsInfo            Integer32,
          oemZxEdslMinuteInOctets            Counter32,
          oemZxEdslMinuteOutOctets           Counter32,
          oemZxEdslMinuteInPackets           Counter32,
          oemZxEdslMinuteOutPackets          Counter32,
          oemZxEdslMinuteInBitRate           Counter32,
          oemZxEdslMinuteOutBitRate          Counter32,
          oemZxEdslPortMaxMacLearn           Integer32, 
          oemZxEdslPortFlowControlStatus     Integer32,  
          oemZxEdslPortFlowControlConfig     Integer32,
          oemZxEdslBroadcastLimitPercent     Integer32   -- added for Indonesia test(2005/04)     
     }
     
     oemZxEdslPortIndex            OBJECT-TYPE
          SYNTAX         Integer32
          MAX-ACCESS     not-accessible
          STATUS         current
          DESCRIPTION
              "The port No."
          ::= { oemZxEdslPortEntry 1}
          
     oemZxEdslPortMirror           OBJECT-TYPE
          SYNTAX         PortList
          MAX-ACCESS     read-write
          STATUS         current
          DESCRIPTION
              "The ingress portlist of the mirror port on this port."
          ::= { oemZxEdslPortEntry 2}

     oemZxEdslPortBandwidthIn     OBJECT-TYPE
          SYNTAX         Integer32
          MAX-ACCESS     read-write
          STATUS         current
          DESCRIPTION
              "In-bandwidth on the port ."
          ::= {oemZxEdslPortEntry 3}
          

     oemZxEdslPortBandwidthOut     OBJECT-TYPE
          SYNTAX         Integer32
          MAX-ACCESS     read-write
          STATUS         current
          DESCRIPTION
              "Out-bandwidth on the port ."
          ::= {oemZxEdslPortEntry 4}
          

     oemZxEdslPortQosPriority     OBJECT-TYPE
          SYNTAX         Integer32
          MAX-ACCESS     read-write
          STATUS         current
          DESCRIPTION
              "Qos priority on the port ."
          ::= {oemZxEdslPortEntry 5}
          
     oemZxEdslPortVlanProtect     OBJECT-TYPE
          SYNTAX         INTEGER{
                            enable(1),
                            disable(2)
                            }
          MAX-ACCESS     read-write
          STATUS         current
          DESCRIPTION
              "isolate the port from other port in same vlan ."
          ::= {oemZxEdslPortEntry 6}

     oemZxEdslPortBroadLimit     OBJECT-TYPE
          SYNTAX         Integer32
          MAX-ACCESS     read-write
          STATUS         current
          DESCRIPTION
              "Broadcast limit on the port ."
          ::= {oemZxEdslPortEntry 7}

     oemZxEdslPortMirrorOut           OBJECT-TYPE
          SYNTAX         PortList
          MAX-ACCESS     read-write
          STATUS         current
          DESCRIPTION
              "The egress portlist of the mirror port on this port."
          ::= { oemZxEdslPortEntry 8}

     oemZxEdslPortMcastLimit     OBJECT-TYPE
          SYNTAX         Integer32
          MAX-ACCESS     read-write
          STATUS         current
          DESCRIPTION
              "Multicast limit on the port ."
          ::= {oemZxEdslPortEntry 9}

     oemZxEdslClearStatsInfo     OBJECT-TYPE
          SYNTAX         Integer32
          MAX-ACCESS     read-write
          STATUS         current
          DESCRIPTION
              "Clear the statistics data of one port in last five minutes ."
          ::= {oemZxEdslPortEntry 10}

     oemZxEdslMinuteInOctets     OBJECT-TYPE
          SYNTAX         Counter32
          MAX-ACCESS     read-only
          STATUS         current
          DESCRIPTION
              "Show the in octets data of one port in the last minute ."
          ::= {oemZxEdslPortEntry 11}

     oemZxEdslMinuteOutOctets     OBJECT-TYPE
          SYNTAX         Counter32
          MAX-ACCESS     read-only
          STATUS         current
          DESCRIPTION
              "Show the out octets data of one port in the last minute ."
          ::= {oemZxEdslPortEntry 12}

     oemZxEdslMinuteInPackets     OBJECT-TYPE
          SYNTAX         Counter32
          MAX-ACCESS     read-only
          STATUS         current
          DESCRIPTION
              "Show the in packets data of one port in the last minute ."
          ::= {oemZxEdslPortEntry 13}

     oemZxEdslMinuteOutPackets     OBJECT-TYPE
          SYNTAX         Counter32
          MAX-ACCESS     read-only
          STATUS         current
          DESCRIPTION
              "Show the out packets data of one port in the last minute ."
          ::= {oemZxEdslPortEntry 14}

     oemZxEdslMinuteInBitRate     OBJECT-TYPE
          SYNTAX         Counter32
          MAX-ACCESS     read-only
          STATUS         current
          DESCRIPTION
              "Show the in bit rates data of one port in the last minute ."
          ::= {oemZxEdslPortEntry 15}

     oemZxEdslMinuteOutBitRate     OBJECT-TYPE
          SYNTAX         Counter32
          MAX-ACCESS     read-only
          STATUS         current
          DESCRIPTION
              "Show the out bit rates data of one port in the last minute ."
          ::= {oemZxEdslPortEntry 16}

     oemZxEdslPortMaxMacLearn           OBJECT-TYPE
          SYNTAX         Integer32
          MAX-ACCESS     read-write
          STATUS         current
          DESCRIPTION
              "The max mac address is learned on this port."
          ::= { oemZxEdslPortEntry 17}

     oemZxEdslPortFlowControlStatus           OBJECT-TYPE
          SYNTAX         Integer32
          MAX-ACCESS     read-write
          STATUS         current
          DESCRIPTION
              "status of flowcontrol
               1: auto flow control enable, 2: force flow control enable.
               3: auto flow control  disable, 4: force flow control disable."
          ::= { oemZxEdslPortEntry 18}

     oemZxEdslPortFlowControlConfig           OBJECT-TYPE
          SYNTAX         Integer32
          MAX-ACCESS     read-write
          STATUS         current
          DESCRIPTION
              "config value of flowcontrol
               1: auto flow control enable, 2: force flow control enable.
               3: auto flow control  disable, 4: force flow control disable."
          ::= { oemZxEdslPortEntry 19}

     oemZxEdslBroadcastLimitPercent           OBJECT-TYPE
          SYNTAX         Integer32
          MAX-ACCESS     read-write
          STATUS         current
          DESCRIPTION
              "the percent of broadcast limit on GigaByte Ethernet port"
          ::= { oemZxEdslPortEntry 20}

------------------------------------------------------------------------------
------------------------------------------------------------------------------

     oemZxEdslBroadLimitOnIpTable         OBJECT-TYPE
          SYNTAX         SEQUENCE OF OemZxEdslBroadLimitOnIpEntry
          MAX-ACCESS     not-accessible
          STATUS         current
          DESCRIPTION
              "The broad limit table base on IP. Bandwidth limit reserved!!!"
          ::= { oemZxEdslService 5 }

     oemZxEdslBroadLimitOnIpEntry         OBJECT-TYPE
          SYNTAX         OemZxEdslBroadLimitOnIpEntry
          MAX-ACCESS     not-accessible
          STATUS         current
          DESCRIPTION
              "An entry in broadlimit table."
          INDEX  {oemZxEdslBroadLimitOnIpAddress}
          ::= { oemZxEdslBroadLimitOnIpTable  1}

     OemZxEdslBroadLimitOnIpEntry    ::= SEQUENCE  {
          oemZxEdslBroadLimitOnIpAddress   IpAddress,
          oemZxEdslBroadLimitOnIpLimit     Integer32
     }
     
     oemZxEdslBroadLimitOnIpAddress            OBJECT-TYPE
          SYNTAX         IpAddress
          MAX-ACCESS     not-accessible
          STATUS         current
          DESCRIPTION
              "The port No."
          ::= { oemZxEdslBroadLimitOnIpEntry 1}
          
     oemZxEdslBroadLimitOnIpLimit     OBJECT-TYPE
          SYNTAX         Integer32
          MAX-ACCESS     read-write
          STATUS         current
          DESCRIPTION
              "Broadcast limit on the IP ."
          ::= {oemZxEdslBroadLimitOnIpEntry 2}

     oemZxEdslBroadLimitOnVlanTable         OBJECT-TYPE
          SYNTAX         SEQUENCE OF OemZxEdslBroadLimitOnVlanEntry
          MAX-ACCESS     not-accessible
          STATUS         current
          DESCRIPTION
              "The broad limit table base on Vlan. reserved!!!!."
          ::= { oemZxEdslService 6 }

     oemZxEdslBroadLimitOnVlanEntry         OBJECT-TYPE
          SYNTAX         OemZxEdslBroadLimitOnVlanEntry
          MAX-ACCESS     not-accessible
          STATUS         current
          DESCRIPTION
              "An entry in broadlimit table."
          INDEX  {oemZxEdslBroadLimitOnVlanAddress}
          ::= { oemZxEdslBroadLimitOnVlanTable  1}

     OemZxEdslBroadLimitOnVlanEntry    ::= SEQUENCE  {
          oemZxEdslBroadLimitOnVlanAddress   INTEGER,
          oemZxEdslBroadLimitOnVlanLimit     Integer32
     }
     
     oemZxEdslBroadLimitOnVlanAddress            OBJECT-TYPE
          SYNTAX         INTEGER(1..4094)
          MAX-ACCESS     not-accessible
          STATUS         current
          DESCRIPTION
              "The Vlan Id."
          ::= { oemZxEdslBroadLimitOnVlanEntry 1}
          
     oemZxEdslBroadLimitOnVlanLimit     OBJECT-TYPE
          SYNTAX         Integer32
          MAX-ACCESS     read-write
          STATUS         current
          DESCRIPTION
              "Broadcast limit on the Vlan ."
          ::= {oemZxEdslBroadLimitOnVlanEntry 2}

     oemZxEdslPriorityOnPortVlanTable         OBJECT-TYPE
          SYNTAX         SEQUENCE OF OemZxEdslPriorityOnPortVlanEntry
          MAX-ACCESS     not-accessible
          STATUS         current
          DESCRIPTION
              "The priority on port and Vlan. ."
          ::= { oemZxEdslService 7 }

     oemZxEdslPriorityOnPortVlanEntry         OBJECT-TYPE
          SYNTAX         OemZxEdslPriorityOnPortVlanEntry
          MAX-ACCESS     not-accessible
          STATUS         current
          DESCRIPTION
              "An entry in priority table."
          INDEX  {oemZxEdslPriorityVlan,oemZxEdslPriorityPort}
          ::= { oemZxEdslPriorityOnPortVlanTable  1}

     OemZxEdslPriorityOnPortVlanEntry    ::= SEQUENCE  {
          oemZxEdslPriorityVlan         Integer32,
          oemZxEdslPriorityPort         Integer32,
          oemZxEdslPriorityPriority     Integer32
     }
     
     oemZxEdslPriorityVlan            OBJECT-TYPE
          SYNTAX         Integer32
          MAX-ACCESS     not-accessible
          STATUS         current
          DESCRIPTION
              "The vlan id."
          ::= { oemZxEdslPriorityOnPortVlanEntry 1}

     oemZxEdslPriorityPort            OBJECT-TYPE
          SYNTAX         Integer32
          MAX-ACCESS     not-accessible
          STATUS         current
          DESCRIPTION
              "The device port."
          ::= { oemZxEdslPriorityOnPortVlanEntry 2}
          

     oemZxEdslPriorityPriority            OBJECT-TYPE
          SYNTAX         Integer32
          MAX-ACCESS     read-write
          STATUS         current
          DESCRIPTION
              "The priority on the port and vlan. value is 0-7 in 9426."
          ::= { oemZxEdslPriorityOnPortVlanEntry 3}
          
------------------------------------------------------------------------------

     oemZxedslSuperVlanTable              OBJECT-TYPE
          SYNTAX         SEQUENCE OF OemZxEdslSuperVlanEntry
          MAX-ACCESS     not-accessible
          STATUS         current
          DESCRIPTION
              "the table is to indicate the information of super vlans of the
               device "
          ::= { oemZxEdslService 8 }

     oemZxEdslSuperVlanEntry         OBJECT-TYPE
          SYNTAX         OemZxEdslSuperVlanEntry
          MAX-ACCESS     not-accessible
          STATUS         current
          DESCRIPTION
              "An entry in super vlan information table."
          INDEX  {oemZxEdslSuperVlanID}
          ::= { oemZxedslSuperVlanTable  1}

     OemZxEdslSuperVlanEntry    ::= SEQUENCE  {
          oemZxEdslSuperVlanID            INTEGER,
          oemZxEdslSuperVlanName          DisplayString,
          oemZxEdslSuperVlanIPaddress     IpAddress,
          oemZxEdslSuperVlanNetMask       IpAddress,
          oemZxEdslProxyArpStatus         INTEGER,
          oemZxEdslSubVlanList            Vlanlist,
          oemZxEdslSuperVlanRowStatus     RowStatus
     }

     oemZxEdslSuperVlanID            OBJECT-TYPE
          SYNTAX         INTEGER(1..4094)
          MAX-ACCESS     not-accessible
          STATUS         current
          DESCRIPTION
              "The super Vlan Id."
          ::= { oemZxEdslSuperVlanEntry 1}
    
    oemZxEdslSuperVlanName            OBJECT-TYPE
          SYNTAX      DisplayString (SIZE (0..32))
          MAX-ACCESS  read-create
          STATUS      current
          DESCRIPTION
              "the string is the super vlan's name "
          ::= { oemZxEdslSuperVlanEntry 2}        

    oemZxEdslSuperVlanIPaddress      OBJECT-TYPE
          SYNTAX     IpAddress
          MAX-ACCESS read-only
          STATUS current
          DESCRIPTION
              "every super vlan should be allocated one ip address and 
               the ipaddrss is the gateway of all hosts in this super vlan"
          ::= { oemZxEdslSuperVlanEntry 3}        

    oemZxEdslSuperVlanNetMask        OBJECT-TYPE
          SYNTAX     IpAddress
          MAX-ACCESS read-only
          STATUS current
          DESCRIPTION
              "every super vlan should be allocated one sub-netmask "
          ::= { oemZxEdslSuperVlanEntry 4}
        
    oemZxEdslProxyArpStatus          OBJECT-TYPE
        SYNTAX INTEGER{
                        enable(1),
                        disable(2)
                        }
          MAX-ACCESS  read-create
          STATUS      current
          DESCRIPTION
              " we can disable or enable the proxy arp status of every super vlan  "
          ::= { oemZxEdslSuperVlanEntry 5}

    oemZxEdslSubVlanList            OBJECT-TYPE
          SYNTAX      Vlanlist(SIZE(512))
          MAX-ACCESS  read-create
          STATUS      current
          DESCRIPTION
              "we can use every bit of vlanlist to indicate the status of
               sub-vlan, if the bit is 1 which means the sub-vlan is belonged to
               the supervlan and if the bit is 0 which means the sub-vlan is not
               belonged to the supervlan"
          ::= { oemZxEdslSuperVlanEntry 6}

     oemZxEdslSuperVlanRowStatus     OBJECT-TYPE
          SYNTAX         RowStatus
          MAX-ACCESS     read-create
          STATUS         current
          DESCRIPTION
              "This object is used to create, delete or modify a row in this
               table."
          ::= {oemZxEdslSuperVlanEntry 7}

-----------------------------------------------------------------------------

     oemZxEdslUtilizationTable         OBJECT-TYPE
          SYNTAX         SEQUENCE OF OemZxEdslUtilizationEntry
          MAX-ACCESS     not-accessible
          STATUS         current
          DESCRIPTION
              "The port setting  table."
          ::= { oemZxEdslService 9 }

     oemZxEdslUtilizationEntry         OBJECT-TYPE
          SYNTAX         OemZxEdslUtilizationEntry
          MAX-ACCESS     not-accessible
          STATUS         current
          DESCRIPTION
              "An entry in the Ip lock table."
          INDEX  {oemZxEdslUtilizationIndex}
          ::= { oemZxEdslUtilizationTable  1}

     OemZxEdslUtilizationEntry    ::= SEQUENCE  {
          oemZxEdslUtilizationIndex              Integer32,
          oemZxEdslUtilizationTotal              Integer32,
          oemZxEdslUtilizationUsed               Integer32,
          oemZxEdslUtilizationFree               Integer32
     }
     
     oemZxEdslUtilizationIndex            OBJECT-TYPE
          SYNTAX         Integer32
          MAX-ACCESS     not-accessible
          STATUS         current
          DESCRIPTION
              "1 - CPU Utilization; 2 - Memory Utilization; 
               3 - Main version Flash Utilization; 4 - Slave version Flash
                   Utilization;
               5 - configure data  Flash Utilization; 6 - durable configure data
                   Flash Utilization."
          ::= { oemZxEdslUtilizationEntry 1}
          
     oemZxEdslUtilizationTotal           OBJECT-TYPE
          SYNTAX         Integer32
          MAX-ACCESS     read-only
          STATUS         current
          DESCRIPTION
              "Total resource ."
          ::= { oemZxEdslUtilizationEntry 2}

     oemZxEdslUtilizationUsed           OBJECT-TYPE
          SYNTAX         Integer32
          MAX-ACCESS     read-only
          STATUS         current
          DESCRIPTION
              "used resource ."
          ::= { oemZxEdslUtilizationEntry 3}

     oemZxEdslUtilizationFree           OBJECT-TYPE
          SYNTAX         Integer32
          MAX-ACCESS     read-only
          STATUS         current
          DESCRIPTION
              "free resource."
          ::= { oemZxEdslUtilizationEntry 4}
-- ---------------------------------------------------------------------------
     oemZxEdslIgmpsnoopListTable         OBJECT-TYPE
          SYNTAX         SEQUENCE OF OemZxEdslIgmpsnoopListEntry
          MAX-ACCESS     not-accessible
          STATUS         current
          DESCRIPTION
              "configurations of controlled multicast list about Igmpsnoop protocol."
          ::= { oemZxEdslService 10 }

     oemZxEdslIgmpsnoopListEntry         OBJECT-TYPE
          SYNTAX         OemZxEdslIgmpsnoopListEntry
          MAX-ACCESS     not-accessible
          STATUS         current
          DESCRIPTION
              "An entry of configuration table."
          INDEX  {oemZxEdslIgmpsnoopListIndex,oemZxEdslIgmpsnoopFromaddress,oemZxEdslIgmpsnoopToaddress,oemZxedslIgmpsnoopMethod}
          ::= { oemZxEdslIgmpsnoopListTable  1}

     OemZxEdslIgmpsnoopListEntry    ::= SEQUENCE  {
          oemZxEdslIgmpsnoopListIndex           Integer32,
          oemZxEdslIgmpsnoopFromaddress         IpAddress,
          oemZxEdslIgmpsnoopToaddress           IpAddress, 
          oemZxedslIgmpsnoopMethod              Integer32, 
          oemZxedslIgmpsnoopRowstatus           RowStatus
     }
     
     oemZxEdslIgmpsnoopListIndex            OBJECT-TYPE
          SYNTAX         Integer32
          MAX-ACCESS     not-accessible
          STATUS         current
          DESCRIPTION
              "The port No. 1-728"
          ::= { oemZxEdslIgmpsnoopListEntry 1}
          
     oemZxEdslIgmpsnoopFromaddress            OBJECT-TYPE
          SYNTAX         IpAddress
          MAX-ACCESS     not-accessible
          STATUS         current
          DESCRIPTION
              "The source IPaddress of one controlled multicast list ."
          ::= { oemZxEdslIgmpsnoopListEntry 2}
          
     oemZxEdslIgmpsnoopToaddress            OBJECT-TYPE
          SYNTAX         IpAddress
          MAX-ACCESS     not-accessible
          STATUS         current
          DESCRIPTION
              "The destination IPaddress of one controlled multicast list."
          ::= { oemZxEdslIgmpsnoopListEntry 3}
          
     oemZxedslIgmpsnoopMethod            OBJECT-TYPE
          SYNTAX         Integer32
          MAX-ACCESS     not-accessible
          STATUS         current
          DESCRIPTION
              "The permit/deny status."
          ::= { oemZxEdslIgmpsnoopListEntry 4}
          
     oemZxedslIgmpsnoopRowstatus            OBJECT-TYPE
          SYNTAX         RowStatus
          MAX-ACCESS     read-create
          STATUS         current
          DESCRIPTION
              "DURABLE:
               This object indicates the status of this entry.  A row in this
               table must be created using the createAndWait(5) action state
               (i.e., createAndGo(4) is not supported).  This object can only
               be set to active(1) after all objects for this row are valid.
               The 'tmsL3IpSubnetName' is optional.
               
               Note that the notInService(2) state is not supported.  Objects
               in this table row can be changed when this object is notReady(3)
               or active(1)."
          ::= { oemZxEdslIgmpsnoopListEntry 5}

-----------------------------------------------------------------------------
-----------------------------------------------------------------------------
     oemZxEdslIgmpsnoopPortTable         OBJECT-TYPE
          SYNTAX         SEQUENCE OF OemZxEdslIgmpsnoopPortEntry
          MAX-ACCESS     not-accessible
          STATUS         current
          DESCRIPTION
              "configurations of port about Igmpsnoop protocol."
          ::= { oemZxEdslService 11 }

     oemZxEdslIgmpsnoopPortEntry         OBJECT-TYPE
          SYNTAX         OemZxEdslIgmpsnoopPortEntry
          MAX-ACCESS     not-accessible
          STATUS         current
          DESCRIPTION
              "An entry of configuration table."
          INDEX  {oemZxEdslIgmpsnoopPortIndex}
          ::= { oemZxEdslIgmpsnoopPortTable  1}

     OemZxEdslIgmpsnoopPortEntry    ::= SEQUENCE  {
          oemZxEdslIgmpsnoopPortIndex         Integer32,
          oemZxedslIgmpsnoopMaxpermit         Integer32,
          oemZxedslIgmpsnoopEnable            Integer32, 
          oemZxedslIgmpsnoopPortInfo          DisplayString,
          oemZxedslIgmpsnoopFastLeave         Integer32
     }
     
     oemZxEdslIgmpsnoopPortIndex            OBJECT-TYPE
          SYNTAX         Integer32
          MAX-ACCESS     not-accessible
          STATUS         current
          DESCRIPTION
              "The port No. 1-728"
          ::= { oemZxEdslIgmpsnoopPortEntry 1}
          
     oemZxedslIgmpsnoopMaxpermit            OBJECT-TYPE
          SYNTAX         Integer32
          MAX-ACCESS     read-write
          STATUS         current
          DESCRIPTION
              "The maximum permitted number of the controlled multicast list
               about this port ."
          ::= { oemZxEdslIgmpsnoopPortEntry 2}
          
     oemZxedslIgmpsnoopEnable            OBJECT-TYPE
          SYNTAX         Integer32
          MAX-ACCESS     read-write
          STATUS         current
          DESCRIPTION
              "Enable/disable status."
          ::= { oemZxEdslIgmpsnoopPortEntry 3}

     oemZxedslIgmpsnoopPortInfo            OBJECT-TYPE
          SYNTAX         DisplayString
          MAX-ACCESS     read-only
          STATUS         current
          DESCRIPTION
              "the controlled-multicast information about this port."
          ::= { oemZxEdslIgmpsnoopPortEntry 4}

     oemZxedslIgmpsnoopFastLeave            OBJECT-TYPE
          SYNTAX         Integer32
          MAX-ACCESS     read-write
          STATUS         current
          DESCRIPTION
              "the status of fast-leave property."
          ::= { oemZxEdslIgmpsnoopPortEntry 5}

------------------------------------------------------------------------------

    oemZxedslNMSAclEnable   OBJECT-TYPE
        SYNTAX     INTEGER(1..2) 
        MAX-ACCESS read-write
        STATUS     current
        DESCRIPTION
            "the vbas status of portlist."
        ::= { oemZxEdslService 12}

------------------------------------------------------------------------------
    oemZxedslNMSAclLastDiscardIPAddr   OBJECT-TYPE
        SYNTAX     IpAddress 
        MAX-ACCESS read-only
        STATUS     current
        DESCRIPTION
            "the vbas status of portlist."
        ::= { oemZxEdslService 13}
          
------------------------------------------------------------------------------
    oemZxedslNMSAclDiscardPacketCount   OBJECT-TYPE
        SYNTAX     Integer32 
        MAX-ACCESS read-only
        STATUS     current
        DESCRIPTION
            "the vbas status of portlist."
        ::= { oemZxEdslService 14}

------------------------------------------------------------------------------
     oemZxEdslNMSAclTable         OBJECT-TYPE
          SYNTAX         SEQUENCE OF OemZxEdslNMSAclEntry
          MAX-ACCESS     not-accessible
          STATUS         current
          DESCRIPTION
              "The Acl table for Network-Manage-System."
          ::= { oemZxEdslService 15 }

     oemZxEdslNMSAclEntry         OBJECT-TYPE
          SYNTAX         OemZxEdslNMSAclEntry
          MAX-ACCESS     not-accessible
          STATUS         current
          DESCRIPTION
              "An entry of configuration table."
          INDEX  {oemZxEdslNMSAclIndex}
          ::= { oemZxEdslNMSAclTable  1}

     OemZxEdslNMSAclEntry    ::= SEQUENCE  {
          oemZxEdslNMSAclIndex             Integer32,
          oemZxEdslNMSAclSrcIp             IpAddress,
          oemZxEdslNMSAclSrcMask           IpAddress,  
          oemZxEdslNMSAclProtocol          Integer32,
          oemZxEdslNMSAclStartPort         Integer32,
          oemZxEdslNMSAclEndPort           Integer32,
          oemZxEdslNMSAclRowStatus         RowStatus,
          oemZxEdslNMSAclCounter           Integer32
     }
     
     oemZxEdslNMSAclIndex             OBJECT-TYPE
          SYNTAX         Integer32
          MAX-ACCESS     not-accessible
          STATUS         current
          DESCRIPTION
              "index of the acl table."
          ::= { oemZxEdslNMSAclEntry 1}

     oemZxEdslNMSAclSrcIp             OBJECT-TYPE
          SYNTAX         IpAddress
          MAX-ACCESS     read-write
          STATUS         current
          DESCRIPTION
              "source Ip."
          ::= { oemZxEdslNMSAclEntry 2}

     oemZxEdslNMSAclSrcMask             OBJECT-TYPE
          SYNTAX         IpAddress
          MAX-ACCESS     read-write
          STATUS         current
          DESCRIPTION
              "source Ip Mask."
          ::= { oemZxEdslNMSAclEntry 3}

     oemZxEdslNMSAclProtocol             OBJECT-TYPE
          SYNTAX         Integer32
          MAX-ACCESS     read-write
          STATUS         current
          DESCRIPTION
              "Protocol type."
          ::= { oemZxEdslNMSAclEntry 4}

     oemZxEdslNMSAclStartPort             OBJECT-TYPE
          SYNTAX         Integer32
          MAX-ACCESS     read-write
          STATUS         current
          DESCRIPTION
              "Protocol start port number."
          ::= { oemZxEdslNMSAclEntry 5}

     oemZxEdslNMSAclEndPort             OBJECT-TYPE
          SYNTAX         Integer32
          MAX-ACCESS     read-write
          STATUS         current
          DESCRIPTION
              "Protocol end port number."
          ::= { oemZxEdslNMSAclEntry 6}

     oemZxEdslNMSAclRowStatus     OBJECT-TYPE
          SYNTAX         RowStatus
          MAX-ACCESS     read-create
          STATUS         current
          DESCRIPTION
              "This object is used to create, delete or modify a row in this
               table."
          ::= {oemZxEdslNMSAclEntry 7}
          
     oemZxEdslNMSAclCounter            OBJECT-TYPE
          SYNTAX         Integer32
          MAX-ACCESS     read-only
          STATUS         current
          DESCRIPTION
              ""
          ::= { oemZxEdslNMSAclEntry 8}

------------------------------------------------------------------------------
     oemZxEdslPvlanTable         OBJECT-TYPE
          SYNTAX         SEQUENCE OF OemZxEdslPvlanEntry
          MAX-ACCESS     not-accessible
          STATUS         current
          DESCRIPTION
              ""
          ::= { oemZxEdslService 16 }

     oemZxEdslPvlanEntry         OBJECT-TYPE
          SYNTAX         OemZxEdslPvlanEntry
          MAX-ACCESS     not-accessible
          STATUS         current
          DESCRIPTION
              "An entry of configuration table."
          INDEX  {oemZxEdslPvlanPortIndex}
          ::= { oemZxEdslPvlanTable  1}

     OemZxEdslPvlanEntry    ::= SEQUENCE  {
          oemZxEdslPvlanPortIndex             Integer32,
          oemZxedslPvlanisOrnotUplink         INTEGER
     }
     
     oemZxEdslPvlanPortIndex            OBJECT-TYPE
          SYNTAX         Integer32
          MAX-ACCESS     not-accessible
          STATUS         current
          DESCRIPTION
              "The port No. 1-728"
          ::= { oemZxEdslPvlanEntry 1}
          
     oemZxedslPvlanisOrnotUplink            OBJECT-TYPE
          SYNTAX         INTEGER(1..2)
          MAX-ACCESS     read-write
          STATUS         current
          DESCRIPTION
              "in the function of pvlan,whether this uplink port can be set to
               trunking mode."
          ::= { oemZxEdslPvlanEntry 2}

------------------------------------------------------------------------------
    oemZxedslpvlanType   OBJECT-TYPE
        SYNTAX INTEGER(1..4) 
        MAX-ACCESS read-write
        STATUS current
        DESCRIPTION
            "."
        ::= { oemZxEdslService 17}

------------------------------------------------------------------------------
    oemZxedslpvlanStatus   OBJECT-TYPE
        SYNTAX INTEGER(1..2) 
        MAX-ACCESS read-write
        STATUS current
        DESCRIPTION
            "the vbas status of portlist."
        ::= { oemZxEdslService 18}

-- ----------------------------------------------------------------------------
------------------------------------------------------------------------------
     oemZxEdslPvlanTrunkingTable         OBJECT-TYPE
          SYNTAX         SEQUENCE OF OemZxEdslPvlanTrunkingEntry
          MAX-ACCESS     not-accessible
          STATUS         current
          DESCRIPTION
              " "
          ::= { oemZxEdslService 19 }

     oemZxEdslPvlanTrunkingEntry         OBJECT-TYPE
          SYNTAX         OemZxEdslPvlanTrunkingEntry
          MAX-ACCESS     not-accessible
          STATUS         current
          DESCRIPTION
              "An entry of configuration table."
          INDEX  {oemZxEdslPvlanCardIndex}
          ::= { oemZxEdslPvlanTrunkingTable  1}

     OemZxEdslPvlanTrunkingEntry    ::= SEQUENCE  {
          oemZxEdslPvlanCardIndex               Integer32,
          oemZxedslPvlanisOrnotTrunking         INTEGER
     }
     
     oemZxEdslPvlanCardIndex            OBJECT-TYPE
          SYNTAX         Integer32
          MAX-ACCESS     not-accessible
          STATUS         current
          DESCRIPTION
              "The port No. 1-16"
          ::= { oemZxEdslPvlanTrunkingEntry 1}
          
     oemZxedslPvlanisOrnotTrunking            OBJECT-TYPE
          SYNTAX         INTEGER(1..2)
          MAX-ACCESS     read-write
          STATUS         current
          DESCRIPTION
              "whether need trunking or not ."
          ::= { oemZxEdslPvlanTrunkingEntry 2}

-- ----------------------------------------------------------------------------

     oemZxEdslVlanExtTable         OBJECT-TYPE
          SYNTAX         SEQUENCE OF OemZxEdslVlanExtEntry
          MAX-ACCESS     not-accessible
          STATUS         current
          DESCRIPTION
              ""
          ::= { oemZxEdslService 20 }

     oemZxEdslVlanExtEntry         OBJECT-TYPE
          SYNTAX         OemZxEdslVlanExtEntry
          MAX-ACCESS     not-accessible
          STATUS         current
          DESCRIPTION
              "An entry of configuration table."
          INDEX  {oemZxEdslVlanExtIndex}
          ::= { oemZxEdslVlanExtTable  1}

     OemZxEdslVlanExtEntry    ::= SEQUENCE  {
          oemZxEdslVlanExtIndex       Integer32,
          oemZxedslVlanExtPVC         INTEGER,
          oemZxedslVlanProtect        INTEGER
     }
     
     oemZxEdslVlanExtIndex            OBJECT-TYPE
          SYNTAX         Integer32
          MAX-ACCESS     not-accessible
          STATUS         current
          DESCRIPTION
              "The vlanid No. "
          ::= { oemZxEdslVlanExtEntry 1}
          
     oemZxedslVlanExtPVC            OBJECT-TYPE
          SYNTAX         INTEGER(1..8)
          MAX-ACCESS     read-write
          STATUS         current
          DESCRIPTION
              "the pvc specified to the vlanid."
          ::= { oemZxEdslVlanExtEntry 2}

     oemZxedslVlanProtect            OBJECT-TYPE
          SYNTAX         INTEGER(1..2)
          MAX-ACCESS     read-write
          STATUS         current
          DESCRIPTION
              "enable/disable protect property of one vlan."
          ::= { oemZxEdslVlanExtEntry 3}

------------------------------------------------------------------------------
    zxDslSvlanMib    OBJECT IDENTIFIER
        ::=  {  oemZxEdslService  21  }
        
    zxDslSvlanObjects    OBJECT IDENTIFIER
        ::=  {  zxDslSvlanMib  1  }
        
    zxDslPortPvcSvlanTable    OBJECT-TYPE
        SYNTAX        SEQUENCE  OF  ZxDslPortPvcSvlanEntry
        MAX-ACCESS    not-accessible
        STATUS        current
        DESCRIPTION    
            "."
        ::=  { zxDslSvlanObjects  5 }

    zxDslPortPvcSvlanEntry    OBJECT-TYPE
        SYNTAX        ZxDslPortPvcSvlanEntry
        MAX-ACCESS    not-accessible
        STATUS        current
        DESCRIPTION
            "An entry in zxDslPortPvcSvlanTable."
        INDEX        {  zxDslPortPvcSvlanLogicalIndex  }
        ::=  { zxDslPortPvcSvlanTable 1 }

    ZxDslPortPvcSvlanEntry  ::=  SEQUENCE {                              
        zxDslPortPvcSvlanLogicalIndex          Unsigned32,
        zxDslPortPvcPsvlanId                   Unsigned32        
        }

    zxDslPortPvcSvlanLogicalIndex    OBJECT-TYPE    
        SYNTAX            Unsigned32
        MAX-ACCESS        not-accessible
        STATUS            current
        DESCRIPTION
            ""
        ::=  {  zxDslPortPvcSvlanEntry  1  }        
        
    zxDslPortPvcPsvlanId    OBJECT-TYPE    
        SYNTAX            Unsigned32
        MAX-ACCESS        read-write
        STATUS            current
        DESCRIPTION
            ""
        ::=  {  zxDslPortPvcSvlanEntry  2  }    

    zxDslSlotSvlanTable    OBJECT-TYPE
        SYNTAX        SEQUENCE  OF  ZxDslSlotSvlanEntry
        MAX-ACCESS    not-accessible
        STATUS        current
        DESCRIPTION
            "."
        ::=  { zxDslSvlanObjects  6 }

    zxDslSlotSvlanEntry    OBJECT-TYPE
        SYNTAX        ZxDslSlotSvlanEntry
        MAX-ACCESS    not-accessible
        STATUS        current
        DESCRIPTION
            "An entry in zxDslSlotSvlanTable."
        INDEX        {  zxDslSlot  }
        ::=  { zxDslSlotSvlanTable 1 }

    ZxDslSlotSvlanEntry  ::=  SEQUENCE {
        zxDslSlot                Integer32,
        zxDslSlotSvlanEnable     Integer32
        }

    zxDslSlot    OBJECT-TYPE    
        SYNTAX            Integer32
        MAX-ACCESS        not-accessible
        STATUS            current
        DESCRIPTION
            "SLOT INDEX"
        ::=  {  zxDslSlotSvlanEntry  1  }
        
    zxDslSlotSvlanEnable    OBJECT-TYPE    
        SYNTAX            Integer32
        MAX-ACCESS        read-write
        STATUS            current
        DESCRIPTION
            ""
        ::=  {  zxDslSlotSvlanEntry  2  }        

------------------------------------------------------------------------------          
          
    zxDslUsrBrgPortVlanTable OBJECT-TYPE
        SYNTAX SEQUENCE OF ZxDslUsrBrgPortVlanEntry
        MAX-ACCESS  not-accessible
        STATUS      current
        DESCRIPTION
            "User side bridge port vlan realation table."
        ::= { oemZxEdslService  22 }

    zxDslUsrBrgPortVlanEntry OBJECT-TYPE
        SYNTAX      ZxDslUsrBrgPortVlanEntry
        MAX-ACCESS  not-accessible
        STATUS      current
        DESCRIPTION
            "User side bridge port vlan realation table."
        INDEX { zxDslUsrBrgPortId }
        ::= { zxDslUsrBrgPortVlanTable 1 }
      
    ZxDslUsrBrgPortVlanEntry ::= SEQUENCE {
      zxDslUsrBrgPortId               Integer32,
      zxDslUsrBrgPortVlanList         DisplayString
    }
    
    zxDslUsrBrgPortId OBJECT-TYPE
        SYNTAX      Integer32
        MAX-ACCESS  not-accessible
        STATUS      current
        DESCRIPTION
            "A unique value for the user side bridge port of a physical port.If
             the bridge port is just a pvc,then this value is pvcId or pvcNo."
        ::= { zxDslUsrBrgPortVlanEntry 1 }

    zxDslUsrBrgPortVlanList OBJECT-TYPE
        SYNTAX      DisplayString  
        MAX-ACCESS  read-only
        STATUS      current
        DESCRIPTION
            "It is a list of vlan which the user side brige port joined.
             The VLANs are seperated by comma, eg. '1,2,1023'."
      ::= { zxDslUsrBrgPortVlanEntry 2 }

-- ----------------------------------------------------------------------------
    oemZxEdslSubvlanBelongstoSupervlan     OBJECT-TYPE
        SYNTAX         Integer32
        MAX-ACCESS     read-write
        STATUS         current
        DESCRIPTION
            "This object is used to indicate which super vlan the sub-vlan belongs to ."
        ::= {oemZxEdslService 99}

------------------------------------------------------------------------------

     oemZxEdslSnmpError     OBJECT-TYPE
         SYNTAX         Integer32
         MAX-ACCESS     read-only
         STATUS         current
         DESCRIPTION
             "This object is used to define an Error after SNMP process."
         ::= {oemZxEdslService 100}
          
     oemZxEdslBroadcastLimit     OBJECT-TYPE
         SYNTAX         Integer32
         MAX-ACCESS     read-write
         STATUS         current
         DESCRIPTION
             " broadcast limit. link-up port receive-packet limit."
         ::= {oemZxEdslService 101}

     oemZxEdslMulticastLimit     OBJECT-TYPE
         SYNTAX         Integer32
         MAX-ACCESS     read-write
         STATUS         current
         DESCRIPTION
             " multicst limit. delete!!!"
         ::= {oemZxEdslService 102}

     oemZxEdslUnknownLimit     OBJECT-TYPE
         SYNTAX         Integer32
         MAX-ACCESS     read-write
         STATUS         current
         DESCRIPTION
             " unkown-dest packet limit. delete!!!"
         ::= {oemZxEdslService 103}

     oemZxEdslPrio2Cos     OBJECT-TYPE
         SYNTAX         OCTET STRING(SIZE(8))
         MAX-ACCESS     read-write
         STATUS         current
         DESCRIPTION
             "array of cos priority according to 0,1,2,3,4,5,6,7 protocol
              priority in receiving-port."
         ::= {oemZxEdslService 104}

     oemZxEdslCosMode     OBJECT-TYPE
         SYNTAX         OCTET STRING(SIZE(4))
         MAX-ACCESS     read-write
         STATUS         current
         DESCRIPTION
             "array of ratio in 4 cos priority."
         ::= {oemZxEdslService 105}

     oemZxEdslError     OBJECT-TYPE
         SYNTAX         Integer32
         MAX-ACCESS     read-only
         STATUS         current
         DESCRIPTION
             "This object is used to define an Error after config process."
         ::= {oemZxEdslService 106}

     oemZxEdslOptionSave     OBJECT-TYPE
         SYNTAX         OCTET STRING(SIZE(100))
         MAX-ACCESS     read-write
         STATUS         current
         DESCRIPTION
             "This object is used to save debug data or other data."
         ::= {oemZxEdslService 107}

     oemZxEdslCos2Prio     OBJECT-TYPE
         SYNTAX         OCTET STRING(SIZE(4))
         MAX-ACCESS     read-write
         STATUS         current
         DESCRIPTION
             "array of protocol priority according to 0,1,2,3 protocol priority in sending-port."
         ::= {oemZxEdslService 108}

     oemZxEdslMirrorPort     OBJECT-TYPE
         SYNTAX         Integer32
         MAX-ACCESS     read-write
         STATUS         current
         DESCRIPTION
             "the port is mirrored on."
         ::= {oemZxEdslService 109}

     oemZxEdslMirrorInSrcPort     OBJECT-TYPE
         SYNTAX         PortList
         MAX-ACCESS     read-write
         STATUS         current
         DESCRIPTION
             "the port is mirrored in flow-in."
         ::= {oemZxEdslService 110}

     oemZxEdslMirrorOutSrcPort     OBJECT-TYPE
         SYNTAX         PortList
         MAX-ACCESS     read-write
         STATUS         current
         DESCRIPTION
             "the port is mirrored in flow-out."
         ::= {oemZxEdslService 111}

     oemZxEdslMacVid2SlotPort      OBJECT-TYPE
         SYNTAX         OCTET STRING(SIZE(0..255))
         MAX-ACCESS     read-write
         STATUS         current
         DESCRIPTION
             "Search slot/port by mac/vid."
         ::= {oemZxEdslService 112}
  
     oemZxEdslFansStatus         OBJECT-TYPE
         SYNTAX         Integer32
         MAX-ACCESS     read-only
         STATUS         current
         DESCRIPTION
             "Status of 9203 device fans' status. use bit 0 to indicates fan
              board status, from bit 1 to MSB, each bit may represent the status
              of different fan, if bit value is 1, it means that the fan(or fan
              board) is OK, 0 means bad. In this version, 6 fans are support,
              bit 1 indicate fan 1"
         ::= { oemZxEdslService 113 }

     oemZxEdslVlanMulticastCapabilityTable         OBJECT-TYPE
         SYNTAX         SEQUENCE OF OemZxEdslVlanMulticastCapabilityEntry
         MAX-ACCESS     not-accessible
         STATUS         current
         DESCRIPTION
             "All Vlan Multicast Capability."
         ::= { oemZxEdslService 114 }

     oemZxEdslVlanMulticastCapabilityEntry         OBJECT-TYPE
         SYNTAX         OemZxEdslVlanMulticastCapabilityEntry
         MAX-ACCESS     not-accessible
         STATUS         current
         DESCRIPTION
             "An entry of configuration table."
         INDEX  {oemZxEdslVlanMulticastCapabilityVid }
         ::= { oemZxEdslVlanMulticastCapabilityTable  1}

     OemZxEdslVlanMulticastCapabilityEntry    ::= SEQUENCE  {
         oemZxEdslVlanMulticastCapabilityVid           Integer32,
         oemZxEdslVlanMulticastCapability              Integer32
     }
     
     oemZxEdslVlanMulticastCapabilityVid            OBJECT-TYPE
         SYNTAX         Integer32
         MAX-ACCESS     not-accessible
         STATUS         current
         DESCRIPTION
             "The Vlan ID."
         ::= { oemZxEdslVlanMulticastCapabilityEntry 1}
          
     oemZxEdslVlanMulticastCapability               OBJECT-TYPE
         SYNTAX         Integer32
         MAX-ACCESS     read-write
         STATUS         current
         DESCRIPTION
             "Vlan Multicast Capability, enable(1) or disable(2)."
         ::= { oemZxEdslVlanMulticastCapabilityEntry 2}       

     oemZxEdslSysPriorityProperty         OBJECT-TYPE
         SYNTAX         Integer32
         MAX-ACCESS     read-write
         STATUS         current
         DESCRIPTION
             "specify the priority process mode: PVC/COS/MIX"
         ::= { oemZxEdslService 115 }     

     oemZxEdslSysPVCPriorityTable         OBJECT-TYPE
         SYNTAX         SEQUENCE OF OemZxEdslSysPVCPriorityEntry
         MAX-ACCESS     not-accessible
         STATUS         current
         DESCRIPTION
             "the configuration information of PVC priority."
         ::= { oemZxEdslService 116 }
          
     oemZxEdslSysPVCPriorityEntry         OBJECT-TYPE
         SYNTAX         OemZxEdslSysPVCPriorityEntry
         MAX-ACCESS     not-accessible
         STATUS         current
         DESCRIPTION
             "An entry of configuration table."
         INDEX  {oemZxEdslSysPVCIndex }
         ::= { oemZxEdslSysPVCPriorityTable  1}

     OemZxEdslSysPVCPriorityEntry    ::= SEQUENCE  {
         oemZxEdslSysPVCIndex          INTEGER,
         oemZxEdslSysPVCPriority       INTEGER
     }
     
     oemZxEdslSysPVCIndex            OBJECT-TYPE
         SYNTAX         INTEGER(0..7)
         MAX-ACCESS     not-accessible
         STATUS         current
         DESCRIPTION
             "The PVC Index."
         ::= { oemZxEdslSysPVCPriorityEntry 1}
          
     oemZxEdslSysPVCPriority               OBJECT-TYPE
         SYNTAX         INTEGER(0..7)
         MAX-ACCESS     read-write
         STATUS         current
         DESCRIPTION
             "The PVC priority value"
         ::= { oemZxEdslSysPVCPriorityEntry 2}
     
     oemZxEdslPortPriorityQueueTable         OBJECT-TYPE
         SYNTAX         SEQUENCE OF OemZxEdslPortPriorityQueueEntry
         MAX-ACCESS     not-accessible
         STATUS         current
         DESCRIPTION
             "the configuration information of port queue."
         ::= { oemZxEdslService 117 }
          
     oemZxEdslPortPriorityQueueEntry         OBJECT-TYPE
         SYNTAX         OemZxEdslPortPriorityQueueEntry
         MAX-ACCESS     not-accessible
         STATUS         current
         DESCRIPTION
             "An entry of configuration table."
         INDEX  {oemZxEdslPortQueueIndex }
         ::= { oemZxEdslPortPriorityQueueTable  1}

     OemZxEdslPortPriorityQueueEntry    ::= SEQUENCE  {
         oemZxEdslPortQueueIndex       INTEGER,
         oemZxEdslPortQueueNum         Integer32,
         oemZxEdslPortQueueWeight      Integer32,
         oemZxEdslPortQueueBufferSize  Integer32
     }
     
     oemZxEdslPortQueueIndex            OBJECT-TYPE
         SYNTAX         INTEGER(0..49)
         MAX-ACCESS     not-accessible
         STATUS         current
         DESCRIPTION
             "The physical port index."
         ::= { oemZxEdslPortPriorityQueueEntry 1}
          
     oemZxEdslPortQueueNum               OBJECT-TYPE
         SYNTAX         Integer32
         MAX-ACCESS     read-write
         STATUS         current
         DESCRIPTION
             "The Quantity of Port Queue"
         ::= { oemZxEdslPortPriorityQueueEntry 2}  
          
     oemZxEdslPortQueueWeight               OBJECT-TYPE
         SYNTAX         Integer32
         MAX-ACCESS     read-write
         STATUS         current
         DESCRIPTION
             "The Weight of Port Queue"
         ::= { oemZxEdslPortPriorityQueueEntry 3}    
     
     
     oemZxEdslPortQueueBufferSize               OBJECT-TYPE
         SYNTAX         Integer32
         MAX-ACCESS     read-write
         STATUS         current
         DESCRIPTION
             "The Size of Port Queue Buffer"
         ::= { oemZxEdslPortPriorityQueueEntry 4} 

     oemZxEdslTrunkingEnable         OBJECT-TYPE
         SYNTAX         Integer32
         MAX-ACCESS     read-write
         STATUS         current
         DESCRIPTION
             "Enable(1)/Diable(2) trunking."
         ::= { oemZxEdslService 118 }

     oemZxEdslCascadeModeTable         OBJECT-TYPE
         SYNTAX         SEQUENCE OF OemZxEdslCascadeModeEntry
         MAX-ACCESS     not-accessible
         STATUS         current
         DESCRIPTION
             "the cascade mode for pvlan."
         ::= { oemZxEdslService 120 }
     
     oemZxEdslCascadeModeEntry         OBJECT-TYPE
         SYNTAX         OemZxEdslCascadeModeEntry
         MAX-ACCESS     not-accessible
         STATUS         current
         DESCRIPTION
             "An entry of cascade mode table."
         INDEX  {oemZxEdslPortIndex }
         ::= { oemZxEdslCascadeModeTable  1}

     OemZxEdslCascadeModeEntry    ::= SEQUENCE  {
          oemZxEdslPortNum            Integer32,
          oemZxEdslCascadeMode        Integer32
     }
     
     oemZxEdslPortNum        OBJECT-TYPE
          SYNTAX         Integer32
          MAX-ACCESS     not-accessible
          STATUS         current
          DESCRIPTION
           "The interface index."
          ::= { oemZxEdslCascadeModeEntry 1}
          
     oemZxEdslCascadeMode    OBJECT-TYPE
          SYNTAX         Integer32
          MAX-ACCESS     read-write
          STATUS         current
          DESCRIPTION
           "The Cascade Mode"
          ::= { oemZxEdslCascadeModeEntry 2}  
     
     
     oemZxEdslSystemTemperature    OBJECT-TYPE
          SYNTAX         Integer32
          MAX-ACCESS     read-only
          STATUS         current
          DESCRIPTION
           "The System Temperature"
          ::= { oemZxEdslService 121} 
          
     oemZxEdslVersionCreateTime    OBJECT-TYPE
         SYNTAX         OCTET STRING
         MAX-ACCESS     read-only
         STATUS         current
         DESCRIPTION
             "The Create Time of the current version"
         ::= { oemZxEdslService 122}      
        
     oemZxEdslLinkHistoryTable         OBJECT-TYPE
         SYNTAX         SEQUENCE OF OemZxEdslLinkHistoryEntry
         MAX-ACCESS     not-accessible
         STATUS         current
         DESCRIPTION
             "the link up/down history."
         ::= { oemZxEdslService 123 }

     oemZxEdslLinkHistoryEntry         OBJECT-TYPE
         SYNTAX         OemZxEdslLinkHistoryEntry
         MAX-ACCESS     not-accessible
         STATUS         current
         DESCRIPTION
             "An entry of link history table."
         INDEX  {oemZxEdslRecordIndex }
         ::= { oemZxEdslLinkHistoryTable  1}

     OemZxEdslLinkHistoryEntry    ::= SEQUENCE  {
         oemZxEdslRecordIndex     Integer32,
         oemZxEdslLinkTime        OCTET STRING,
         oemZxEdslLinkPort        Integer32,
         oemZxEdslLinkStatus      Integer32
     }
     
     oemZxEdslRecordIndex    OBJECT-TYPE
         SYNTAX         Integer32
         MAX-ACCESS     not-accessible
         STATUS         current
         DESCRIPTION
             "the record index"
         ::= { oemZxEdslLinkHistoryEntry 1}
     
     oemZxEdslLinkTime    OBJECT-TYPE
         SYNTAX         OCTET STRING
         MAX-ACCESS     read-only
         STATUS         current
         DESCRIPTION
             "the time of the link up/down event"
         ::= { oemZxEdslLinkHistoryEntry 2}                   

     oemZxEdslLinkPort    OBJECT-TYPE
         SYNTAX         Integer32
         MAX-ACCESS     read-only
         STATUS         current
         DESCRIPTION
             "The link up/down port"
         ::= { oemZxEdslLinkHistoryEntry 3}                   

     oemZxEdslLinkStatus    OBJECT-TYPE
         SYNTAX         Integer32
         MAX-ACCESS     read-only
         STATUS         current
         DESCRIPTION
             "the link up/down status, 1 for up, 2 for down"
         ::= { oemZxEdslLinkHistoryEntry 4}                   

     oemZxEdslThreshSystemTemperature         OBJECT-TYPE
         SYNTAX         Integer32
         MAX-ACCESS     read-write
         STATUS         current
         DESCRIPTION
             "the system temperature threshold."
         ::= { oemZxEdslService 124 }

     oemZxEdslMemoryUse    OBJECT-TYPE
         SYNTAX        Integer32
         MAX-ACCESS    read-only
         STATUS        current
         DESCRIPTION
             " the memory use rate of specific card(1-100)."
         ::= { oemZxEdslService 129 } 

     oemZxEdslSysPerfTable         OBJECT-TYPE
         SYNTAX         SEQUENCE OF OemZxEdslSysPerfEntry
         MAX-ACCESS     not-accessible
         STATUS         current
         DESCRIPTION
             "system performance info"
         ::= { oemZxEdslService 130 }

     oemZxEdslSysPerfEntry         OBJECT-TYPE
         SYNTAX         OemZxEdslSysPerfEntry
         MAX-ACCESS     not-accessible
         STATUS         current
         DESCRIPTION
             "An entry of system performance table."
         INDEX  {oemZxEdslSlotIndex}
         ::= { oemZxEdslSysPerfTable  1}

     OemZxEdslSysPerfEntry    ::= SEQUENCE  {
         oemZxEdslSlotIndex      Integer32,
         oemZxEdslCPUUse         Integer32
     }
     
     oemZxEdslSlotIndex     OBJECT-TYPE
         SYNTAX        Integer32
         MAX-ACCESS    not-accessible
         STATUS        current
         DESCRIPTION
             " the slot index: 0-14 line card, 15 master SCB "
         ::= { oemZxEdslSysPerfEntry 1 } 
          
     oemZxEdslCPUUse     OBJECT-TYPE
         SYNTAX        Integer32
         MAX-ACCESS    read-only
         STATUS        current
         DESCRIPTION
             " the cpu use rate of specific card"
         ::= { oemZxEdslSysPerfEntry 2 } 

     oemZxEdslQueuingCfgMechanism     OBJECT-TYPE
         SYNTAX         Integer32
         MAX-ACCESS     read-write
         STATUS         current
         DESCRIPTION
             "9210"
         ::= {oemZxEdslService 131}

     oemZxEdsl350Prio2Cos     OBJECT-TYPE
         SYNTAX         OCTET STRING(SIZE(8))
         MAX-ACCESS     read-write
         STATUS         current
         DESCRIPTION
             "array of cos priority according to 0,1,2,3,4,5,6,7 protocol
              priority in receiving-port."
         ::= {oemZxEdslService 132}

     oemZxEdslSysTime         OBJECT-TYPE
         SYNTAX         OCTET STRING
         MAX-ACCESS     read-write
         STATUS         current
         DESCRIPTION
             "system time"
         ::= { oemZxEdslService 133 }

------------------------------------------------------------------------------

     oemZxEdslxDSLRateThreshTable         OBJECT-TYPE
         SYNTAX         SEQUENCE OF OemZxEdslxDSLRateThreshEntry
         MAX-ACCESS     not-accessible
         STATUS         current
         DESCRIPTION
             "xDSL line rate thresh alarm"
         ::= { oemZxEdslService 134 }

     oemZxEdslxDSLRateThreshEntry         OBJECT-TYPE
         SYNTAX         OemZxEdslxDSLRateThreshEntry
         MAX-ACCESS     not-accessible
         STATUS         current
         DESCRIPTION
             "An entry of oemZxEdslxDSLRateThreshTable."
         INDEX  {oemZxEdslRateThreshPortIndex}
         ::= { oemZxEdslxDSLRateThreshTable  1}

     OemZxEdslxDSLRateThreshEntry    ::= SEQUENCE  {
         oemZxEdslRateThreshPortIndex      Integer32,
         oemZxEdslTxRateThresh             Integer32,
         oemZxEdslRxRateThresh             Integer32,
         oemZxEdslRateThreshRowStatus      Integer32
     }
     
     oemZxEdslRateThreshPortIndex    OBJECT-TYPE
         SYNTAX        Integer32
         MAX-ACCESS    not-accessible
         STATUS        current
         DESCRIPTION
             " the port index "
         ::= { oemZxEdslxDSLRateThreshEntry 1 } 
          
     oemZxEdslTxRateThresh     OBJECT-TYPE
         SYNTAX        Integer32
         MAX-ACCESS    read-write
         STATUS        current
         DESCRIPTION
             "the TxRate Thresh value."
         ::= { oemZxEdslxDSLRateThreshEntry 2 }

     oemZxEdslRxRateThresh     OBJECT-TYPE
         SYNTAX        Integer32
         MAX-ACCESS    read-write
         STATUS        current
         DESCRIPTION
             "the RxRate Thresh value."
         ::= { oemZxEdslxDSLRateThreshEntry 3 }

     oemZxEdslRateThreshRowStatus     OBJECT-TYPE
         SYNTAX        Integer32
         MAX-ACCESS    read-write
         STATUS        current
         DESCRIPTION
             " the row status of oemZxEdslxDSLRateThreshEntry."
         ::= { oemZxEdslxDSLRateThreshEntry 4 }
           
-----------------------------
---    ACL Rule    -----
-----------------------------
     oemZxEdslAclRuleTable         OBJECT-TYPE
         SYNTAX         SEQUENCE OF OemZxEdslAclRuleEntry
         MAX-ACCESS     not-accessible
         STATUS         current
         DESCRIPTION
             "The Acl Rule table."
         ::= { oemZxEdslService 135 }

     oemZxEdslAclRuleEntry         OBJECT-TYPE
         SYNTAX         OemZxEdslAclRuleEntry
         MAX-ACCESS     not-accessible
         STATUS         current
         DESCRIPTION
             "An entry in the Acl Rule table."
         INDEX  {oemZxEdslAclRulePortIndex}
         ::= { oemZxEdslAclRuleTable  1}

     OemZxEdslAclRuleEntry    ::= SEQUENCE  {
         oemZxEdslAclRulePortIndex     Integer32,
         oemZxEdslAclRuleAction        Integer32,  
         oemZxEdslAclRuleDir           Integer32,  
         oemZxEdslAclPktType           Integer32,  
         oemZxEdslAclfilterType        Integer32,
         oemZxEdslAclfilterIndex       Integer32,
         oemZxEdslAclRuleRowStatus     RowStatus
     }
     
     oemZxEdslAclRulePortIndex             OBJECT-TYPE
         SYNTAX         Integer32
         MAX-ACCESS     not-accessible
         STATUS         current
         DESCRIPTION
             "port index (for single pvc,this is physical port index; for multiple pvc, this is logical port index)."
         ::= { oemZxEdslAclRuleEntry 1}

     oemZxEdslAclRuleAction             OBJECT-TYPE
         SYNTAX         Integer32
         MAX-ACCESS     read-write
         STATUS         current
         DESCRIPTION
             ""
         ::= { oemZxEdslAclRuleEntry 2}

     oemZxEdslAclRuleDir             OBJECT-TYPE
         SYNTAX         Integer32
         MAX-ACCESS     read-write
         STATUS         current
         DESCRIPTION
             ""
         ::= { oemZxEdslAclRuleEntry 3}

     oemZxEdslAclPktType             OBJECT-TYPE
         SYNTAX         Integer32
         MAX-ACCESS     read-write
         STATUS         current
         DESCRIPTION
             ""
         ::= { oemZxEdslAclRuleEntry 4}

     oemZxEdslAclfilterType             OBJECT-TYPE
         SYNTAX         Integer32
         MAX-ACCESS     read-write
         STATUS         current
         DESCRIPTION
             ""
         ::= { oemZxEdslAclRuleEntry 5}

     oemZxEdslAclfilterIndex             OBJECT-TYPE
         SYNTAX         Integer32
         MAX-ACCESS     read-write
         STATUS         current
         DESCRIPTION
             ""
         ::= { oemZxEdslAclRuleEntry 6}

     oemZxEdslAclRuleRowStatus             OBJECT-TYPE
         SYNTAX         RowStatus
         MAX-ACCESS     read-create
         STATUS         current
         DESCRIPTION
             "Row Status"
         ::= { oemZxEdslAclRuleEntry 7}

-----------------------------
---    ACL IP Filter    -----
-----------------------------

     oemZxEdslAclIPFilterTable         OBJECT-TYPE
         SYNTAX         SEQUENCE OF OemZxEdslAclIPFilterEntry
         MAX-ACCESS     not-accessible
         STATUS         current
         DESCRIPTION
             "The Acl IP Filter table."
         ::= { oemZxEdslService 136 }

     oemZxEdslAclIPFilterEntry         OBJECT-TYPE
         SYNTAX         OemZxEdslAclIPFilterEntry
         MAX-ACCESS     not-accessible
         STATUS         current
         DESCRIPTION
             "An entry in the Acl table."
         INDEX  {oemZxEdslAclIPFilterIndex}
         ::= { oemZxEdslAclIPFilterTable  1}

     OemZxEdslAclIPFilterEntry    ::= SEQUENCE  {
         oemZxEdslAclIPFilterIndex            Integer32,
         oemZxEdslAclIPFilterSrcIpFrom        IpAddress,
         oemZxEdslAclIPFilterSrcIpTo          IpAddress,  
         oemZxEdslAclIPFilterDestIpFrom       IpAddress,  
         oemZxEdslAclIPFilterDestIpTo         IpAddress,  
         oemZxEdslAclIPFilterRowStatus        RowStatus
     }
     
     oemZxEdslAclIPFilterIndex    OBJECT-TYPE
         SYNTAX         Integer32
         MAX-ACCESS     not-accessible
         STATUS         current
         DESCRIPTION
             "filter index."
         ::= { oemZxEdslAclIPFilterEntry 1}

     oemZxEdslAclIPFilterSrcIpFrom    OBJECT-TYPE
         SYNTAX         IpAddress
         MAX-ACCESS     read-write
         STATUS         current
         DESCRIPTION
             "source Ip start range."
         ::= { oemZxEdslAclIPFilterEntry 2}

     oemZxEdslAclIPFilterSrcIpTo    OBJECT-TYPE
         SYNTAX         IpAddress
         MAX-ACCESS     read-write
         STATUS         current
         DESCRIPTION
             "source Ip end range."
         ::= { oemZxEdslAclIPFilterEntry 3}

     oemZxEdslAclIPFilterDestIpFrom    OBJECT-TYPE
         SYNTAX         IpAddress
         MAX-ACCESS     read-write
         STATUS         current
         DESCRIPTION
             "Dest Ip start range."
         ::= { oemZxEdslAclIPFilterEntry 4}

     oemZxEdslAclIPFilterDestIpTo    OBJECT-TYPE
         SYNTAX         IpAddress
         MAX-ACCESS     read-write
         STATUS         current
         DESCRIPTION
             "Dest Ip end range."
         ::= { oemZxEdslAclIPFilterEntry 5}


     oemZxEdslAclIPFilterRowStatus     OBJECT-TYPE
         SYNTAX         RowStatus
         MAX-ACCESS     read-create
         STATUS         current
         DESCRIPTION
              "This object is used to create, delete or modify a row in this
               table."
         ::= {oemZxEdslAclIPFilterEntry 6}
          
          
    --------------------------------------------      
    -- Argentina Dsl ACL rule
    --------------------------------------------
    zxACLConfigTable    OBJECT-TYPE
        SYNTAX        SEQUENCE  OF  zxACLEntry
        MAX-ACCESS    not-accessible
        STATUS        current
        DESCRIPTION    "The (conceptual) table listing all ACL rules."
        ::=  { oemZxEdslService 137 }

    zxACLConfigEntry    OBJECT-TYPE
        SYNTAX        zxACLEntry
        MAX-ACCESS    not-accessible
        STATUS        current
        DESCRIPTION    "An entry (conceptual row) representing an ACL rule."
        INDEX        {  zxACLNumber  }
        ::=  { zxACLConfigTable 1 }

    zxACLEntry  ::=  SEQUENCE {
        zxACLNumber  Integer32,
        zxACLMatch  DisplayString,
        zxACLRowStatus RowStatus
        }


    zxACLNumber    OBJECT-TYPE    
        SYNTAX            Integer32  (1 .. 720) 
        MAX-ACCESS        not-accessible
        STATUS            current
        DESCRIPTION        "the id of rule."
        ::=  {  zxACLConfigEntry  1  }

    zxACLMatch    OBJECT-TYPE    
        SYNTAX            DisplayString  ( SIZE ( 0 .. 255  ) ) 
        MAX-ACCESS        read-create
        STATUS            current
        DESCRIPTION        "The string contains the class's content."
        ::=  {  zxACLConfigEntry  2  }
    
    zxACLRowStatus    OBJECT-TYPE    
        SYNTAX            RowStatus
        MAX-ACCESS        read-create
        STATUS            current
        DESCRIPTION        ""
        ::=  {  zxACLConfigEntry  3  }          
        
        


    --------------------------------------------      
    -- Argentina Dsl port ACL rule config
    --------------------------------------------
    zxACLPortInfoTable    OBJECT-TYPE
        SYNTAX        SEQUENCE  OF  ZxACLPortInfoEntry
        MAX-ACCESS    not-accessible
        STATUS        current
        DESCRIPTION    "The ACL information of one physical port."
        ::=  { oemZxEdslService 138 }

    zxACLPortInfoEntry    OBJECT-TYPE
        SYNTAX        ZxACLPortInfoEntry
        MAX-ACCESS    not-accessible
        STATUS        current
        DESCRIPTION    "An entry (conceptual row) representing QoS information of physical port."
        INDEX        {  zxACLPortIfaceNum }
        ::=  { zxACLPortInfoTable 1 }

    ZxACLPortInfoEntry  ::=  SEQUENCE {
        zxACLPortIfaceNum  Integer32,
        zxACLPortAclNumber Integer32,
        zxACLPortAclAction Integer32
        }


    zxACLPortIfaceNum    OBJECT-TYPE    
        SYNTAX            Integer32  ( 0 .. 728  ) 
        MAX-ACCESS        not-accessible
        STATUS            current
        DESCRIPTION        "The index of the Port ACL information table."
        ::=  {  zxACLPortInfoEntry  1  }
        
    zxACLPortAclNumber    OBJECT-TYPE    
        SYNTAX            Integer32  ( 0 .. 720  ) 
        MAX-ACCESS        read-create
        STATUS            current
        DESCRIPTION        "The ACL rule id of one port ."
        ::=  {  zxACLPortInfoEntry  2  }    
        
    zxACLPortAclAction OBJECT-TYPE    
        SYNTAX            Integer32
        MAX-ACCESS        read-create
        STATUS            current
        DESCRIPTION        ""
        ::=  {  zxACLPortInfoEntry  3  }        

     oemZxEdslStaticMacTable         OBJECT-TYPE
          SYNTAX         SEQUENCE OF OemZxEdslStaticMacEntry
          MAX-ACCESS     not-accessible
          STATUS         current
          DESCRIPTION
           "The static MAC address table."
          ::= { oemZxEdslService 140 }

     oemZxEdslStaticMacEntry         OBJECT-TYPE
          SYNTAX         OemZxEdslStaticMacEntry
          MAX-ACCESS     not-accessible
          STATUS         current
          DESCRIPTION
           "An entry in the static Mac address table."
          INDEX{oemZxEdslStaticMacPort,oemZxEdslStaticMacAddress,oemZxEdslStaticMacVid,oemZxEdslStaticMacTagflag}
          ::= { oemZxEdslStaticMacTable  1}

     OemZxEdslStaticMacEntry    ::= SEQUENCE  {
          oemZxEdslStaticMacPort            Integer32,
          oemZxEdslStaticMacAddress         MacAddress,
          oemZxEdslStaticMacVid             Integer32,
          oemZxEdslStaticMacTagflag         Integer32,
          oemZxEdslStaticMacStatus          Integer32,
          oemZxEdslStaticMacRowStatus       RowStatus
     }
         
     oemZxEdslStaticMacPort            OBJECT-TYPE
          SYNTAX         Integer32
          MAX-ACCESS     not-accessible
          STATUS         current
          DESCRIPTION
           "The port to static MAC table."
          ::= { oemZxEdslStaticMacEntry 1}
          
     oemZxEdslStaticMacAddress             OBJECT-TYPE
          SYNTAX         MacAddress
          MAX-ACCESS     not-accessible
          STATUS         current
          DESCRIPTION
           "The MAC in the static mac table."
          ::= { oemZxEdslStaticMacEntry 2}

     oemZxEdslStaticMacVid            OBJECT-TYPE
          SYNTAX         Integer32
          MAX-ACCESS     not-accessible
          STATUS         current
          DESCRIPTION
           "The Vlan Id."
          ::= { oemZxEdslStaticMacEntry 3}
     
     oemZxEdslStaticMacTagflag            OBJECT-TYPE
          SYNTAX         Integer32
          MAX-ACCESS     not-accessible
          STATUS         current
          DESCRIPTION
           "tag or untag."
          ::= { oemZxEdslStaticMacEntry 4}
          
     oemZxEdslStaticMacStatus            OBJECT-TYPE
          SYNTAX         Integer32
          MAX-ACCESS     not-accessible
          STATUS         current
          DESCRIPTION
           "is or not send to card."
          ::= { oemZxEdslStaticMacEntry 5}
               
     oemZxEdslStaticMacRowStatus     OBJECT-TYPE
          SYNTAX         RowStatus
          MAX-ACCESS     read-create
          STATUS         current
          DESCRIPTION
           "This object is used to create, delete or modify a row in this table."
          ::= {oemZxEdslStaticMacEntry 6}

     oemZxEdslVlanPortModeTable         OBJECT-TYPE
          SYNTAX         SEQUENCE OF OemZxEdslVlanPortModeEntry
          MAX-ACCESS     not-accessible
          STATUS         current
          DESCRIPTION
           "The dsl-mpvc VlanPortMode table."
          ::= { oemZxEdslService 144 }

     oemZxEdslVlanPortModeEntry         OBJECT-TYPE
          SYNTAX         OemZxEdslVlanPortModeEntry
          MAX-ACCESS     not-accessible
          STATUS         current
          DESCRIPTION
           "An entry in the dsl-mpvc VlanPortMode table."
          INDEX {oemZxEdslDslPort}
          ::= { oemZxEdslVlanPortModeTable  1}

     OemZxEdslVlanPortModeEntry    ::= SEQUENCE  {
          oemZxEdslDslPort                    Integer32,
          oemZxEdslVlanPortMode               INTEGER
     }

     
     oemZxEdslDslPort            OBJECT-TYPE
         SYNTAX         Integer32
         MAX-ACCESS     not-accessible
         STATUS         current
         DESCRIPTION
             "The dsl ports id."
         ::= { oemZxEdslVlanPortModeEntry 1}
          
     oemZxEdslVlanPortMode             OBJECT-TYPE
         SYNTAX         INTEGER(1..2)
         MAX-ACCESS     read-write
         STATUS         current
         DESCRIPTION
             "The vlan-port-mode of dsl-mpvc port."
         ::= { oemZxEdslVlanPortModeEntry 2}

     oemZxEdslMacAddressTable         OBJECT-TYPE
         SYNTAX         SEQUENCE OF OemZxEdslMacAddressEntry
         MAX-ACCESS     not-accessible
         STATUS         current
         DESCRIPTION
             "The listing of zxEdsl bridge port mac address table."
         ::= { oemZxEdslService 145 }
          
     oemZxEdslMacAddressEntry         OBJECT-TYPE
         SYNTAX         OemZxEdslMacAddressEntry
         MAX-ACCESS     not-accessible
         STATUS         current
         DESCRIPTION
             "An entry listing of zxEdsl bridge port mac address table."
         INDEX{oemZxEdslUsrBrgPortId}
         ::= { oemZxEdslMacAddressTable  1}
     
     OemZxEdslMacAddressEntry    ::= SEQUENCE  {
         oemZxEdslUsrBrgPortId      Integer32,
         oemZxEdslMacAddressList    OCTET STRING
     }
     
     oemZxEdslUsrBrgPortId OBJECT-TYPE
         SYNTAX      Integer32
         MAX-ACCESS  not-accessible
         STATUS      current
         DESCRIPTION
             "A unique value for the user side bridge port."
         ::= { oemZxEdslMacAddressEntry 1 }
     
     oemZxEdslMacAddressList    OBJECT-TYPE    
         SYNTAX          OCTET STRING (SIZE(0..2048))
         MAX-ACCESS      read-only
         STATUS          current
         DESCRIPTION        
             "
              The MAC address list of current bridge port, The OCTET STRING
              contains pairs of values in the following structure:
              Octets 0-5 - MAC address.
              Octets 6-7 - VID.
              Each entry need 8 octets, and the peak load is 254 entries.
              "
         ::= { oemZxEdslMacAddressEntry 2 } 
        
------------------------------------------------------------------------------

     oemZxEdslPvlanUpPort     OBJECT-TYPE
          SYNTAX         Integer32
          MAX-ACCESS     read-write
          STATUS         current
          DESCRIPTION
           "the port is for uplink."
          ::= {oemZxEdslService 150}

     oemZxEdslPvlanLoopPorts     OBJECT-TYPE
          SYNTAX         Integer32
          MAX-ACCESS     read-write
          STATUS         current
          DESCRIPTION
           "the two ports is loopd between self. UP WORD is one port and 
           DOWN PORT is another."
          ::= {oemZxEdslService 151}
          
     oemZxEdslPvlanUpVlan     OBJECT-TYPE
          SYNTAX         Integer32
          MAX-ACCESS     read-write
          STATUS         current
          DESCRIPTION
           "the VLAN is used for uplink."
          ::= {oemZxEdslService 152}
          
     oemZxEdslPvlanCommonVlan     OBJECT-TYPE
          SYNTAX         Integer32
          MAX-ACCESS     read-write
          STATUS         current
          DESCRIPTION
           "the VLAN is used for down to user ports."
          ::= {oemZxEdslService 153}
          
     oemZxEdslPvlanStatus     OBJECT-TYPE
          SYNTAX         Integer32
          MAX-ACCESS     read-write
          STATUS         current
          DESCRIPTION
           "Active(1) the configuration data above."
          ::= {oemZxEdslService 154}

-- ---------------------------------------------------------------------------
--    zxQos802.1pToDscp 
-- ---------------------------------------------------------------------------          

    zxQos8021pToDscpTable OBJECT-TYPE
        SYNTAX      SEQUENCE OF ZxQos8021pToDscpEntry
        MAX-ACCESS  not-accessible
        STATUS      current
        DESCRIPTION
            "The 802.p mapping table given DSCP value."
        ::= { oemZxEdslService 160 }
 
    zxQos8021pToDscpEntry OBJECT-TYPE
        SYNTAX      ZxQos8021pToDscpEntry
        MAX-ACCESS  not-accessible
        STATUS      current
        DESCRIPTION
            "An entry (conceptual row) representing a zxQos8021pToDscpTable."
        INDEX      { zxQos8021pToDscp8021PValue }
        ::= { zxQos8021pToDscpTable 1 }
 
    ZxQos8021pToDscpEntry ::= SEQUENCE {
        zxQos8021pToDscp8021PValue      INTEGER,
        zxQos8021pToDscpDSCPValue       INTEGER
    }
 
    zxQos8021pToDscp8021PValue OBJECT-TYPE
        SYNTAX     INTEGER(0..7)
        MAX-ACCESS not-accessible
        STATUS     current
        DESCRIPTION
            "The index of the 802.1P mapping DSCP value table."
        ::= { zxQos8021pToDscpEntry 1 }
 
    zxQos8021pToDscpDSCPValue  OBJECT-TYPE
        SYNTAX INTEGER (0..63)
        MAX-ACCESS read-write
        STATUS current
        DESCRIPTION
            "The DSCP value given one 802.1p value."
        ::= { zxQos8021pToDscpEntry 2 }  
        
-- ---------------------------------------------------------------------------
--    zxQosDscpTo8021pTable
-- ---------------------------------------------------------------------------

    zxQosDscpTo8021pTable OBJECT-TYPE
        SYNTAX SEQUENCE OF ZxQosDscpTo8021pEntry
        MAX-ACCESS not-accessible
        STATUS     current
        DESCRIPTION
            "The DSCP mapping table given 802.1p value."
        ::= { oemZxEdslService 161 }
 
    zxQosDscpTo8021pEntry OBJECT-TYPE
        SYNTAX     ZxQosDscpTo8021pEntry
        MAX-ACCESS not-accessible
        STATUS     current
        DESCRIPTION
            "An entry (conceptual row) representing a zxQosDscpTo8021pTable"
        INDEX  { zxQosDscpTo8021pDSCPValue }
        ::= { zxQosDscpTo8021pTable 1 }
 
    ZxQosDscpTo8021pEntry ::= SEQUENCE {
        zxQosDscpTo8021pDSCPValue      INTEGER,
        zxQosDscpTo8021p8021PValue     INTEGER
    }
 
    zxQosDscpTo8021pDSCPValue OBJECT-TYPE
        SYNTAX     INTEGER(0..63)
        MAX-ACCESS not-accessible
        STATUS     current
        DESCRIPTION
            "The index of the DSCP mapping 802.1p value table."
        ::= { zxQosDscpTo8021pEntry 1 }
 
    zxQosDscpTo8021p8021PValue  OBJECT-TYPE
        SYNTAX INTEGER (0..7)
        MAX-ACCESS read-write
        STATUS current
        DESCRIPTION
            "The 802.1p value given one DSCP value."
        ::= { zxQosDscpTo8021pEntry 2 }    

    qosProfileTable    OBJECT-TYPE
         SYNTAX          SEQUENCE OF QosProfileEntry
         MAX-ACCESS      not-accessible
         STATUS          current
         DESCRIPTION
             "This table contains information about qos queues.
             One entry in this table reflects a
             profile defined by a manager which can be used to
             configure the ADSL port."
     ::= { oemZxEdslService 500}

     qosProfileEntry     OBJECT-TYPE
         SYNTAX          QosProfileEntry
         MAX-ACCESS      not-accessible
         STATUS          current
         DESCRIPTION
             "Each entry consists of a list of parameters about
              the four queues of a adsl port,including minbandwidth,
              maxbandwidth and  weight of the four queues.                 
             "
         INDEX {qosProfileName}
     ::= { qosProfileTable 1}

     QosProfileEntry ::=
         SEQUENCE {
         qosProfileName                        OCTET STRING,
         qosQueue0MinBandwidth                 Unsigned32,
         qosQueue0MaxBandwidth                 Unsigned32,
         qosQueue1MinBandwidth                 Unsigned32,
         qosQueue1MaxBandwidth                 Unsigned32,
         qosQueue2MinBandwidth                 Unsigned32,
         qosQueue2MaxBandwidth                 Unsigned32,
         qosQueue3MinBandwidth                 Unsigned32,
         qosQueue3MaxBandwidth                 Unsigned32,  
         qosQueueWeightRatio                   OCTET STRING,
         qosProfileRowStatus                   RowStatus
     }
     

     qosProfileName          OBJECT-TYPE
             SYNTAX          OCTET STRING (SIZE (1..32))
             MAX-ACCESS      not-accessible
             STATUS          current
             DESCRIPTION
             "This object is used by the qos configuration table
             in order to identify a row of this table.
             "
     ::= { qosProfileEntry 1 }

     qosQueue0MinBandwidth   OBJECT-TYPE
         SYNTAX      Unsigned32
         UNITS       "kbps"
         MAX-ACCESS  read-write
         STATUS      current
         DESCRIPTION
             "Configured Minimum acceptable bandwidth of queue0.       
             "
     ::= { qosProfileEntry 2 }

     qosQueue0MaxBandwidth   OBJECT-TYPE
         SYNTAX      Unsigned32
         UNITS       "kbps"
         MAX-ACCESS  read-write
         STATUS      current
         DESCRIPTION
             "Configured Maximum acceptable bandwidth of queue0.
             "
     ::= { qosProfileEntry 3 }

     qosQueue1MinBandwidth   OBJECT-TYPE
         SYNTAX      Unsigned32
         UNITS       "kbps"
         MAX-ACCESS  read-write
         STATUS      current
         DESCRIPTION
             "Configured Minimum acceptable bandwidth of queue1.       
             "
     ::= { qosProfileEntry 4 }

     qosQueue1MaxBandwidth   OBJECT-TYPE
         SYNTAX      Unsigned32
         UNITS       "kbps"
         MAX-ACCESS  read-write
         STATUS      current
         DESCRIPTION
             "Configured Maximum acceptable bandwidth of queue1.
             "
     ::= { qosProfileEntry 5 }

     qosQueue2MinBandwidth   OBJECT-TYPE
         SYNTAX      Unsigned32
         UNITS       "kbps"
         MAX-ACCESS  read-write
         STATUS      current
         DESCRIPTION
             "Configured Minimum acceptable bandwidth of queue2.       
             "
     ::= { qosProfileEntry 6 }

     qosQueue2MaxBandwidth   OBJECT-TYPE
         SYNTAX      Unsigned32
         UNITS       "kbps"
         MAX-ACCESS  read-write
         STATUS      current
         DESCRIPTION
             "Configured Maximum acceptable bandwidth of queue2.
             "
     ::= { qosProfileEntry 7 }

     qosQueue3MinBandwidth   OBJECT-TYPE
         SYNTAX      Unsigned32
         UNITS       "kbps"
         MAX-ACCESS  read-write
         STATUS      current
         DESCRIPTION
             "Configured Minimum acceptable bandwidth of queue3.       
             "
     ::= { qosProfileEntry 8 }

     qosQueue3MaxBandwidth   OBJECT-TYPE
         SYNTAX      Unsigned32
         UNITS       "kbps"
         MAX-ACCESS  read-write
         STATUS      current
         DESCRIPTION
             "Configured Maximum acceptable bandwidth of queue3.
             "
     ::= { qosProfileEntry 9 }

     qosQueueWeightRatio     OBJECT-TYPE
      SYNTAX         OCTET STRING(SIZE(4))
      MAX-ACCESS     read-write
      STATUS         current
      DESCRIPTION
       "array of ratio in 4 cos priority."
      ::= {qosProfileEntry 10}

     qosProfileRowStatus OBJECT-TYPE
         SYNTAX          RowStatus
         MAX-ACCESS      read-create
         STATUS          current
         DESCRIPTION
             "This object is used to create a new row or modify or
             delete an existing row in this table.
             A profile activated by setting this object to
             `active'.  When `active' is set, the system
             will validate the profile.
             Before a profile can be deleted or taken out of
             service, (by setting this object to `destroy' or
             `outOfService') it must be first unreferenced
             from all associated ports.
             "
     ::= { qosProfileEntry 11 }

      qosPortProfileTable   OBJECT-TYPE
         SYNTAX          SEQUENCE OF qosPortProfileEntry
         MAX-ACCESS      not-accessible
         STATUS          current
         DESCRIPTION
             "This table includes the qos-profile information of port."
     ::= { oemZxEdslService 501 }

     qosPortProfileEntry   OBJECT-TYPE
         SYNTAX          qosPortProfileEntry
         MAX-ACCESS      not-accessible
         STATUS          current
         DESCRIPTION     "An entry in qosPortProfileTable."
         INDEX           { ifIndex }
     ::= { qosPortProfileTable 1 }

     qosPortProfileEntry ::=
         SEQUENCE {
         ifIndex                  Unsigned32,       
         qosPortProfileName       OCTET STRING
         }

     ifIndex        OBJECT-TYPE
         SYNTAX      Unsigned32
         MAX-ACCESS  not-accessible
         STATUS      current
         DESCRIPTION
             "Specifies the port number.
             "
     ::= { qosPortProfileEntry 1 }

     qosPortProfileName OBJECT-TYPE
         SYNTAX      OCTET STRING (SIZE (1..32))
         MAX-ACCESS  read-write
         STATUS      current
         DESCRIPTION
             "The qos profile which is applied to the port."
     ::= { qosPortProfileEntry 2 }

     zxDslQosPortBaseInfoTable   OBJECT-TYPE
         SYNTAX          SEQUENCE OF zxDslQosPortBaseInfoEntry
         MAX-ACCESS      not-accessible
         STATUS          current
         DESCRIPTION
             "The QoS information of one physical port."
     ::= { oemZxEdslService 502 }

     zxDslQosPortBaseInfoEntry   OBJECT-TYPE
         SYNTAX          zxDslQosPortBaseInfoEntry
         MAX-ACCESS      not-accessible
         STATUS          current
         DESCRIPTION     "An entry in zxDslQosPortBaseInfoTable."
         INDEX           { ifIndex }
     ::= { zxDslQosPortBaseInfoTable 1 }

     zxDslQosPortBaseInfoEntry ::=
         SEQUENCE {
         zxDslQosPortCosOverride  Unsigned32,
         zxQosPortTrusted         Unsigned32,
         zxQosPortQosShaping      Unsigned32,
          zxQosPortBurstSize       Unsigned32,
          zxQosPortGFNTrusted      Unsigned32
         }

     zxDslQosPortCosOverride    OBJECT-TYPE    
         SYNTAX            Unsigned32
         MAX-ACCESS        read-write
         STATUS            current
         DESCRIPTION        "The COS value will be override in the ingress flow."
     ::=  {  zxDslQosPortBaseInfoEntry  2  }
     
     zxQosPortTrusted    OBJECT-TYPE    
         SYNTAX            Unsigned32
         MAX-ACCESS        read-write
         STATUS            current
         DESCRIPTION        "Whether the port trust the value in the ingress flow."
     ::=  {  zxDslQosPortBaseInfoEntry  4  }

     zxQosPortQosShaping    OBJECT-TYPE    
         SYNTAX            Unsigned32 (1..16384)
         MAX-ACCESS        read-write
         STATUS            current
         DESCRIPTION        ""
     ::=  {  zxDslQosPortBaseInfoEntry  5  }
     
     zxQosPortBurstSize    OBJECT-TYPE    
         SYNTAX            Unsigned32  (1..4096)
         MAX-ACCESS        read-write
         STATUS            current
         DESCRIPTION        ""
     ::=  {  zxDslQosPortBaseInfoEntry  6  }
     
     zxQosPortGFNTrusted    OBJECT-TYPE    
         SYNTAX            Unsigned32  (1..4)
         MAX-ACCESS        read-write
         STATUS            current
         DESCRIPTION        ""
     ::=  {  zxDslQosPortBaseInfoEntry  7  }

------------------------------------------------------------------------------

    zxQueuingBufTable    OBJECT-TYPE
        SYNTAX        SEQUENCE  OF  ZxQueuingBufEntry
        MAX-ACCESS    not-accessible
        STATUS        current
        DESCRIPTION    "Description"
        ::=  { oemZxEdslService 503 }        

    zxQueuingBufEntry    OBJECT-TYPE
        SYNTAX        ZxQueuingBufEntry
        MAX-ACCESS    not-accessible
        STATUS        current
        DESCRIPTION    "Row Description"
        INDEX        {  ifIndex  }
        ::=  { zxQueuingBufTable 1 }

    ZxQueuingBufEntry  ::=  SEQUENCE {        
        zxQueueBuf1Number       Integer32,
        zxQueueBuf2Number       Integer32,
        zxQueueBuf3Number       Integer32,
        zxQueueBuf4Number       Integer32,
        zxQueueBuf1NumberGet    Integer32,
        zxQueueBuf2NumberGet    Integer32,
        zxQueueBuf3NumberGet    Integer32,
        zxQueueBuf4NumberGet    Integer32        
        }
        
    zxQueueBuf1Number    OBJECT-TYPE    
        SYNTAX            Integer32  
        MAX-ACCESS        read-write
        STATUS            current
        DESCRIPTION        "if set 0, means to be auto"
        ::=  {  zxQueuingBufEntry  1  }
                
    zxQueueBuf2Number    OBJECT-TYPE    
        SYNTAX            Integer32  
        MAX-ACCESS        read-write
        STATUS            current
        DESCRIPTION        "if set 0, means to be auto"
        ::=  {  zxQueuingBufEntry  2  }
        
    zxQueueBuf3Number    OBJECT-TYPE    
        SYNTAX            Integer32  
        MAX-ACCESS        read-write
        STATUS            current
        DESCRIPTION        "if set 0, means to be auto"
        ::=  {  zxQueuingBufEntry  3  }
       
    zxQueueBuf4Number    OBJECT-TYPE    
        SYNTAX            Integer32  
        MAX-ACCESS        read-write
        STATUS            current
        DESCRIPTION        "if set 0, means to be auto"
        ::=  {  zxQueuingBufEntry  4  }    
    
    zxQueueBuf1NumberGet    OBJECT-TYPE    
        SYNTAX            Integer32  
        MAX-ACCESS        read-only
        STATUS            current
        DESCRIPTION        ""
        ::=  {  zxQueuingBufEntry  5  }
                
    zxQueueBuf2NumberGet    OBJECT-TYPE    
        SYNTAX            Integer32  
        MAX-ACCESS        read-only
        STATUS            current
        DESCRIPTION        ""
        ::=  {  zxQueuingBufEntry  6  }
        
    zxQueueBuf3NumberGet    OBJECT-TYPE    
        SYNTAX            Integer32  
        MAX-ACCESS        read-only
        STATUS            current
        DESCRIPTION        ""
        ::=  {  zxQueuingBufEntry  7  }
       
    zxQueueBuf4NumberGet    OBJECT-TYPE    
        SYNTAX            Integer32  
        MAX-ACCESS        read-only
        STATUS            current
        DESCRIPTION        ""
        ::=  {  zxQueuingBufEntry  8  }          
         
------------------------------------------------------------------------------

    zxPvcQueueTable    OBJECT-TYPE
        SYNTAX        SEQUENCE  OF  zxPvcQueueEntry
        MAX-ACCESS    not-accessible
        STATUS        current
        DESCRIPTION    "Description"
        ::=  { oemZxEdslService 504 }        

    zxPvcQueueEntry    OBJECT-TYPE
        SYNTAX        zxPvcQueueEntry
        MAX-ACCESS    not-accessible
        STATUS        current
        DESCRIPTION    "Row Description"
        INDEX        {  ifIndex  }
        ::=  { zxPvcQueueTable 1 }

    zxPvcQueueEntry  ::=  SEQUENCE {        
        zxPvcQueue       OCTET STRING
        }
        
    zxPvcQueue    OBJECT-TYPE    
        SYNTAX            OCTET STRING  
        MAX-ACCESS        read-write
        STATUS            current
        DESCRIPTION        ""
        ::=  {  zxPvcQueueEntry  1  }
                
------------------------------------------------------------------------------

     oemZxEdslLNPTable         OBJECT-TYPE
          SYNTAX         SEQUENCE OF OemZxEdslLNPEntry
          MAX-ACCESS     not-accessible
          STATUS         current
          DESCRIPTION
           " table of setting on LNP card."
          ::= { oemZxEdslLNP 1 }

     oemZxEdslLNPEntry         OBJECT-TYPE
          SYNTAX         OemZxEdslLNPEntry
          MAX-ACCESS     not-accessible
          STATUS         current
          DESCRIPTION
           "An entry in the LNP table."
          INDEX  {oemZxEdslLNPPort}
          ::= { oemZxEdslLNPTable  1}

     OemZxEdslLNPEntry    ::= SEQUENCE  {
          oemZxEdslLNPPort                Integer32,
          oemZxEdslLNPLineInOn            INTEGER,
          oemZxEdslLNPLineOutOn           INTEGER,
          oemZxEdslLNPTest                Integer32,
          oemZxEdslLNPProtect             Integer32
          
     }
     
     oemZxEdslLNPPort            OBJECT-TYPE
          SYNTAX         Integer32
          MAX-ACCESS     not-accessible
          STATUS         current
          DESCRIPTION
           "The port to operate."
          ::= { oemZxEdslLNPEntry 1}
          
     oemZxEdslLNPLineInOn             OBJECT-TYPE
          SYNTAX         INTEGER{
                            enable(1),
                            disable(2)
                            }
          MAX-ACCESS     read-write
          STATUS         current
          DESCRIPTION
           "put the port line on ZXDSL's side to test device or not.
            enable(1) is scrab lines on the port to test device,
            disable(1) is release lines on the port from test device,"
          ::= { oemZxEdslLNPEntry 2}

     oemZxEdslLNPLineOutOn             OBJECT-TYPE
          SYNTAX         INTEGER{
                            enable(1),
                            disable(2)
                            }
          MAX-ACCESS     read-write
          STATUS         current
          DESCRIPTION
           "put the port line on user's side to test device or not.
            enable(1) is scrab lines on the port to test device,
            disable(1) is release lines on the port from test device,"
          ::= { oemZxEdslLNPEntry 3}

     oemZxEdslLNPTest     OBJECT-TYPE
          SYNTAX         Integer32
          MAX-ACCESS     read-write
          STATUS         current
          DESCRIPTION
           "now it is protect card slot when set."
          ::= {oemZxEdslLNPEntry 4}

     oemZxEdslLNPProtect            OBJECT-TYPE
          SYNTAX         Integer32
          MAX-ACCESS     read-write
          STATUS         current
          DESCRIPTION
           "put the port to protect device or not.
            enable(1) is scrab lines on the port to protect device,
            disable(1) is release lines on the port from protect device,"
          ::= { oemZxEdslLNPEntry 5}

------------------------------------------------------------------------------

 oemPortLocationIfaceTable OBJECT-TYPE
        SYNTAX     SEQUENCE OF OemPortLocationIfaceEntry
        MAX-ACCESS not-accessible
        STATUS     current
        DESCRIPTION
            "A table of switch interfaces and associated properties. "
        ::= { oemZxEdslPortLocation 1 }

    oemPortLocationIfaceEntry OBJECT-TYPE
        SYNTAX      OemPortLocationIfaceEntry
        MAX-ACCESS  not-accessible
        STATUS      current
        DESCRIPTION
            "Table entry for switch interface port-location information."
      INDEX { oemPortLocationIfacePort }
        ::= { oemPortLocationIfaceTable 1 }

    OemPortLocationIfaceEntry ::= SEQUENCE {
        oemPortLocationIfacePort                      Integer32,  
        oemPortLocationIfacePPPoeEnable               INTEGER,
        oemPortLocationIfaceDHCPEnable                INTEGER,
        oemPortLocationIfaceServerRemoteId            DisplayString,
        oemPortLocationIfaceServerRemoteIdEnable      INTEGER,
        oemPortLocationIfaceServerDhcpSubOption       INTEGER
    }

    oemPortLocationIfacePort OBJECT-TYPE
        SYNTAX Integer32 (1..728)
        MAX-ACCESS not-accessible
        STATUS current
        DESCRIPTION
            "An index that uniquely identifies a TMS Application 'logical port'
             (i.e., IEEE 802.3ad Aggregator) within the oemPortLocationIfaceUnit."
        ::= { oemPortLocationIfaceEntry 1 }

    oemPortLocationIfacePPPoeEnable OBJECT-TYPE
          SYNTAX INTEGER{
                enable(1),
                disable(2)
                } 
          MAX-ACCESS     read-write
          STATUS         current
          DESCRIPTION
              "config the status of the PPPoE function"
          ::= { oemPortLocationIfaceEntry 2}
          
    oemPortLocationIfaceDHCPEnable OBJECT-TYPE
          SYNTAX INTEGER{
                enable(1),
                disable(2)
                } 
          MAX-ACCESS     read-write
          STATUS         current
          DESCRIPTION
              "config the status of the DHCP function"
          ::= { oemPortLocationIfaceEntry 3}
          
    oemPortLocationIfaceServerRemoteId OBJECT-TYPE
          SYNTAX DisplayString (SIZE (0..64))
          MAX-ACCESS     read-write
          STATUS         current
          DESCRIPTION
              "config the port server remote ID"
          ::= { oemPortLocationIfaceEntry 4}     
    
    oemPortLocationIfaceServerRemoteIdEnable OBJECT-TYPE
          SYNTAX INTEGER{
                enable(1),
                disable(2)
                } 
          MAX-ACCESS     read-write
          STATUS         current
          DESCRIPTION
              "config the status of the Server RemoteID"
          ::= { oemPortLocationIfaceEntry 5}   
          
    oemPortLocationIfaceServerDhcpSubOption OBJECT-TYPE
          SYNTAX INTEGER{
                china-telecom(1),
                cisco(2),
                juniper(3),
                wt101(4)
                } 
          MAX-ACCESS     read-write
          STATUS         current
          DESCRIPTION
              "config Server DHCP sub option"
          ::= { oemPortLocationIfaceEntry 6}  


------------------------------------------------------------------------------

oemPortLocationSlotTable OBJECT-TYPE
        SYNTAX      SEQUENCE OF OemPortLocationSlotEntry
        MAX-ACCESS  not-accessible
        STATUS      current
        DESCRIPTION
            "A table of switch slots and associated properties. "
        ::= { oemZxEdslPortLocation 2 }

    oemPortLocationSlotEntry OBJECT-TYPE
        SYNTAX      OemPortLocationSlotEntry
        MAX-ACCESS  not-accessible
        STATUS      current
        DESCRIPTION
            "Table entry for switch slot port-location information."
      INDEX { oemPortLocationSlotCard }
        ::= { oemPortLocationSlotTable 1 }

    OemPortLocationSlotEntry ::= SEQUENCE {
        oemPortLocationSlotCard                Integer32,  
        oemPortLocationSlotServerRemovePppoeTagEnable   INTEGER,
        oemPortLocationSlotServerRemoveDhcpTagEnable    INTEGER
    }

    oemPortLocationSlotCard OBJECT-TYPE
        SYNTAX Integer32 (1..15)
        MAX-ACCESS not-accessible
        STATUS current
        DESCRIPTION
            "An index that uniquely identifies a TMS Application 'logical slot'"
        ::= { oemPortLocationSlotEntry 1 }

     oemPortLocationSlotServerRemovePppoeTagEnable OBJECT-TYPE
          SYNTAX INTEGER{
                enable(1),
                disable(2)
                } 
          MAX-ACCESS     read-write
          STATUS         current
          DESCRIPTION
              "config remove PPPoE tag"
          ::= { oemPortLocationSlotEntry 2} 
    
    oemPortLocationSlotServerRemoveDhcpTagEnable OBJECT-TYPE
          SYNTAX INTEGER{
                enable(1),
                disable(2)
                } 
          MAX-ACCESS     read-write
          STATUS         current
          DESCRIPTION
              "config remove DHCP tag"
          ::= { oemPortLocationSlotEntry 3} 


------------------------------------------------------------------------------
        oemPortLocationPppoeEnable   OBJECT-TYPE
           SYNTAX     INTEGER{
                           enable(1),
                           disable(2)
                           } 
        MAX-ACCESS read-write
        STATUS current
        DESCRIPTION
            "global pppoe status."
        ::= { oemZxEdslPortLocation 3}

------------------------------------------------------------------------------
        oemPortLocationDhcpEnable   OBJECT-TYPE
           SYNTAX     INTEGER{
                           enable(1),
                           disable(2)
                           } 
        MAX-ACCESS read-write
        STATUS current
        DESCRIPTION
            "global dhcp status."
        ::= { oemZxEdslPortLocation 4}

------------------------------------------------------------------------------
        oemPortLocationDhcpL2Relay   OBJECT-TYPE
        SYNTAX         MacAddress
        MAX-ACCESS read-write
        STATUS current
        DESCRIPTION
            "dhcp l2-relay server macaddress."
        ::= { oemZxEdslPortLocation 5}

------------------------------------------------------------------------------

        oemPortLocationAccessNodeId   OBJECT-TYPE
           SYNTAX     DisplayString (SIZE (0..64))
        MAX-ACCESS read-write
        STATUS current
        DESCRIPTION
            "access-node-identify of the system."
        ::= { oemZxEdslPortLocation 6}

------------------------------------------------------------------------------

        zxDslamIdRack OBJECT-TYPE
        SYNTAX      Integer32
        MAX-ACCESS  read-write
        STATUS      current
        DESCRIPTION
            " Rack ID for dslam.It will be used in locatiing information,such as
            PPPoE,DHCP."
        ::= { oemZxEdslPortLocation 8 }

------------------------------------------------------------------------------

        zxDslamIdShelf OBJECT-TYPE
        SYNTAX      Integer32
        MAX-ACCESS  read-write
        STATUS      current
        DESCRIPTION
            " Shelf ID for dslam.It will be used in locatiing information,such as
            PPPoE,DHCP."
        ::= { oemZxEdslPortLocation 9 }

------------------------------------------------------------------------------

    oemZxEdslMVREnable OBJECT-TYPE
        SYNTAX INTEGER{
                        enable(1),
                        disable(2)
                        }
        MAX-ACCESS read-write
        STATUS     current
        DESCRIPTION
            "Enable/disable MVR in this system."
        ::= { oemZxEdslMVR 1 }

    oemZxEdslMVRMaxResponseTime OBJECT-TYPE
        SYNTAX     Integer32
        MAX-ACCESS read-write
        STATUS     current
        DESCRIPTION
            "Max response time ."
        ::= { oemZxEdslMVR 2 }
       
    oemZxEdslMVRTable OBJECT-TYPE
        SYNTAX     SEQUENCE OF OemZxEdslMVREntry
        MAX-ACCESS not-accessible
        STATUS     current
        DESCRIPTION
        "A table that contains all ZXDSL informations in this stack system.
        It is allowed to get in master module."
    ::= { oemZxEdslMVR 3 }

    oemZxEdslMVREntry OBJECT-TYPE
        SYNTAX     OemZxEdslMVREntry
        MAX-ACCESS not-accessible
        STATUS     current
        DESCRIPTION
            "A list of  entries of all ZXDSL information."
        INDEX { oemZxEdslMVRMvlan, oemZxEdslMVRIpaddress}
    ::= { oemZxEdslMVRTable 1 }

    OemZxEdslMVREntry ::=
        SEQUENCE {
            oemZxEdslMVRMvlan                 INTEGER,
            oemZxEdslMVRIpaddress             IpAddress,
            oemZxEdslMVRSrcPorts              PortList,
            oemZxEdslMVRRecvPorts             PortList,
            oemZxEdslIgmpMPVC                 INTEGER,
            oemZxEdslMVRMaxGroup              INTEGER,
            oemZxEdslStaticRecvPorts          DisplayString,
            oemZxEdslMVRRowStatus             Integer32,
            oemZxEdslMVRCurrentGroupNumber    Integer32
        }

    oemZxEdslMVRMvlan OBJECT-TYPE
        SYNTAX     INTEGER(1..4095)
        MAX-ACCESS not-accessible
        STATUS     current
        DESCRIPTION
            "vlan."
    ::= { oemZxEdslMVREntry 1 }

    oemZxEdslMVRIpaddress OBJECT-TYPE
        SYNTAX     IpAddress
        MAX-ACCESS not-accessible
        STATUS     current
        DESCRIPTION
            "multicast ip address . it can be 0.0.0.0 when setting "
    ::= { oemZxEdslMVREntry 2 }

    oemZxEdslMVRSrcPorts OBJECT-TYPE
        SYNTAX     PortList
        MAX-ACCESS read-write
        STATUS     current
        DESCRIPTION
            "the ports that send multicast"
    ::= { oemZxEdslMVREntry 3 }

    oemZxEdslMVRRecvPorts OBJECT-TYPE
        SYNTAX     PortList
        MAX-ACCESS read-write
        STATUS     current
        DESCRIPTION
            "the ports that receive multicast"
    ::= { oemZxEdslMVREntry 4 }

    oemZxEdslIgmpMPVC OBJECT-TYPE
        SYNTAX     INTEGER(1..8)
        MAX-ACCESS read-write
        STATUS     current
        DESCRIPTION
            "the property of the pvc belongs to one port."
    ::= { oemZxEdslMVREntry 5 }

    oemZxEdslMVRMaxGroup OBJECT-TYPE
        SYNTAX     INTEGER(1..512)
        MAX-ACCESS read-write
        STATUS     current
        DESCRIPTION
            "the max group ip amount of a mvlan ."
    ::= { oemZxEdslMVREntry 6 }

    oemZxEdslStaticRecvPorts OBJECT-TYPE
        SYNTAX     DisplayString (SIZE (0..4))
        MAX-ACCESS read-only
        STATUS     current
        DESCRIPTION
            "Interface ."
    ::= { oemZxEdslMVREntry 7 }
    
    oemZxEdslMVRRowStatus OBJECT-TYPE
        SYNTAX     Integer32
        MAX-ACCESS read-write
        STATUS     current
        DESCRIPTION
            "Interface ."
    ::= { oemZxEdslMVREntry 8 }

    oemZxEdslMVRCurrentGroupNumber    OBJECT-TYPE
        SYNTAX     Integer32
        MAX-ACCESS read-only
        STATUS     current
        DESCRIPTION
            "the number of current group."
    ::= { oemZxEdslMVREntry 9 }

------------------------------------------------------------------------------
     oemZxEdslFdbTable         OBJECT-TYPE
          SYNTAX         SEQUENCE OF OemZxEdslFdbEntry
          MAX-ACCESS     not-accessible
          STATUS         current
          DESCRIPTION
           " fdb table."
          ::= { oemZxEdslFdb 1 }

     oemZxEdslFdbEntry         OBJECT-TYPE
          SYNTAX         OemZxEdslFdbEntry
          MAX-ACCESS     not-accessible
          STATUS         current
          DESCRIPTION
           "An entry in the Fdb table."
          INDEX  {oemZxEdslFdbPort,oemZxEdslFdbMac,oemZxEdslFdbVid}
          ::= { oemZxEdslFdbTable  1}

     OemZxEdslFdbEntry    ::= SEQUENCE  {
         oemZxEdslFdbPort               Integer32,
         oemZxEdslFdbMac                MacAddress,
         oemZxEdslFdbVid                Integer32,
         oemZxEdslResever               Integer32,
         oemZxEdslFdbStatus             INTEGER
     }
     
     oemZxEdslFdbPort            OBJECT-TYPE
          SYNTAX         Integer32
          MAX-ACCESS     not-accessible
          STATUS         current
          DESCRIPTION
           "The port to operate."
          ::= { oemZxEdslFdbEntry 1}
          
     oemZxEdslFdbMac             OBJECT-TYPE
          SYNTAX         MacAddress
          MAX-ACCESS     not-accessible
          STATUS         current
          DESCRIPTION
           "put the port line on ZXDSL's side to test device or not.
            enable(1) is scrab lines on the port to test device,
            disable(1) is release lines on the port from test device,"
          ::= { oemZxEdslFdbEntry 2}

     oemZxEdslFdbVid             OBJECT-TYPE
          SYNTAX         Integer32 (1..4095)
          MAX-ACCESS     not-accessible
          STATUS         current
          DESCRIPTION
           "put the port line on user's side to test device or not.
            enable(1) is scrab lines on the port to test device,
            disable(1) is release lines on the port from test device,"
          ::= { oemZxEdslFdbEntry 3}


     oemZxEdslResever     OBJECT-TYPE
          SYNTAX         Integer32
          MAX-ACCESS     not-accessible
          STATUS         current
          DESCRIPTION
           "now it is protect card slot when set."
          ::= {oemZxEdslFdbEntry 4}

     oemZxEdslFdbStatus            OBJECT-TYPE
          SYNTAX         INTEGER{
                            enable(1),
                            disable(2)
                            }
          MAX-ACCESS     read-write
          STATUS         current
          DESCRIPTION
           "put the port to protect device or not.
            enable(1) is scrab lines on the port to protect device,
            disable(1) is release lines on the port from protect device,"
          ::= { oemZxEdslFdbEntry 5}
          

          
     oemZxEdslLoopCheckTable         OBJECT-TYPE
          SYNTAX         SEQUENCE OF OemZxEdslLoopCheckEntry
          MAX-ACCESS     not-accessible
          STATUS         current
          DESCRIPTION
           " loop check table."
          ::= { oemZxEdslLoopCheck 1 }

     oemZxEdslLoopCheckEntry         OBJECT-TYPE
          SYNTAX         OemZxEdslLoopCheckEntry
          MAX-ACCESS     not-accessible
          STATUS         current
          DESCRIPTION
           "An entry in the Fdb table."
          INDEX  {oemZxEdslFdbPort,oemZxEdslFdbMac,oemZxEdslFdbVid}
          ::= { oemZxEdslLoopCheckTable  1}

     OemZxEdslLoopCheckEntry    ::= SEQUENCE  {
          oemZxEdslLoopCheckSlot            Integer32,
          oemZxEdslSlotLoopCheckInterval    Integer32
     }
     
     oemZxEdslLoopCheckSlot         OBJECT-TYPE
          SYNTAX         Integer32
          MAX-ACCESS     not-accessible
          STATUS         current
          DESCRIPTION
           "The slot to operate."
          ::= { oemZxEdslLoopCheckEntry 1}
          
     oemZxEdslSlotLoopCheckInterval     OBJECT-TYPE
          SYNTAX         Integer32
          MAX-ACCESS     read-write
          STATUS         current
          DESCRIPTION
           "the interval for this slot to send port loop-check frame"
          ::= { oemZxEdslLoopCheckEntry 2}
          
     oemZxEdslSelfLoopDisappearDetectTime         OBJECT-TYPE
          SYNTAX      Integer32 (0..7200)
          UNITS       "min"
          MAX-ACCESS  read-write
          STATUS      current
          DESCRIPTION
             "Interval to check whether bridge self-loop disappeared.
             0 mains disable the self loop disappearance auto check.
             Recommended range is between 3 and 7200 min.If the value is too small,
             the network or the cpu of device will have high loads.
             "
          DEFVAL { 0 }                   
          ::= { oemZxEdslLoopCheck 2 }     

     oemZxEdslSelfLoopDisappearDetectMaxNumber               OBJECT-TYPE
          SYNTAX      Integer32 (0..10)
          MAX-ACCESS  read-write
          STATUS      current
          DESCRIPTION
             "Max number of no shutdown.
             Recommended range is between 1 and 10.
             Running 'no' commond on command line and setting this object to '0' value 
             means that the selfloop can't be reopened automatically 
             after closing itself up when selfloop alarm happened."
          DEFVAL { 3 }   
          ::= { oemZxEdslLoopCheck 3 }          

------------------------------------------------------------------------------
    oemZxEdslLastMib OBJECT-TYPE
        SYNTAX     Integer32
        MAX-ACCESS read-only
        STATUS     current
        DESCRIPTION
            "This item is end of all mibview ."
    ::= { oemZxEdslMibEnd 1 }

          
   END

------------------------------------------------------------------------------
-- RADIUS MIB
------------------------------------------------------------------------------

OEMRADIUSMIB DEFINITIONS ::= BEGIN

    IMPORTS
        MODULE-IDENTITY, OBJECT-TYPE, NOTIFICATION-TYPE,
        Integer32, Counter64,TimeTicks,Counter32,IpAddress
                            FROM SNMPv2-SMI
        tmsGeneric          FROM WRS-MASTER-MIB
        DisplayString, TruthValue,               
        RowStatus,MacAddress                            FROM SNMPv2-TC
        SnmpAdminString                         FROM SNMP-FRAMEWORK-MIB
        MODULE-COMPLIANCE, OBJECT-GROUP         FROM SNMPv2-CONF
        galnet                                 FROM OEMMIB;       

    oemRadius MODULE-IDENTITY
        LAST-UPDATED    "0007120000Z"  -- July 12, 2000
        ORGANIZATION    "Wind River Systems, Inc."
        CONTACT-INFO    "Wind River Systems, Inc.
                         E-mail: support@windriver.com"

        DESCRIPTION     "TMS Broadcom GALNET StrataSwitch OEM-Product
                         Enterprise MIB definition."

        REVISION        "0007120000Z"  -- July 12, 2000
        DESCRIPTION     "Initial MIB creation."

        ::= { tmsGeneric 6 }



    oemRadiusClientAuthServer        OBJECT IDENTIFIER ::= { oemRadius 1 }
    oemRadiusClientAccServer         OBJECT IDENTIFIER ::= { oemRadius 2 }
        
    
    
oemRadiusClientAuthServerTable OBJECT-TYPE
      SYNTAX SEQUENCE OF OemRadiusClientAuthServerEntry
      MAX-ACCESS not-accessible
      STATUS     current
      DESCRIPTION
            "The (conceptual) table listing the RADIUS accounting
             servers with which the client shares a secret."
      ::= { oemRadiusClientAuthServer 1 }

oemRadiusClientAuthServerEntry OBJECT-TYPE
      SYNTAX     OemRadiusClientAuthServerEntry
      MAX-ACCESS not-accessible
      STATUS     current
      DESCRIPTION
            "An entry (conceptual row) representing a RADIUS
             accounting server with which the client shares a secret."
      INDEX      { oemRadiusClientAuthServerAddress,oemRadiusClientAuthServerPortNumber }
      ::= { oemRadiusClientAuthServerTable 1 }

OemRadiusClientAuthServerEntry ::= SEQUENCE {
      oemRadiusClientAuthServerAddress                         IpAddress,
      oemRadiusClientAuthServerPortNumber                Integer32,
      oemRadiusClientAuthSecret                                SnmpAdminString,
      oemRadiusClientAuthRowStatus                             RowStatus
}


oemRadiusClientAuthServerAddress OBJECT-TYPE
      SYNTAX     IpAddress
      MAX-ACCESS read-write
      STATUS     current
      DESCRIPTION
            "The IP address of the RADIUS accounting server
             referred to in this table entry."
      ::= { oemRadiusClientAuthServerEntry 1 }

oemRadiusClientAuthServerPortNumber  OBJECT-TYPE
      SYNTAX Integer32 (0..65535)
      MAX-ACCESS read-write
      STATUS current
      DESCRIPTION
            "The UDP port the client is using to send requests to
             this server."
      ::= { oemRadiusClientAuthServerEntry 2 }

oemRadiusClientAuthSecret OBJECT-TYPE
    SYNTAX      SnmpAdminString (SIZE (0..32))
    MAX-ACCESS  read-write
    STATUS      current
    DESCRIPTION
        ""
    REFERENCE
        "1"
    ::= { oemRadiusClientAuthServerEntry 3}
    
    
   oemRadiusClientAuthRowStatus OBJECT-TYPE
    SYNTAX      RowStatus
    MAX-ACCESS  read-write
    STATUS      current
    DESCRIPTION
        "This object indicates the status of this entry."
    ::= { oemRadiusClientAuthServerEntry 4 }
    
    
--    ///////////////////////////////////////////////////////////////////
    
    
oemRadiusClientAccServerTable OBJECT-TYPE
      SYNTAX SEQUENCE OF OemRadiusClientAccServerEntry
      MAX-ACCESS not-accessible
      STATUS     current
      DESCRIPTION
            "The (conceptual) table listing the RADIUS accounting
             servers with which the client shares a secret."
      ::= { oemRadiusClientAccServer 2 }

oemRadiusClientAccServerEntry OBJECT-TYPE
      SYNTAX     OemRadiusClientAccServerEntry
      MAX-ACCESS not-accessible
      STATUS     current
      DESCRIPTION
            "An entry (conceptual row) representing a RADIUS
             accounting server with which the client shares a secret."
      INDEX      { oemRadiusClientAccServerAddress,oemRadiusClientAccServerPortNumber }
      ::= { oemRadiusClientAccServerTable 1 }

OemRadiusClientAccServerEntry ::= SEQUENCE {
      oemRadiusClientAccServerAddress                   IpAddress,
      oemRadiusClientAccServerPortNumber                Integer32,
      oemRadiusClientAccSecret                          SnmpAdminString,
      oemRadiusClientAccRowStatus                       RowStatus
}


oemRadiusClientAccServerAddress OBJECT-TYPE
      SYNTAX     IpAddress
      MAX-ACCESS read-write
      STATUS     current
      DESCRIPTION
            "The IP address of the RADIUS accounting server
             referred to in this table entry."
      ::= { oemRadiusClientAccServerEntry 1 }

oemRadiusClientAccServerPortNumber  OBJECT-TYPE
      SYNTAX Integer32 (0..65535)
      MAX-ACCESS read-write
      STATUS current
      DESCRIPTION
            "The UDP port the client is using to send requests to
             this server."
      ::= { oemRadiusClientAccServerEntry 2 }

oemRadiusClientAccSecret OBJECT-TYPE
    SYNTAX      SnmpAdminString (SIZE (0..32))
    MAX-ACCESS  read-write
    STATUS      current
    DESCRIPTION
        ""
    REFERENCE
        "1"
    ::= { oemRadiusClientAccServerEntry 3}
    
oemRadiusClientAccRowStatus OBJECT-TYPE
    SYNTAX      RowStatus
    MAX-ACCESS  read-write
    STATUS      current
    DESCRIPTION
        "This object indicates the status of this entry."
    ::= { oemRadiusClientAccServerEntry 4 }

END    


------------------------------------------------------------------------------
------------------------------------------------------------------------------

------------------------------------------------------------------------------
------------------------------------------------------------------------------
--
--  File         : oemZxMulticast.mib
--  Description  : Sample TMS OEM Product Enterprise MIB for 
--                 Multicast service of ZXDSL9210 v3.1.1
--  Version      : 0.00   
--  Date         : Aug 9, 2004     
--
------------------------------------------------------------------------------
------------------------------------------------------------------------------
--  Sample ZTE Multicast MIB
--
--  NOTES:
--   1. This is a SMIv2 MIB.
--
--   2. The following groups are supported in this MIB:
--      -
--
------------------------------------------------------------------------------
------------------------------------------------------------------------------

    OEMZXMULTICAST DEFINITIONS ::= BEGIN

    IMPORTS
        MODULE-IDENTITY, OBJECT-TYPE, NOTIFICATION-TYPE,
        Integer32, Counter64,TimeTicks,Counter32,
        IpAddress                            FROM SNMPv2-SMI
        
        DisplayString, TruthValue, RowStatus,              
        MacAddress, DateAndTime            FROM SNMPv2-TC
       SnmpAdminString                   FROM SNMP-FRAMEWORK-MIB
        
        MODULE-COMPLIANCE, OBJECT-GROUP         FROM SNMPv2-CONF
        oemProd                                 FROM WRS-MASTER-MIB       
        PortList                                 FROM Q-BRIDGE-MIB;     
--      Note:
--         RowStatus: active(1),notInService(2),notReady(3),createAndGo(4),
--                    createAndWait(5),destroy(6)
--

    oemZxMulticastMib MODULE-IDENTITY
        LAST-UPDATED    "0408090000Z"  -- Aug 9, 2004
        ORGANIZATION    "ZTE."
        CONTACT-INFO    "ZTE."

        DESCRIPTION     "Description of Multicast Service of  ZXDSL9210 v3.1.1. "

        REVISION        "0408090000Z"  -- Aug 9, 2004
        DESCRIPTION     "Initial MIB creation."

        ::= { oemProd 10 }


    oemZxMulticastIGMP        OBJECT IDENTIFIER ::= { oemZxMulticastMib 1 }
    oemZxMulticastMVR         OBJECT IDENTIFIER ::= { oemZxMulticastMib 2 }
    oemZxMulticastCAC         OBJECT IDENTIFIER ::= { oemZxMulticastMib 3 }
    oemZxMulticastPRW         OBJECT IDENTIFIER ::= { oemZxMulticastMib 4 }
    oemZxMulticastCDR         OBJECT IDENTIFIER ::= { oemZxMulticastMib 5 }
    
------------------------------------------------------------------------------
------------------------------------------------------------------------------
    
    oemZxIgmpEnabled  OBJECT-TYPE
        SYNTAX TruthValue
        MAX-ACCESS read-write
        STATUS current
        DESCRIPTION
            "DURABLE: { false )
             Setting this object to true(1) enables IGMP .  Setting
             it to false(2) disables IGMP.
             
             Note that IGMP can function with or without GVRP and
             GMRP enabled."
        ::= { oemZxMulticastIGMP 1 }
        
     oemZxIgmpAging  OBJECT-TYPE
        SYNTAX Integer32 (30..3600)
        MAX-ACCESS read-write
        STATUS current
        DESCRIPTION
            "DURABLE: { 300 )
             The timeout period in seconds for aging out Multicast Groups
             dynamically learned with IGMP.  Note that aging operates
             on a per interface per VLAN per multicast group basis."
        ::= { oemZxMulticastIGMP 2 }
        
     oemZxIgmpMode  OBJECT-TYPE
        SYNTAX     INTEGER(1..3)
        MAX-ACCESS read-write
        STATUS current
        DESCRIPTION
            "IGMP mode"
        ::= { oemZxMulticastIGMP 3 }
     
     oemZxIgmpTable OBJECT-TYPE
        SYNTAX SEQUENCE OF OemZxIgmpEntry
        MAX-ACCESS not-accessible
        STATUS current
        DESCRIPTION
        "A table that contains all IGMP informations."
    ::= { oemZxMulticastIGMP 4 }

    oemZxIgmpEntry OBJECT-TYPE
        SYNTAX OemZxIgmpEntry
        MAX-ACCESS not-accessible
        STATUS current
        DESCRIPTION
            "A list of  entries of all IGMP information."
        INDEX { oemZxIgmpPortIndex}
    ::= { oemZxIgmpTable 1 }

    OemZxIgmpEntry ::=
        SEQUENCE {
                  oemZxIgmpPortIndex            INTEGER,
              oemZxIgmpFastLeave        INTEGER
        }   
     
     oemZxIgmpPortIndex            OBJECT-TYPE
          SYNTAX         INTEGER
          MAX-ACCESS     not-accessible
          STATUS         current
          DESCRIPTION
           "The port No. 1-728"
          ::= { oemZxIgmpEntry 1}
     
     oemZxIgmpFastLeave  OBJECT-TYPE
        SYNTAX     INTEGER
        MAX-ACCESS read-write
        STATUS current
        DESCRIPTION
            "the status of fast-leave property."
        ::= { oemZxIgmpEntry 2 }
        
     oemZxIgmpRecognitionTime  OBJECT-TYPE
        SYNTAX     INTEGER
        MAX-ACCESS read-write
        STATUS current
        DESCRIPTION
            "Recognition Time"
        ::= { oemZxMulticastIGMP 5 }
        
-----------------------------------------------------------------------------------------    
    
    
    oemZxMVREnable OBJECT-TYPE
        SYNTAX INTEGER{
                        enable(1),
                        disable(2)
                        }
        MAX-ACCESS read-write
        STATUS current
        DESCRIPTION
            "Enable/disable MVR in this system."
        ::= { oemZxMulticastMVR 1 }

    oemZxMVRMaxResponseTime OBJECT-TYPE
        SYNTAX INTEGER
        MAX-ACCESS read-write
        STATUS current
        DESCRIPTION
            "Max response time ."
        ::= { oemZxMulticastMVR 2 }
       
    oemZxMVRTable OBJECT-TYPE
        SYNTAX SEQUENCE OF OemZxMVREntry
        MAX-ACCESS not-accessible
        STATUS current
        DESCRIPTION
        "A table that contains all ZXDSL informations in this stack system.
        It is allowed to get in master module."
    ::= { oemZxMulticastMVR 3 }

    oemZxMVREntry OBJECT-TYPE
        SYNTAX OemZxMVREntry
        MAX-ACCESS not-accessible
        STATUS current
        DESCRIPTION
            "A list of  entries of all ZXDSL information."
        INDEX { oemZxMVRMvlan, oemZxMVRIpaddress}
    ::= { oemZxMVRTable 1 }

    OemZxMVREntry ::=
        SEQUENCE {
        oemZxMVRMvlan        INTEGER,
        oemZxMVRIpaddress       IpAddress,
                oemZxMVRSrcPorts    PortList,
        oemZxMVRRecvPorts       PortList,
               oemZxMVRCurrentGroupNumber    INTEGER,
               oemZxDynamicRecvPorts    DisplayString,
               oemZxStaticRecvPorts    DisplayString,
               oemZxMVRRowStatus    INTEGER,
               oemZxMVRMaxGroup        INTEGER,
               oemZxMVRSrcIpaddress        IpAddress
        }

    oemZxMVRMvlan OBJECT-TYPE
        SYNTAX INTEGER(1..4095)
        MAX-ACCESS not-accessible
        STATUS current
        DESCRIPTION
            "vlan."
    ::= { oemZxMVREntry 1 }

    oemZxMVRIpaddress OBJECT-TYPE
        SYNTAX IpAddress
        MAX-ACCESS not-accessible
        STATUS current
        DESCRIPTION
            "multicast ip address . it can be 0.0.0.0 when setting "
    ::= { oemZxMVREntry 2 }

    oemZxMVRSrcPorts OBJECT-TYPE
        SYNTAX PortList
        MAX-ACCESS read-write
        STATUS current
        DESCRIPTION
            "the ports that send multicast"
    ::= { oemZxMVREntry 3 }

    oemZxMVRRecvPorts OBJECT-TYPE
        SYNTAX PortList
        MAX-ACCESS read-write
        STATUS current
        DESCRIPTION
            "the ports that receive multicast"
    ::= { oemZxMVREntry 4 }

    oemZxMVRCurrentGroupNumber OBJECT-TYPE
        SYNTAX INTEGER
        MAX-ACCESS read-only
        STATUS current
        DESCRIPTION
            "the number of current group."
    ::= { oemZxMVREntry 5 }

    oemZxDynamicRecvPorts OBJECT-TYPE
        SYNTAX DisplayString
        MAX-ACCESS read-only
        STATUS current
        DESCRIPTION
            "Interface ."
    ::= { oemZxMVREntry 6 }

    oemZxStaticRecvPorts OBJECT-TYPE
        SYNTAX DisplayString (SIZE (0..4))
        MAX-ACCESS read-write
        STATUS current
        DESCRIPTION
            "Interface ."
    ::= { oemZxMVREntry 7 }
    
    oemZxMVRRowStatus OBJECT-TYPE
        SYNTAX INTEGER
        MAX-ACCESS read-write
        STATUS current
        DESCRIPTION
            ""
    ::= { oemZxMVREntry 8 }

    oemZxMVRMaxGroup OBJECT-TYPE
        SYNTAX INTEGER(1..512)
        MAX-ACCESS read-write
        STATUS current
        DESCRIPTION
            ""
    ::= { oemZxMVREntry 9 }

    oemZxMVRSrcIpaddress OBJECT-TYPE
        SYNTAX IpAddress
        MAX-ACCESS read-write
        STATUS current
        DESCRIPTION
            ""
    ::= { oemZxMVREntry 10 }
    
------------------------------------------------------------------------------------

oemZxACGpIpTable OBJECT-TYPE
        SYNTAX SEQUENCE OF OemZxACGpIpEntry
        MAX-ACCESS not-accessible
        STATUS current
        DESCRIPTION
        "CAC Address Table info"
    ::= { oemZxMulticastCAC 1 }

    oemZxACGpIpEntry OBJECT-TYPE
        SYNTAX OemZxACGpIpEntry
        MAX-ACCESS not-accessible
        STATUS current
        DESCRIPTION
            "A list of  entries of all Multicast address information."
        INDEX { oemZxGpIp}
    ::= { oemZxACGpIpTable 1 }

    OemZxACGpIpEntry ::=
        SEQUENCE {
        oemZxGpIp            IpAddress,
        oemZxMaxPrwCount           Counter,
                oemZxMaxPrwInter        Counter,
        oemZxPrwResumeInter           INTEGER,
               oemZxACRowStatus        INTEGER
               }

    oemZxGpIp     OBJECT-TYPE
        SYNTAX         IpAddress
        MAX-ACCESS     not-accessible
        STATUS current
        DESCRIPTION
            "Group IP."
    ::= { oemZxACGpIpEntry 1 }

    oemZxMaxPrwCount OBJECT-TYPE
        SYNTAX         Counter
        MAX-ACCESS     read-write
        STATUS current
        DESCRIPTION
            "The max preview count of the multicast group."
    ::= { oemZxACGpIpEntry 2 }

    oemZxMaxPrwInter OBJECT-TYPE
        SYNTAX         Counter
        MAX-ACCESS     read-write
        STATUS current
        DESCRIPTION
            "The max preview time."
    ::= { oemZxACGpIpEntry 3 }

    oemZxPrwResumeInter OBJECT-TYPE
        SYNTAX         INTEGER
        MAX-ACCESS     read-write
        STATUS current
        DESCRIPTION
            "The interval of two continuous previews."
    ::= { oemZxACGpIpEntry 4 }

    oemZxACRowStatus OBJECT-TYPE
        SYNTAX         INTEGER
        MAX-ACCESS     read-write
        STATUS current
        DESCRIPTION
            "Row Status of AC Table."
    ::= { oemZxACGpIpEntry 5 }

--------------------------------------------------------------------------------------
oemZxACProfileTable OBJECT-TYPE
        SYNTAX SEQUENCE OF OemZxACProfileEntry
        MAX-ACCESS not-accessible
        STATUS current
        DESCRIPTION
        "CAC Profile Table info"
    ::= { oemZxMulticastCAC 2 }

    oemZxACProfileEntry OBJECT-TYPE
        SYNTAX OemZxACProfileEntry
        MAX-ACCESS not-accessible
        STATUS current
        DESCRIPTION
            "A list of  entries of all Multicast profile information."
        INDEX { oemZxProfileIndex,oemZxACProfileGpIp}
    ::= { oemZxACProfileTable 1 }

    OemZxACProfileEntry ::=
        SEQUENCE {
        oemZxProfileIndex        INTEGER,
        oemZxACProfileGpIp        IpAddress,
        oemZxGpRight               INTEGER,
               oemZxProfileItemRowStatus    INTEGER
               }

    oemZxProfileIndex     OBJECT-TYPE
        SYNTAX         INTEGER
        MAX-ACCESS     not-accessible
        STATUS current
        DESCRIPTION
            "Profile Index."
    ::= { oemZxACProfileEntry 1 }

    oemZxACProfileGpIp OBJECT-TYPE
        SYNTAX         IpAddress
        MAX-ACCESS     not-accessible
        STATUS current
        DESCRIPTION
            "Group IP."
    ::= { oemZxACProfileEntry 2 }

    oemZxGpRight OBJECT-TYPE
        SYNTAX         INTEGER
        MAX-ACCESS     read-write
        STATUS current
        DESCRIPTION
            "The Group Right for multicast."
    ::= { oemZxACProfileEntry 3 }

    oemZxProfileItemRowStatus OBJECT-TYPE
        SYNTAX         INTEGER
        MAX-ACCESS     read-write
        STATUS current
        DESCRIPTION
            "Row Status of Profile Table."
    ::= { oemZxACProfileEntry 4 }

---------------------------------------------------------------------------------------
oemZxACPortGpTable OBJECT-TYPE
        SYNTAX SEQUENCE OF OemZxACPortGpEntry
        MAX-ACCESS not-accessible
        STATUS current
        DESCRIPTION
        "CAC Port Multicast info"
    ::= { oemZxMulticastCAC 3 }

    oemZxACPortGpEntry OBJECT-TYPE
        SYNTAX OemZxACPortGpEntry
        MAX-ACCESS not-accessible
        STATUS current
        DESCRIPTION
            "A list of  entries of all port multicast information."
        INDEX { oemZxPort,oemZxACPortGpIp}
    ::= { oemZxACPortGpTable 1 }

    OemZxACPortGpEntry ::=
        SEQUENCE {
        oemZxPort            INTEGER,
        oemZxACPortGpIp           IpAddress,
                oemZxRight            INTEGER,
        oemZxPortTableItemRowStatus       INTEGER
               }

    oemZxPort     OBJECT-TYPE
        SYNTAX         INTEGER
        MAX-ACCESS     not-accessible
        STATUS current
        DESCRIPTION
            "port number."
    ::= { oemZxACPortGpEntry 1 }

    oemZxACPortGpIp OBJECT-TYPE
        SYNTAX         IpAddress
        MAX-ACCESS     not-accessible
        STATUS current
        DESCRIPTION
            "Group IP."
    ::= { oemZxACPortGpEntry 2 }

    oemZxRight OBJECT-TYPE
        SYNTAX         INTEGER
        MAX-ACCESS     read-write
        STATUS current
        DESCRIPTION
            "The Group Right for multicast."
    ::= { oemZxACPortGpEntry 3 }

    oemZxPortTableItemRowStatus OBJECT-TYPE
        SYNTAX         INTEGER
        MAX-ACCESS     read-write
        STATUS current
        DESCRIPTION
            "The RowStatus of port item."
    ::= { oemZxACPortGpEntry 4 }

---------------------------------------------------------------------------
oemZxACPortInfoTable OBJECT-TYPE
        SYNTAX SEQUENCE OF OemZxACPortInfoEntry
        MAX-ACCESS not-accessible
        STATUS current
        DESCRIPTION
        "CAC Address Table info"
    ::= { oemZxMulticastCAC 4 }

    oemZxACPortInfoEntry OBJECT-TYPE
        SYNTAX OemZxACPortInfoEntry
        MAX-ACCESS not-accessible
        STATUS current
        DESCRIPTION
            "A list of  entries of all Multicast port information."
        INDEX { oemZxACPort}
    ::= { oemZxACPortInfoTable 1 }

    OemZxACPortInfoEntry ::=
        SEQUENCE {
        oemZxACPort        INTEGER,
        profileIndex        INTEGER,
        oemZxPortGpTotalInfo     OCTET STRING
               }

    oemZxACPort     OBJECT-TYPE
        SYNTAX         INTEGER
        MAX-ACCESS     not-accessible
        STATUS current
        DESCRIPTION
            "Port Number."
    ::= { oemZxACPortInfoEntry 1 }

    profileIndex OBJECT-TYPE
        SYNTAX         INTEGER
        MAX-ACCESS     read-write
        STATUS current
        DESCRIPTION
            "The port multicast information."
    ::= { oemZxACPortInfoEntry 2 }
    
    oemZxPortGpTotalInfo OBJECT-TYPE
        SYNTAX         OCTET STRING
        MAX-ACCESS     read-write
        STATUS current
        DESCRIPTION
            "The port multicast information."
    ::= { oemZxACPortInfoEntry 3 }

    oemZxACPrwSwitch OBJECT-TYPE
        SYNTAX         INTEGER
        MAX-ACCESS     read-write
        STATUS current
        DESCRIPTION
            "the switch used by both CAC and PRW module, '1'-enable."
        ::= { oemZxMulticastCAC 5 }

------------------------------------------------------------------------------

    oemZxPRWManageReset OBJECT-TYPE
        SYNTAX         INTEGER
        MAX-ACCESS     read-write
        STATUS current
        DESCRIPTION
            "used to manage reset in PRW module,when '1',need to reset."
        ::= { oemZxMulticastPRW 1 }

    oemZxPRWResetPeriod    OBJECT-TYPE
    SYNTAX         INTEGER
    MAX-ACCESS     read-write
        STATUS current
        DESCRIPTION
            "specify the fix time of reseting the preview management structure."
        ::= { oemZxMulticastPRW 2 }
        
------------------------------------------------------------------------------------

    oemZxCDRMaxSize OBJECT-TYPE
        SYNTAX         Unsigned32
        MAX-ACCESS     read-write
        STATUS current
        DESCRIPTION
            "The max size of CDR."
        ::= { oemZxMulticastCDR 1 }
    
    oemZxCDRServerIP OBJECT-TYPE
        SYNTAX         IpAddress
        MAX-ACCESS     read-write
        STATUS current
        DESCRIPTION
            "The IP of SMS server."
        ::= { oemZxMulticastCDR 2 }
        
        oemZxCDRMaxSendInterval    OBJECT-TYPE
        SYNTAX        Unsigned32
        MAX-ACCESS    read-write    
        STATUS    current
        DESCRIPTION
            "The Max Send Interval of CDR Record."
        ::= { oemZxMulticastCDR 3 }
        
        oemZxCDREnable OBJECT-TYPE
        SYNTAX         TruthValue
        MAX-ACCESS     read-write
        STATUS current
        DESCRIPTION
            "DURABLE: { false )
             Setting this object to true(1) enables CDR .  Setting
             it to false(2) disables CDR."
        ::= { oemZxMulticastCDR 4 }
        
        oemZxCDRCurrentRecordNumber    OBJECT-TYPE
        SYNTAX         INTEGER
        MAX-ACCESS     read-only
        STATUS current
        DESCRIPTION
            "the number of CDR records"
        ::= { oemZxMulticastCDR 5 }      
        
        oemZxCDRTimeZone    OBJECT-TYPE
        SYNTAX         INTEGER
        MAX-ACCESS     read-write
        STATUS current
        DESCRIPTION
            "time zone (-12~12)"
        ::= { oemZxMulticastCDR 6 }    
          
   END

------------------------------------------------------------------------------
------------------------------------------------------------------------------
--
--  File         : oemZxMSTP.mib
--  Description  : 9426 MSTP mib 
--  Version      : 0.00   
--  Date         : Dec 22, 2004     
--
------------------------------------------------------------------------------

    OEMZXMSTP DEFINITIONS ::= BEGIN

    IMPORTS
        MODULE-IDENTITY, OBJECT-TYPE, NOTIFICATION-TYPE,
        Integer32                            FROM SNMPv2-SMI
        
        RowStatus                     FROM SNMPv2-TC
        oemProd                              FROM WRS-MASTER-MIB;       

-------------------------------------------------------------------------------

    oemZxMstpMib MODULE-IDENTITY
        LAST-UPDATED    "0412220000Z"  -- Dec 22, 2004
        ORGANIZATION    "ZTE."
        CONTACT-INFO    "ZTE."

        DESCRIPTION     "Description of several ZXDSL9426 MSTP. "

        REVISION        "0412110000Z"  -- Dec 11, 2004
        DESCRIPTION     "Initial MIB creation."

        ::= { oemProd 8 }


    oemZxMstpScalarObjects                OBJECT IDENTIFIER ::= { oemZxMstpMib 1 }
    oemZxMstpTableObjects                OBJECT IDENTIFIER ::= { oemZxMstpMib 2 }

------------------------------------------------------------------------------
------------------------------------------------------------------------------
    
    oemZxMstpSpanningTreeEnable OBJECT-TYPE
        SYNTAX INTEGER 
        MAX-ACCESS read-write
        STATUS current
        DESCRIPTION
            "enable---1/disable---0"
        ::= { oemZxMstpScalarObjects 1 }

    oemZxMstpSpanningTreeForwardDelay OBJECT-TYPE
        SYNTAX INTEGER 
        MAX-ACCESS read-write
        STATUS current
        DESCRIPTION
            "4-30"
        ::= { oemZxMstpScalarObjects 2 }
        
    oemZxMstpSpanningTreeHelloTime OBJECT-TYPE
        SYNTAX INTEGER 
        MAX-ACCESS read-write
        STATUS current
        DESCRIPTION
            "1-10"
        ::= { oemZxMstpScalarObjects 3 }
        
    oemZxMstpSpanningTreeMaxAge OBJECT-TYPE
        SYNTAX INTEGER 
        MAX-ACCESS read-write
        STATUS current
        DESCRIPTION
            "6-40"
        ::= { oemZxMstpScalarObjects 4 }
        
    oemZxMstpSpanningTreeMode OBJECT-TYPE
        SYNTAX INTEGER 
        MAX-ACCESS read-write
        STATUS current
        DESCRIPTION
            "mstp/rstp/sstp    ."
        ::= { oemZxMstpScalarObjects 5 }
        
------------------------------------------------------------------------------
------------------------------------------------------------------------------
    
    oemZxMstpSpanningMstHmd5Key OBJECT-TYPE
        SYNTAX DisplayString 
        MAX-ACCESS read-write
        STATUS current
        DESCRIPTION
            "Spanning Mst Hmac Md5 Key-34byte"
        ::= { oemZxMstpScalarObjects 6 }
    
    oemZxMstpSpanningMaxHops OBJECT-TYPE
        SYNTAX INTEGER (1..40) 
        MAX-ACCESS read-write
        STATUS current
        DESCRIPTION
            "Spanning Mst Max Hops"
        DEFVAL {20}
        ::= { oemZxMstpScalarObjects 7 }
        
    oemZxMstpSpanningPaketType OBJECT-TYPE
        SYNTAX INTEGER (0..1)
        MAX-ACCESS read-write
        STATUS current
        DESCRIPTION
            "IEEE-TYPE-0  CISCO-TYPE-1"
        DEFVAL {1}
        ::= { oemZxMstpScalarObjects 8 }
        
   oemZxMstpSpanningVer3LenType OBJECT-TYPE
        SYNTAX INTEGER (0..1)
        MAX-ACCESS read-write
        STATUS current
        DESCRIPTION
            "IEEE-VER3L-0  INS-NUM-1"
        ::= { oemZxMstpScalarObjects 9 }
        
   oemZxMstpSpanningName            OBJECT-TYPE
          SYNTAX         DisplayString
          MAX-ACCESS     read-write
          STATUS         current
          DESCRIPTION
           "  "
          ::= { oemZxMstpScalarObjects  10}
          
   oemZxMstpSpanningRevision            OBJECT-TYPE
          SYNTAX         INTEGER
          MAX-ACCESS     read-write
          STATUS         current
          DESCRIPTION
           "0-65535"
          ::= { oemZxMstpScalarObjects  11}
       
------------------------------------------------------------------------------
------------------------------------------------------------------------------

--    

    oemZxMstpSpanningMstInstanceTable         OBJECT-TYPE
          SYNTAX         SEQUENCE OF OemZxMstpSpanningMstInstanceEntry
          MAX-ACCESS     not-accessible
          STATUS         current
          DESCRIPTION
           "Instance table."
          ::= { oemZxMstpTableObjects 1 }

     oemZxMstpSpanningMstInstanceEntry         OBJECT-TYPE
          SYNTAX         OemZxMstpSpanningMstInstanceEntry
          MAX-ACCESS     not-accessible
          STATUS         current
          DESCRIPTION
           "An entry in the mstp instance table."
          INDEX  {oemZxMstpSpanningMstInstanceIndex}
          ::= { oemZxMstpSpanningMstInstanceTable  1}

     OemZxMstpSpanningMstInstanceEntry    ::= SEQUENCE  
     {
          oemZxMstpSpanningMstInstanceIndex            INTEGER,
           oemZxMstpSpanningMstInstancePriority         INTEGER,
          oemZxMstpSpanningMstInstanceVlan1            OCTET STRING,
          oemZxMstpSpanningMstInstanceVlan2            OCTET STRING,
          oemZxMstpSpanningMstInstanceRowStatus        INTEGER
     }
     
     oemZxMstpSpanningMstInstanceIndex            OBJECT-TYPE
          SYNTAX         INTEGER
          MAX-ACCESS     not-accessible
          STATUS         current
          DESCRIPTION
           "The instance No."
          ::= { oemZxMstpSpanningMstInstanceEntry  1}
          
     oemZxMstpSpanningMstInstancePriority            OBJECT-TYPE
          SYNTAX         INTEGER
          MAX-ACCESS     read-write
          STATUS         current
          DESCRIPTION
           " 0-15"
          ::= { oemZxMstpSpanningMstInstanceEntry  2}
          
     oemZxMstpSpanningMstInstanceVlan1            OBJECT-TYPE
          SYNTAX         OCTET STRING
          MAX-ACCESS     read-write
          STATUS         current
          DESCRIPTION
           ""
          ::= { oemZxMstpSpanningMstInstanceEntry  3}
          
     oemZxMstpSpanningMstInstanceVlan2            OBJECT-TYPE
          SYNTAX         OCTET STRING
          MAX-ACCESS     read-write
          STATUS         current
          DESCRIPTION
           ""
          ::= { oemZxMstpSpanningMstInstanceEntry  4}

     oemZxMstpSpanningMstInstanceRowStatus            OBJECT-TYPE
          SYNTAX         INTEGER
          MAX-ACCESS     read-write
          STATUS         current
          DESCRIPTION
           "active(1),notInService(2),notReady(3),createAndGo(4),createAndWait(5),destroy(6)"
          ::= { oemZxMstpSpanningMstInstanceEntry  5}
          
------------------------------------------------------------------------------
------------------------------------------------------------------------------

--   

    oemZxMstpSpanningMstInterfaceTable         OBJECT-TYPE
          SYNTAX         SEQUENCE OF OemZxMstpSpanningMstInterfaceEntry
          MAX-ACCESS     not-accessible
          STATUS         current
          DESCRIPTION
           "Instance table."
          ::= { oemZxMstpTableObjects 2 }

     oemZxMstpSpanningMstInterfaceEntry         OBJECT-TYPE
          SYNTAX         OemZxMstpSpanningMstInterfaceEntry
          MAX-ACCESS     not-accessible
          STATUS         current
          DESCRIPTION
           "An entry in the mstp interface table."
          INDEX  {oemZxMstpSpanningMstInterfaceIndex}
          ::= { oemZxMstpSpanningMstInterfaceTable  1}

     OemZxMstpSpanningMstInterfaceEntry    ::= SEQUENCE  
     {
          oemZxMstpSpanningMstInterfaceIndex            INTEGER,
           oemZxMstpSpanningMstInterfaceEnable        INTEGER,
           oemZxMstpSpanningMstInterfaceLinkType         INTEGER
     }
     
     oemZxMstpSpanningMstInterfaceIndex            OBJECT-TYPE
          SYNTAX         INTEGER
          MAX-ACCESS     not-accessible
          STATUS         current
          DESCRIPTION
           "The interface No."
          ::= { oemZxMstpSpanningMstInterfaceEntry  1}

     oemZxMstpSpanningMstInterfaceEnable            OBJECT-TYPE
          SYNTAX         INTEGER
          MAX-ACCESS     read-write
          STATUS         current
          DESCRIPTION
           "0:disable,1:enable."
          ::= { oemZxMstpSpanningMstInterfaceEntry  2}
          
     oemZxMstpSpanningMstInterfaceLinkType            OBJECT-TYPE
          SYNTAX         INTEGER
          MAX-ACCESS     read-write
          STATUS         current
          DESCRIPTION
           " P2P-FORCE-FALSE = 0,P2P-FORCE-TRUE,P2P-AUTO"
          ::= { oemZxMstpSpanningMstInterfaceEntry  3}
          
------------------------------------------------------------------------------
------------------------------------------------------------------------------


    oemZxMstpSpanningMstInstanceInterfaceTable         OBJECT-TYPE
          SYNTAX         SEQUENCE OF OemZxMstpSpanningMstInstanceInterfaceEntry
          MAX-ACCESS     not-accessible
          STATUS         current
          DESCRIPTION
           "Instance interface table."
          ::= { oemZxMstpTableObjects 3 }

     oemZxMstpSpanningMstInstanceInterfaceEntry         OBJECT-TYPE
          SYNTAX         OemZxMstpSpanningMstInstanceInterfaceEntry
          MAX-ACCESS     not-accessible
          STATUS         current
          DESCRIPTION
           "An entry in the mstp instance interface table."
          INDEX  {oemZxMstpSpanningMstComplexInstanceIndex, oemZxMstpSpanningMstComplexInterfaceIndex}
          ::= { oemZxMstpSpanningMstInstanceInterfaceTable  1}

     OemZxMstpSpanningMstInstanceInterfaceEntry    ::= SEQUENCE  
     {
          oemZxMstpSpanningMstComplexInstanceIndex              INTEGER,
          oemZxMstpSpanningMstComplexInterfaceIndex             INTEGER,
           oemZxMstpSpanningMstInstanceInterfacePriority         INTEGER,
          oemZxMstpSpanningMstInstanceInterfacePathCost         INTEGER
     }
     
     oemZxMstpSpanningMstComplexInstanceIndex            OBJECT-TYPE
          SYNTAX         INTEGER
          MAX-ACCESS     not-accessible
          STATUS         current
          DESCRIPTION
           "The instance No."
          ::= { oemZxMstpSpanningMstInstanceInterfaceEntry  1}
          
     oemZxMstpSpanningMstComplexInterfaceIndex            OBJECT-TYPE
          SYNTAX         INTEGER
          MAX-ACCESS     not-accessible
          STATUS         current
          DESCRIPTION
           "The interface No."
          ::= { oemZxMstpSpanningMstInstanceInterfaceEntry  2}
          
     oemZxMstpSpanningMstInstanceInterfacePriority            OBJECT-TYPE
          SYNTAX         INTEGER
          MAX-ACCESS     read-write
          STATUS         current
          DESCRIPTION
           "0-15"
          ::= { oemZxMstpSpanningMstInstanceInterfaceEntry  3}
          
     oemZxMstpSpanningMstInstanceInterfacePathCost            OBJECT-TYPE
          SYNTAX         INTEGER
          MAX-ACCESS     read-write
          STATUS         current
          DESCRIPTION
           " 1-2000000"
          ::= { oemZxMstpSpanningMstInstanceInterfaceEntry  4}
          
   END

------------------------------------------------------------------------------
------------------------------------------------------------------------------
--
--  File         : oemZxSntp.mib
--  Description  : Sample TMS OEM Product Enterprise MIB for 
--                 SNTP module on 9210
--  Version      : 0.00   
--  Date         : Jan 04, 2005     
--
------------------------------------------------------------------------------

    OEMZXSNTP DEFINITIONS ::= BEGIN

    IMPORTS
        MODULE-IDENTITY, OBJECT-TYPE, NOTIFICATION-TYPE,
        IpAddress                                FROM SNMPv2-SMI
        
        DisplayString, TEXTUAL-CONVENTION       FROM SNMPv2-TC
        oemProd                                 FROM WRS-MASTER-MIB;       

-------------------------------------------------------------------------------

    oemZxSntpMib MODULE-IDENTITY
        LAST-UPDATED    "0212110000Z"  -- Dec 11, 2002
        ORGANIZATION    "ZTE."
        CONTACT-INFO    "ZTE."

        DESCRIPTION     "Description of several ZXDSL9210 stack. "

        REVISION        "0212110000Z"  -- Dec 11, 2002
        DESCRIPTION     "Initial MIB creation."

        ::= { oemProd 12 }


    oemZxSntpScalarObjects                 OBJECT IDENTIFIER ::= { oemZxSntpMib 1 }


        oemZxEdslNTPEnable OBJECT-TYPE
        SYNTAX INTEGER{
                        enable(1),
                        disable(2)
                        }
        MAX-ACCESS read-write
        STATUS current
        DESCRIPTION
            "Enable/disable NTP in this system."
        ::= { oemZxSntpScalarObjects 1}


        oemZxEdslNTPServerAddr OBJECT-TYPE
           SYNTAX     IpAddress
          MAX-ACCESS read-write
          STATUS current
          DESCRIPTION
            " the NTP server's IP address "
          ::= { oemZxSntpScalarObjects 2}
    
        oemZxEdslNTPInterval OBJECT-TYPE
           SYNTAX     INTEGER
          MAX-ACCESS read-write
          STATUS current
          DESCRIPTION
            " the NTP server's fetch time's interval time, the default is 64"
          ::= { oemZxSntpScalarObjects 3}
          
        oemZxEdslNTPSynchronize OBJECT-TYPE
           SYNTAX     INTEGER
          MAX-ACCESS read-only
          STATUS current
          DESCRIPTION
            " the NTP server whether is  synchronized or not "
          ::= { oemZxSntpScalarObjects 4}          
          
        oemZxEdslNTPStratum OBJECT-TYPE
           SYNTAX     INTEGER
          MAX-ACCESS read-only
          STATUS current
          DESCRIPTION
            " the local NTP server 's stratum "
          ::= { oemZxSntpScalarObjects 5}
          
        oemZxEdslNTPServerIP OBJECT-TYPE
           SYNTAX     IpAddress
          MAX-ACCESS read-only
          STATUS current
          DESCRIPTION
            " the NTP server's ip address, just for read only. "
          ::= { oemZxSntpScalarObjects 6}          

    oemZxedslNTPReftime OBJECT-TYPE
           SYNTAX     DisplayString (SIZE (0..64))
          MAX-ACCESS read-only
          STATUS current
          DESCRIPTION
            " the NTP reference time, just for read only. "
          ::= { oemZxSntpScalarObjects 7}

    oemZxedslNTPRefTimeZone OBJECT-TYPE
           SYNTAX     INTEGER
          MAX-ACCESS read-write
          STATUS current
          DESCRIPTION
            " the NTP reference timezone"
          ::= { oemZxSntpScalarObjects 8}

    END
