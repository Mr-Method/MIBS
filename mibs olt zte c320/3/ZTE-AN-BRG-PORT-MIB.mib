--------------------------------------------------------------------------------
-- File Name : ZTE-AN-BRG-PORT-MIB.mib
-- Date      : 2007-05-08
-- Author    : ZTE Nms dept.

--
-- Zte Bridge Port Mib for Access Node
-- 
-- 
--------------------------------------------------------------------------------

ZTE-AN-BRG-PORT-MIB    DEFINITIONS ::= BEGIN
    IMPORTS     
        RowStatus, DisplayString,MacAddress             FROM SNMPv2-TC
        MODULE-IDENTITY, enterprises, OBJECT-TYPE, IpAddress,
        Integer32, TimeTicks,Counter32,Counter64        FROM SNMPv2-SMI
        ifIndex, ifAdminStatus,ifOperStatus,ifType      FROM IF-MIB
        ZxAnIfindex,ZxAnPortList,ZxAnIdList,zxAn        FROM ZTE-AN-TC-MIB
        InetAddress, InetAddressPrefixLength            FROM INET-ADDRESS-MIB;

    zxAnBrgPortMib    MODULE-IDENTITY
        LAST-UPDATED    "200705081200Z"
        ORGANIZATION    "ZTE Corporation"
        CONTACT-INFO    "Su Chunshan
                        Mail: suchunshan@zte.com.cn
                        Tel : 021-68896292"
        DESCRIPTION     "This MIB defines zte Access Node managed objects."
        ::= { zxAn 5 }

    zxAnBrgPortObjects     OBJECT IDENTIFIER    ::=  { zxAnBrgPortMib 1 }
    zxAnBrgPortGlobalObjects OBJECT IDENTIFIER  ::=  { zxAnBrgPortMib 2 }
    zxAnBrgPortTrapObjects OBJECT IDENTIFIER    ::=  { zxAnBrgPortMib 3 }

--------------------------------------------------------------------------------
-- Following objects are defined.
-- 2.Bridge Port User-Side  Table
-- 3.Static Host Table
-- 4.Static MAC Table
-- 5.MAC Filter Table
-- 6.Static IPv6 Binding Table
-- 7.Bridge Port Statistics Table
-- 8.VMAC VLAN Table
--------------------------------------------------------------------------------

--------------------------------------------------------------------------------
-- 1.Bridge Port  Global Mgmt
--------------------------------------------------------------------------------

    zxAnBrgPktRateLimit     OBJECT IDENTIFIER ::= { zxAnBrgPortGlobalObjects 1 }
    
    zxAnBrgBroadcastRateLimit  OBJECT-TYPE 
        SYNTAX      Integer32(0..65535) 
        UNITS       "pps"
        MAX-ACCESS  read-write
        STATUS      current
        DESCRIPTION 
            "Maximum broadcast package rate.
             Value 65535 means no limit."
        DEFVAL  { 100 }
        ::= { zxAnBrgPktRateLimit 1 }

    zxAnBrgMulticastRateLimit  OBJECT-TYPE 
        SYNTAX      Integer32(0..65535) 
        UNITS       "pps"
        MAX-ACCESS  read-write
        STATUS      current
        DESCRIPTION
            "Maximum multicast package rate.
            Value 65535 means no limit."
        DEFVAL  { 65535 }
        ::= { zxAnBrgPktRateLimit 2 }

    zxAnBrgFloodingRateLimit  OBJECT-TYPE 
        SYNTAX      Integer32(0..65535) 
        UNITS       "pps"
        MAX-ACCESS  read-write
        STATUS      current
        DESCRIPTION
            "Maximum flooding package rate.
             Value 65535 means no limit."
        DEFVAL  { 100 }
        ::= { zxAnBrgPktRateLimit 3 }

    zxAnBrgBpduFloodingRateLimit  OBJECT-TYPE 
        SYNTAX      Integer32(0..65535) 
        UNITS       "pps"
        MAX-ACCESS  read-write
        STATUS      current
        DESCRIPTION
            "Maximum BPDU(Bridge Protocol Data Unit) flooding package rate.
             Value 65535 means no limit."
        DEFVAL  { 65535 }
        ::= { zxAnBrgPktRateLimit 4 }

    zxAnBrgUnknownUcastFloodingEn  OBJECT-TYPE
        SYNTAX      INTEGER
        {
            enabled(1),
            disabled(2)
        }
        MAX-ACCESS  read-write
        STATUS      current
        DESCRIPTION
            "Enable/disable the unknown unicast flooding."
        DEFVAL  { enabled }                   
        ::= { zxAnBrgPktRateLimit 5 }

    zxAnBrgUnknownMcastFloodingEn OBJECT-TYPE
        SYNTAX      INTEGER
        {
            enabled(1),
            disabled(2)
        }
        MAX-ACCESS  read-write
        STATUS      current
        DESCRIPTION
            "Enable/disable the unknown multicast flooding."
        DEFVAL  { disabled }                   
        ::= { zxAnBrgPktRateLimit 6 }

    zxAnBrgVirtualMac  OBJECT IDENTIFIER ::= { zxAnBrgPortGlobalObjects 2 }
  
    zxAnBrgVirtualMacKey  OBJECT-TYPE 
        SYNTAX      Integer32(0..65535) 
        MAX-ACCESS  read-create
        STATUS      current
        DESCRIPTION
            "Set this key for generate the virtual mac."
        DEFVAL  { 0 }
        ::= { zxAnBrgVirtualMac 1 }

    zxAnBrgVirtualMacFormat  OBJECT-TYPE 
        SYNTAX      INTEGER
        {   
            tpsa(1),
            magyarTel(2)
        }
        MAX-ACCESS  read-create
        STATUS      current
        DESCRIPTION
            "Format of virtual MAC."
        DEFVAL  { tpsa }
        ::= { zxAnBrgVirtualMac 2 }

    zxAnBrgVirtualMacUserDefined  OBJECT-TYPE 
        SYNTAX      Integer32(0..63) 
        MAX-ACCESS  read-create
        STATUS      current
        DESCRIPTION
            "Reserved bits, operator can configure it. 
             It is invalid in TPSA format."
        DEFVAL  { 0 }
        ::= { zxAnBrgVirtualMac 3 }
        
--##################  IP Soruce Guard 4 Poland ##################
--##################    Please Keep the oid !!!    ##################
--#    zxAnBrgPktSrcLimit  OBJECT IDENTIFIER ::= { zxAnBrgPortGlobalObjects 3 }   
--#   
--#    zxAnBrgPktAntiIpSpoofAdminStatus   OBJECT-TYPE
--#    
--#        SYNTAX      INTEGER
--#            {
--#            enable(1),
--#            disable(2)
--#            
--#            }
--#        MAX-ACCESS  read-write
--#        STATUS      current
--#        DESCRIPTION ""
--#       ::=  { zxAnBrgPktSrcLimit  1 }        
--##################  IP Soruce Guard 4 Poland ##################
--##################    Please Keep the oid !!!    ##################

    zxAnBrgPortCapabilities OBJECT-TYPE
        SYNTAX     BITS {
            vdslAtmPtmCoexist(0),
            shdslAtmEfmCoexist(1),
            supportPppoeRateLimit(2)
        }
        MAX-ACCESS  read-only
        STATUS      current
        DESCRIPTION
            "The bridge port management capabilities of this equipment.
            The bit value 1 means the function represented by this bit is 
            supported by this equipment.  

            vdslAtmPtmCoexist(0): value 1 means supporting ATM and PTM of 
                                  VDSL port coexist.
            shdslAtmEfmCoexist(1): value 1 means supporting ATM and EFM of 
                                  SHDSL port coexist.
            supportPppoeRateLimit(2): value 1 means supporting 
                                      zxAnBrgUsrPortPppoeRateLimit and
                                      zxAnBrgUsrPortMaxPppoeRate in the 
                                      zxAnBrgUsrSidePortTable.

            NOTE: No recomanded to display it in NMS."
        ::= { zxAnBrgPortGlobalObjects 50 } 

--------------------------------------------------------------------------------
-- 2.Bridge Port User-Side  Table
--------------------------------------------------------------------------------

    zxAnBrgUsrSidePortTable  OBJECT-TYPE
        SYNTAX      SEQUENCE OF ZxAnBrgUsrSidePortEntry
        MAX-ACCESS  not-accessible
        STATUS      current
        DESCRIPTION
            "This table includes the bridge port user-side information."
        ::= { zxAnBrgPortObjects 1 }

    zxAnBrgUsrSidePortEntry   OBJECT-TYPE
        SYNTAX      ZxAnBrgUsrSidePortEntry
        MAX-ACCESS  not-accessible
        STATUS      current
        DESCRIPTION
            "An entry in zxAnBrgUsrSidePortTable."
        INDEX  { ifIndex, zxAnBrgUsrPortId }
        ::= { zxAnBrgUsrSidePortTable 1 }

    ZxAnBrgUsrSidePortEntry  ::= SEQUENCE {
        zxAnBrgUsrPortId                 Integer32,
        zxAnBrgUsrPortAdminStatus        INTEGER,
        zxAnBrgUsrPortPvcVpi             Integer32,
        zxAnBrgUsrPortPvcVci             Integer32,
        zxAnBrgUsrPortBindIpEnable       INTEGER,
        zxAnBrgUsrPortBindMacEnable      INTEGER,
        zxAnBrgUsrPortMacLearnLimit      INTEGER,
        zxAnBrgUsrPortMaxMacLearn        Integer32,
        zxAnBrgUsrPortBrdcastRateLimit   INTEGER,
        zxAnBrgUsrPortMaxBroadcastRate   Integer32,
        zxAnBrgUsrPortDhcpRateLimit      INTEGER,
        zxAnBrgUsrPortMaxDhcpRate        Integer32,
        zxAnBrgUsrPortIgmpRateLimit      INTEGER,
        zxAnBrgUsrPortMaxIgmpRate        Integer32,
        zxAnBrgUsrPortEncapsType         INTEGER,
        zxAnBrgUserPortBrdcastEnable     INTEGER,
        zxAnBrgUserPortFloodEnable       INTEGER,    
        zxAnBrgUserPortActualEncapsType  INTEGER,        
        zxAnBrgUserPortVirtualMacEnable  INTEGER,
        zxAnBrgUserPortTxNetDataRate     Integer32,
        zxAnBrgUserPortRxNetDataRate     Integer32,
        zxAnBrgUsrPortPppoeRateLimit     INTEGER,
        zxAnBrgUsrPortMaxPppoeRate       Integer32,
        zxAnBrgUsrPortRowStatus          RowStatus
        }

    zxAnBrgUsrPortId  OBJECT-TYPE 
        SYNTAX      Integer32
        MAX-ACCESS  not-accessible
        STATUS      current
        DESCRIPTION
            "Bridge port id in this interface."
        ::= { zxAnBrgUsrSidePortEntry 1 }

    zxAnBrgUsrPortAdminStatus  OBJECT-TYPE 
        SYNTAX      INTEGER {
            up(1),
            down(2)
        }
        MAX-ACCESS  read-create
        STATUS      current
        DESCRIPTION
            "Enable/disable bridge port."
        ::= { zxAnBrgUsrSidePortEntry 2 }

    zxAnBrgUsrPortPvcVpi  OBJECT-TYPE 
        SYNTAX      Integer32
        MAX-ACCESS  read-create
        STATUS      current
        DESCRIPTION
            "VPI of PVC in this bridge port."
        ::= { zxAnBrgUsrSidePortEntry 3 }

    zxAnBrgUsrPortPvcVci  OBJECT-TYPE 
        SYNTAX      Integer32
        MAX-ACCESS  read-create
        STATUS      current
        DESCRIPTION
            "VCI of PVC in this bridge port."
        ::= { zxAnBrgUsrSidePortEntry 4 }

    zxAnBrgUsrPortBindIpEnable  OBJECT-TYPE 
        SYNTAX      INTEGER {
            enable(1),
            disable(2)
        }
        MAX-ACCESS  read-create
        STATUS      current
        DESCRIPTION
            "Enable/disable IP binding."
        ::= { zxAnBrgUsrSidePortEntry 5 }

    zxAnBrgUsrPortBindMacEnable  OBJECT-TYPE 
        SYNTAX      INTEGER {
            enable(1),
            disable(2)
        }
        MAX-ACCESS  read-create
        STATUS      current
        DESCRIPTION
            "Enable/disable MacAddress binding."
        ::= { zxAnBrgUsrSidePortEntry 6 }

    zxAnBrgUsrPortMacLearnLimit  OBJECT-TYPE 
        SYNTAX      INTEGER {
            enable(1),
            disable(2)
        }
        MAX-ACCESS  read-create
        STATUS      current
        DESCRIPTION
            "Enable/disable MAC learning limit."
        ::= { zxAnBrgUsrSidePortEntry 7 }

    zxAnBrgUsrPortMaxMacLearn  OBJECT-TYPE 
        SYNTAX      Integer32 
        UNITS       "package"
        MAX-ACCESS  read-create
        STATUS      current
        DESCRIPTION
            "Max MAC limit learnt."
        ::= { zxAnBrgUsrSidePortEntry 8 }

    zxAnBrgUsrPortBrdcastRateLimit  OBJECT-TYPE 
        SYNTAX      INTEGER {
            enable(1),
            disable(2)
        }
        MAX-ACCESS  read-create
        STATUS      current
        DESCRIPTION
            "Enable/disable broadcast package rate limit."
        ::= { zxAnBrgUsrSidePortEntry 9 }

    zxAnBrgUsrPortMaxBroadcastRate  OBJECT-TYPE 
        SYNTAX      Integer32 
        UNITS       "pps"  -- package/s
        MAX-ACCESS  read-create
        STATUS      current
        DESCRIPTION
            "Maximum Broadcast package rate limit."
        ::= { zxAnBrgUsrSidePortEntry 10 }

    zxAnBrgUsrPortDhcpRateLimit  OBJECT-TYPE 
        SYNTAX      INTEGER {
            enable(1),
            disable(2)
        }
        MAX-ACCESS  read-create
        STATUS      current
        DESCRIPTION
            "Enable/disable DHCP package rate limit."
        ::= { zxAnBrgUsrSidePortEntry 11 }

    zxAnBrgUsrPortMaxDhcpRate  OBJECT-TYPE
        SYNTAX      Integer32 
        UNITS       "pps"  -- package/s
        MAX-ACCESS  read-create
        STATUS      current
        DESCRIPTION
            "Maximum DHCP package rate limit."
        ::= { zxAnBrgUsrSidePortEntry 12 }

    zxAnBrgUsrPortIgmpRateLimit  OBJECT-TYPE 
        SYNTAX      INTEGER {
            enable(1),
            disable(2)
        }
        MAX-ACCESS  read-create
        STATUS      current
        DESCRIPTION
            "Enable/disable DHCP package rate limit."
        ::= { zxAnBrgUsrSidePortEntry 13 }

    zxAnBrgUsrPortMaxIgmpRate  OBJECT-TYPE 
        SYNTAX      Integer32 
        UNITS       "pps"  -- package/s
        MAX-ACCESS  read-create
        STATUS      current
        DESCRIPTION
            "Maximum DHCP package rate limit."
        ::= { zxAnBrgUsrSidePortEntry 14 }

    zxAnBrgUsrPortEncapsType  OBJECT-TYPE 
        SYNTAX      INTEGER {
            eoaLlc(1),    -- EoA(1483B)-LLC
            eoaVcmux(2),  -- EoA(1483B)-VCMUX
            pppoaLlc(3), 
            pppoaVcmux(4),
            ipoaLlc(5),   -- IPoA(1483R)-LLC
            ipoaVcmux(6), -- IPoA(1483R)-VCMUX
            aoe(7),
            modemMgmt(8),
            auto(9),
            aoeAal0(10)
        }
        MAX-ACCESS  read-create
        STATUS      current
        DESCRIPTION
            "Encapsulation of this bridge port."
        ::= { zxAnBrgUsrSidePortEntry 15 }

    zxAnBrgUserPortBrdcastEnable  OBJECT-TYPE
        SYNTAX      INTEGER {
            enable(1),
            disable(2)
        }
        MAX-ACCESS  read-create
        STATUS      current
        DESCRIPTION
            "enable(1): enable Broadcast.
             disable(2): disable Broadcast."
        DEFVAL  { disable }
        ::= { zxAnBrgUsrSidePortEntry 16 }

    zxAnBrgUserPortFloodEnable  OBJECT-TYPE
        SYNTAX      INTEGER {
            enable(1),
            disable(2)
        }
        MAX-ACCESS  read-create
        STATUS      current
        DESCRIPTION
            "enable(1):  enable Flood.
             disable(2): disable Flood."
        DEFVAL  { disable }
        ::= { zxAnBrgUsrSidePortEntry 17 }                

    zxAnBrgUserPortActualEncapsType OBJECT-TYPE 
        SYNTAX      INTEGER {
            eoaLlc(1),    -- EoA(1483B)-LLC
            eoaVcmux(2),  -- EoA(1483B)-VCMUX
            pppoaLlc(3), 
            pppoaVcmux(4),
            ipoaLlc(5),   -- IPoA(1483R)-LLC
            ipoaVcmux(6), -- IPoA(1483R)-VCMUX
            aoe(7),
            modemMgmt(8),
            unknown(9),
            aoeAal0(10)
        }
        MAX-ACCESS  read-only
        STATUS      current
        DESCRIPTION
            "Actual Encapsulation of this bridge port."
        ::= { zxAnBrgUsrSidePortEntry 18 }

    zxAnBrgUserPortVirtualMacEnable  OBJECT-TYPE
        SYNTAX      INTEGER {
            enable(1),
            disable(2)
        }
        MAX-ACCESS  read-create
        STATUS      current
        DESCRIPTION
            "Enable/disable to configure the port status for virtual MAC."
        DEFVAL  { disable }
        ::= { zxAnBrgUsrSidePortEntry 19 }   

    zxAnBrgUserPortTxNetDataRate  OBJECT-TYPE 
        SYNTAX      Integer32
        UNITS       "kbps"
        MAX-ACCESS  read-only
        STATUS      current
        DESCRIPTION
            "Current actual data transmitted speed at this bridge port."
        ::= { zxAnBrgUsrSidePortEntry 20 }

    zxAnBrgUserPortRxNetDataRate  OBJECT-TYPE 
        SYNTAX      Integer32
        UNITS       "kbps"
        MAX-ACCESS  read-only
        STATUS      current
        DESCRIPTION
            "Current actual data received speed at this bridge port."
        ::= { zxAnBrgUsrSidePortEntry 21 }

    zxAnBrgUsrPortPppoeRateLimit  OBJECT-TYPE 
        SYNTAX      INTEGER {
            enabled(1),
            disabled(2)
        }
        MAX-ACCESS  read-create
        STATUS      current
        DESCRIPTION
            "Enable/disable PPPoE package rate limit."
        DEFVAL  { disabled }
        ::= { zxAnBrgUsrSidePortEntry 22 }

    zxAnBrgUsrPortMaxPppoeRate  OBJECT-TYPE 
        SYNTAX      Integer32(0..255)
        UNITS       "pps"
        MAX-ACCESS  read-create
        STATUS      current
        DESCRIPTION
            "Maximum PPPoE package rate.
             Value 0 means discarding PPPoE packets."
        DEFVAL  { 255 }
        ::= { zxAnBrgUsrSidePortEntry 23 }

    zxAnBrgUsrPortRowStatus  OBJECT-TYPE    
        SYNTAX      RowStatus
        MAX-ACCESS  read-create
        STATUS      current
        DESCRIPTION
            "RowStatus of this table."
        ::= { zxAnBrgUsrSidePortEntry 50 }

--------------------------------------------------------------------------------
-- 3.Static Host Table
--------------------------------------------------------------------------------
    zxAnBrgPortStaticHostTable   OBJECT-TYPE
        SYNTAX      SEQUENCE  OF  ZxAnBrgPortStaticHostEntry
        MAX-ACCESS  not-accessible
        STATUS      current
        DESCRIPTION "This table includes the bridge port host ip information."
        ::=  { zxAnBrgPortObjects  2 }

    zxAnBrgPortStaticHostEntry   OBJECT-TYPE
        SYNTAX      ZxAnBrgPortStaticHostEntry
        MAX-ACCESS  not-accessible
        STATUS      current
        DESCRIPTION "An entry in zxAnBrgPortStaticHostTable."
        INDEX       { ifIndex, zxAnBrgUsrPortId,zxAnBrgPortStaticHostIp }
        ::=  { zxAnBrgPortStaticHostTable 1 }

    ZxAnBrgPortStaticHostEntry  ::=  SEQUENCE 
    {
        zxAnBrgPortStaticHostIp        IpAddress,
        zxAnBrgPortStaticHostRowStatus RowStatus
    }
        

    zxAnBrgPortStaticHostIp OBJECT-TYPE 
        SYNTAX          IpAddress 
        MAX-ACCESS      not-accessible
        STATUS          current
        DESCRIPTION     "IP  bund to this port."
        ::=  {  zxAnBrgPortStaticHostEntry  1  }
        

    zxAnBrgPortStaticHostRowStatus    OBJECT-TYPE    
        SYNTAX            RowStatus
        MAX-ACCESS      read-create
        STATUS          current
        DESCRIPTION     "RowStatus of this table."
        ::=  {  zxAnBrgPortStaticHostEntry  2  }
        
                
        
--------------------------------------------------------------------------------
-- 4.Static MAC Table
--------------------------------------------------------------------------------
    zxAnBrgPortStaticMacTable   OBJECT-TYPE
        SYNTAX      SEQUENCE  OF  ZxAnBrgPortStaticMacEntry
        MAX-ACCESS  not-accessible
        STATUS      current
        DESCRIPTION "This table includes the bridge port static MAC information."
        ::=  { zxAnBrgPortObjects  3 }

    zxAnBrgPortStaticMacEntry   OBJECT-TYPE
        SYNTAX      ZxAnBrgPortStaticMacEntry
        MAX-ACCESS  not-accessible
        STATUS      current
        DESCRIPTION "An entry in zxAnBrgPortStaticMacTable."
        INDEX       { ifIndex, zxAnBrgUsrPortId,zxAnBrgPortStaticMac }
        ::=  { zxAnBrgPortStaticMacTable 1 }

    ZxAnBrgPortStaticMacEntry  ::=  SEQUENCE 
    {
        zxAnBrgPortStaticMac          MacAddress,
        zxAnSecIfMacBindingRowStatus RowStatus
    }
        
    zxAnBrgPortStaticMac OBJECT-TYPE 
        SYNTAX          MacAddress 
        MAX-ACCESS      not-accessible
        STATUS          current
        DESCRIPTION     "MacAddress bund to this port."
        ::=  {  zxAnBrgPortStaticMacEntry  1  }
        

    zxAnSecIfMacBindingRowStatus    OBJECT-TYPE    
        SYNTAX            RowStatus
        MAX-ACCESS      read-create
        STATUS          current
        DESCRIPTION     "RowStatus of this table."
        ::=  {  zxAnBrgPortStaticMacEntry  2  }
        
--------------------------------------------------------------------------------
-- 5.MAC Filter Table
--------------------------------------------------------------------------------
    zxAnBrgPortFilterMacTable   OBJECT-TYPE
        SYNTAX      SEQUENCE  OF  ZxAnBrgPortFilterMacEntry
        MAX-ACCESS  not-accessible
        STATUS      current
        DESCRIPTION "This table includes the bridge port Filter MAC information."
        ::=  { zxAnBrgPortObjects  4 }

    zxAnBrgPortFilterMacEntry   OBJECT-TYPE
        SYNTAX      ZxAnBrgPortFilterMacEntry
        MAX-ACCESS  not-accessible
        STATUS      current
        DESCRIPTION "An entry in zxAnBrgPortStaticMacTable."
        INDEX       { ifIndex, zxAnBrgUsrPortId,zxAnBrgPortFilterMac }
        ::=  { zxAnBrgPortFilterMacTable 1 }

    ZxAnBrgPortFilterMacEntry  ::=  SEQUENCE 
    {
        zxAnBrgPortFilterMac          MacAddress,
        zxAnSecIfMacFilterRowStatus RowStatus
    }
        
    zxAnBrgPortFilterMac OBJECT-TYPE 
        SYNTAX          MacAddress 
        MAX-ACCESS      not-accessible
        STATUS          current
        DESCRIPTION     "Filter MacAddress of this port."
        ::=  {  zxAnBrgPortFilterMacEntry  1  }
        

    zxAnSecIfMacFilterRowStatus    OBJECT-TYPE    
        SYNTAX            RowStatus
        MAX-ACCESS      read-create
        STATUS          current
        DESCRIPTION     "RowStatus of this table."
        ::=  {  zxAnBrgPortFilterMacEntry  2  }
    
--------------------------------------------------------------------------------

--##################  IP Soruce Guard 4 Poland ##################
--##################    Please Keep the oid !!!    ##################
--#--------------------------------------------------------------------------------
--#-- 6.Anti IP Spoof Table
--#--------------------------------------------------------------------------------
--#    zxAnBrgPortAntiIpSpoofTable   OBJECT-TYPE
--#        SYNTAX      SEQUENCE  OF  ZxAnBrgPortAntiIpSpoofEntry
--#        MAX-ACCESS  not-accessible
--#        STATUS      current
--#        DESCRIPTION ""
--#        ::=  { zxAnBrgPortObjects  5 }
--#
--#    zxAnBrgPortAntiIpSpoofEntry   OBJECT-TYPE
--#        SYNTAX      ZxAnBrgPortAntiIpSpoofEntry
--#        MAX-ACCESS  not-accessible
--#        STATUS      current
--#        DESCRIPTION "An entry in zxAnBrgPortAntiIpSpoofTable."
--#        INDEX       { ifIndex, zxAnBrgUsrPortId}
--#        ::=  { zxAnBrgPortAntiIpSpoofTable 1 }
--#
--#    ZxAnBrgPortAntiIpSpoofEntry  ::=  SEQUENCE 
--#    {
--#        zxAnBrgPortAntiIpSpoofAdminStatus          INTEGER
--#    }
--#        
--#    zxAnBrgPortAntiIpSpoofAdminStatus OBJECT-TYPE 
--#        SYNTAX      INTEGER
--#            {
--#            enable(1),
--#            disable(2)
--#            
--#            }
--#        MAX-ACCESS  read-write
--#        STATUS      current
--#        DESCRIPTION ""
--#        ::=  {  zxAnBrgPortAntiIpSpoofEntry  1  }        
--#   
--##################  IP Soruce Guard 4 Poland ##################
--##################    Please Keep the oid !!!    ##################

--------------------------------------------------------------------------------
-- 6.Static IPv6 Binding Table
--------------------------------------------------------------------------------

    zxAnBrgPortIpv6Objects  OBJECT IDENTIFIER
        ::=  { zxAnBrgPortObjects  10 }
        
    zxAnBrgPortIpv6IpBindTable    OBJECT-TYPE
        SYNTAX        SEQUENCE  OF  ZxAnBrgPortIpv6IpBindEntry
        MAX-ACCESS    not-accessible
        STATUS        current
        DESCRIPTION    "The bridge port IP binding information table.
                       Only traffic from these IP addresses is valid and 
                       allowed to pass through the interface."
        ::=  { zxAnBrgPortIpv6Objects  1 }

    zxAnBrgPortIpv6IpBindEntry    OBJECT-TYPE
        SYNTAX        ZxAnBrgPortIpv6IpBindEntry
        MAX-ACCESS    not-accessible
        STATUS        current
        DESCRIPTION   "The bridge port IP binding information entry."
        INDEX         { ifIndex, zxAnBrgUsrPortId, zxAnBrgPortIpv6IpBindIp }
        ::=  { zxAnBrgPortIpv6IpBindTable 1 }

    ZxAnBrgPortIpv6IpBindEntry  ::=  SEQUENCE {     
        zxAnBrgPortIpv6IpBindIp         InetAddress,
        zxAnBrgPortIpv6IpBindIpPfxLen   InetAddressPrefixLength,
        zxAnBrgPortIpv6IpBindRowStatus  RowStatus
        }
            
    zxAnBrgPortIpv6IpBindIp  OBJECT-TYPE    
        SYNTAX               InetAddress
        MAX-ACCESS           not-accessible
        STATUS               current
        DESCRIPTION          "The IPv6 address for IP binding."
        ::=  {  zxAnBrgPortIpv6IpBindEntry  1  }
        
    zxAnBrgPortIpv6IpBindIpPfxLen   OBJECT-TYPE 
        SYNTAX          InetAddressPrefixLength
        MAX-ACCESS      read-create
        STATUS          current
        DESCRIPTION     "The prefix length of IPv6 address.
                        This parameter is reserved for further extending."
        ::=  {  zxAnBrgPortIpv6IpBindEntry  2  }

    zxAnBrgPortIpv6IpBindRowStatus    OBJECT-TYPE    
        SYNTAX          RowStatus 
        MAX-ACCESS      read-create
        STATUS          current
        DESCRIPTION     "The row status of this entry."
        ::=  {  zxAnBrgPortIpv6IpBindEntry  10  }

--------------------------------------------------------------------------------
-- 7.Bridge Port Statistics Table
--------------------------------------------------------------------------------

    zxAnBrgPortStatsObjects  OBJECT IDENTIFIER  ::=  { zxAnBrgPortObjects  11 }
    
    zxAnBrgPortStatsTable    OBJECT-TYPE
        SYNTAX        SEQUENCE  OF  ZxAnBrgPortStatsEntry
        MAX-ACCESS    not-accessible
        STATUS        current
        DESCRIPTION    
            "Bridge port statistics table."
        ::=  { zxAnBrgPortStatsObjects  2 }

    zxAnBrgPortStatsEntry    OBJECT-TYPE
        SYNTAX      ZxAnBrgPortStatsEntry
        MAX-ACCESS  not-accessible
        STATUS      current
        DESCRIPTION   
            "Bridge port statistics entry."
        INDEX       { ifIndex, zxAnBrgUsrPortId }
        ::=  { zxAnBrgPortStatsTable 1 }

    ZxAnBrgPortStatsEntry  ::=  SEQUENCE {     
        zxAnBrgPortInDiscards        Counter64,
        zxAnBrgPortOutDiscards       Counter64
        }
        
    zxAnBrgPortInDiscards OBJECT-TYPE 
        SYNTAX          Counter64
        MAX-ACCESS      read-only
        STATUS          current
        DESCRIPTION     
            "Received discarded packet number at this bridge port."
        ::=  {  zxAnBrgPortStatsEntry  1  }
        
    zxAnBrgPortOutDiscards OBJECT-TYPE 
        SYNTAX          Counter64
        MAX-ACCESS      read-only
        STATUS          current
        DESCRIPTION     
            "Transmitted discarded packet number at this bridge port."
        ::=  {  zxAnBrgPortStatsEntry  2  }

-------------------------------------------------------------------------------
-- 8.VMAC VLAN Table
-------------------------------------------------------------------------------

    zxAnBrgVirtualMacObjects  OBJECT IDENTIFIER ::= { zxAnBrgPortObjects 12 }
    
    zxAnBrgVirtualMacVlanTable    OBJECT-TYPE
        SYNTAX     SEQUENCE  OF  ZxAnBrgVirtualMacVlanEntry
        MAX-ACCESS not-accessible
        STATUS     current
        DESCRIPTION   
            "Virtual MAC VLAN table."
        ::=  { zxAnBrgVirtualMacObjects  2 }

    zxAnBrgVirtualMacVlanEntry    OBJECT-TYPE
        SYNTAX     ZxAnBrgVirtualMacVlanEntry
        MAX-ACCESS not-accessible
        STATUS     current
        DESCRIPTION   
            "The zxAnBrgVirtualMacVlanTable entry."
        INDEX  { zxAnBrgVirtualMacVid }
        ::=  { zxAnBrgVirtualMacVlanTable 1 }

    ZxAnBrgVirtualMacVlanEntry  ::=  SEQUENCE {     
        zxAnBrgVirtualMacVid            Integer32,
        zxAnBrgVirtualMacVlanRowStatus  RowStatus
        }
            
    zxAnBrgVirtualMacVid  OBJECT-TYPE    
        SYNTAX     Integer32(1..4094)
        MAX-ACCESS not-accessible
        STATUS     current
        DESCRIPTION
            "VLAN ID."
        ::= { zxAnBrgVirtualMacVlanEntry 1 }
        
    zxAnBrgVirtualMacVlanRowStatus OBJECT-TYPE 
        SYNTAX     RowStatus
        MAX-ACCESS read-create
        STATUS     current
        DESCRIPTION 
            "The status of this conceptual row.

            The supported actions of this conceptual row only include:
            'createAndGo' and 'destroy'.

            To create a row in this table, a manager must set this object to 
            createAndGo(4), and must comply with the multi-variables binding 
            rule described in zxAnBrgVirtualMacVlanEntry.

            To delete a row in this table, a manager must set this object to 
            destroy(6).

            To get this object, the agent always returns active(1)."
        ::= { zxAnBrgVirtualMacVlanEntry 50 }

-- 9.Trap Definations
-------------------------------------------------------------------------------
END
