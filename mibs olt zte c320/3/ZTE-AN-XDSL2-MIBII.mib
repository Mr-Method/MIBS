--------------------------------------------------------------------------
-- File Name : ZTE-AN-VDSL-MIBII.mib
-- Date      : 2008-4-9
-- Author    : ZTE Nms dept.

--
-- Zte VDSL Mib for Access Node
--------------------------------------------------------------------------
ZTE-AN-XDSL2-MIBII DEFINITIONS ::= BEGIN

    IMPORTS
       MODULE-IDENTITY, OBJECT-TYPE, Unsigned32,Integer32, Counter32,
       NOTIFICATION-TYPE                                        FROM SNMPv2-SMI
       enterprises                                              FROM SNMPv2-SMI
       ifIndex                                                  FROM IF-MIB
       DisplayString,TEXTUAL-CONVENTION,TruthValue,RowStatus    FROM SNMPv2-TC
       HCPerfIntervalThreshold,HCPerfTimeElapsed       FROM HC-PerfHist-TC-MIB
       SnmpAdminString                                 FROM SNMP-FRAMEWORK-MIB
       
       xdsl2PMLineCurrEntry,xdsl2PMLineHist15MinEntry,xdsl2PMLineHist1DayEntry,
       xdsl2PMChCurrEntry,xdsl2PMChHist15MinEntry,xdsl2PMChHist1DEntry,       
       xdsl2SCStatusDirection, xdsl2SCStatusSegment,xdsl2LineBandEntry       
                                                                FROM VDSL2-LINE-MIB
       Xdsl2Unit, Xdsl2Direction, Xdsl2Band, Xdsl2TransmissionModeType,
       Xdsl2RaMode,Xdsl2InitResult,Xdsl2OperationModes,Xdsl2PowerMngState,
       Xdsl2ConfPmsForce,Xdsl2LinePmMode,
       Xdsl2LineLdsf,Xdsl2LdsfResult,Xdsl2SymbolProtection,
       Xdsl2MaxBer,Xdsl2ScMaskDs,Xdsl2ScMaskUs,Xdsl2CarMask,
       Xdsl2PsdMaskDs, Xdsl2PsdMaskUs, Xdsl2Tssi,
       Xdsl2LastTransmittedState, Xdsl2LineStatus,
       Xdsl2ChAtmStatus, Xdsl2ChPtmStatus, Xdsl2UpboKLF, Xdsl2BandUs,
       Xdsl2LineProfiles, Xdsl2LineUs0Mask, Xdsl2LineClassMask,
       Xdsl2LineLimitMask, Xdsl2LineUs0Disable, Xdsl2RfiBands,
       Xdsl2LineSnrMode,Xdsl2LineBpsc,Xdsl2BpscResult,Xdsl2LineReset,
       Xdsl2SymbolProtection8,Xdsl2ChInitPolicy,Xdsl2LineCeFlag,
       Xdsl2MrefPsdDs,Xdsl2MrefPsdUs,Xdsl2LinePsdMaskSelectUs
                                                       FROM   VDSL2-LINE-TC-MIB
       ZxAnIfindex                                     FROM   ZTE-AN-TC-MIB
       ZxAnXdsl2TransmissionModeType                   FROM   ZTE-AN-XDSL2-MIB;



    zxAnXdsl2Mib MODULE-IDENTITY
        LAST-UPDATED    "200901061500Z"
        ORGANIZATION "ZTE Corporation"
        CONTACT-INFO "ZTE NMS dept. 
                      Su Chunshan   68896292 "
        DESCRIPTION  "This MIB defines managed objects of zte xDSL mgmt . "
        ::= { zxAn 1001 }
         
    zte OBJECT IDENTIFIER ::= { enterprises 3902 }
    zxAn OBJECT IDENTIFIER ::= { zte 1015 } 
         
    zxAnXdsl2Objects            OBJECT IDENTIFIER  ::= {zxAnXdsl2Mib 1}
    zxAnXdsl2TrapObjects        OBJECT IDENTIFIER  ::= {zxAnXdsl2Mib 3}

    zxAnXdsl2GlobalObjects      OBJECT IDENTIFIER  ::= {zxAnXdsl2Objects 1}
    zxAnXdsl2Line               OBJECT IDENTIFIER  ::= {zxAnXdsl2Objects 2}
    zxAnXdsl2LineProfile        OBJECT IDENTIFIER  ::= {zxAnXdsl2Objects 3}
    zxAnXdsl2AlarmProfile       OBJECT IDENTIFIER  ::= {zxAnXdsl2Objects 4}
    zxAnXdsl2PMLine             OBJECT IDENTIFIER  ::= {zxAnXdsl2Objects 5}
    zxAnXdsl2PMChannel          OBJECT IDENTIFIER  ::= {zxAnXdsl2Objects 6}
    zxAnXdsl2LineTest           OBJECT IDENTIFIER  ::= {zxAnXdsl2Objects 7}
    zxAnXdsl2Vectoring          OBJECT IDENTIFIER  ::= {zxAnXdsl2Objects 8}
    zxAnXdsl2Status             OBJECT IDENTIFIER  ::= {zxAnXdsl2Objects 9}

--------------------------------------------------------------------------------
-- Following objects are defined.
-- zxAnXdsl2GlobalObjects
-- zxAnXdsl2LnTable

-- zxAnXdsl2DsDataRateConfPrfTable
-- zxAnXdsl2UsDataRateConfPrfTable
-- zxAnXdsl2SpectrumConfPrfTable
-- zxAnXdsl2DpboConfPrfTable
-- zxAnXdsl2UpboConfPrfTable
-- zxAnXdsl2SnrMarginConfPrfTable
-- zxAnXdsl2DelayInpConfPrfTable
-- zxAnXdsl2VirtualNoiseConfPrfTable
-- zxAnXdsl2RfiConfPrfTable
-- zxAnXdsl2ProfModeSpecTable 
-- zxAnXdsl2ExtConfPrfTable
-- zxAnXdsl2SosConfPrfTable
-- zxAnXdsl2InmConfPrfTable

-- zxAnXdsl2AlmThreshPrfTable

-- zxAnXdsl2PMLineCurrTable
-- zxAnXdsl2PMLineHist15MinTable
-- zxAnXdsl2PMLineHist1DayTable
-- zxAnXdsl2PMChCurrTable
-- zxAnXdsl2PMChHist15MinTable
-- zxAnXdsl2PMChHist1DayTable

-- zxAnXdsl2SeltConfTable
-- zxAnXdsl2SeltLineStatusTable
-- zxAnXdsl2SeltSCStatusTable

-- zxAnXdsl2MeltConfTable
-- zxAnXdsl2MeltStatusTable

-- zxAnXdsl2FextCoefficientTable
-- zxAnXdsl2VectoringCrosstalkTable
-- zxAnXdsl2SCStatusTable
-- zxAnXdsl2SeltRawDataTable
-- zxAnXdsl2XlogSampleTable
-- Trap



-- xdsl2LineBandTable        see VDSL2-LINE-MIB xdsl2LineBandTable
-- xdsl2ChannelStatusTable   see VDSL2-LINE-MIB xdsl2ChannelStatusTable
-- xdsl2SCStatusTable        see VDSL2-LINE-MIB xdsl2SCStatusTable
-- xdsl2LineSegmentTable     see VDSL2-LINE-MIB xdsl2LineSegmentTable
-- xdsl2SCStatusSegmentTable see VDSL2-LINE-MIB xdsl2SCStatusSegmentTable
-- xdsl2LineInventoryTable   see VDSL2-LINE-MIB xdsl2LineInventoryTable
-- xdsl2PMLineCurrTable      see VDSL2-LINE-MIB xdsl2PMLineCurrTable
-- xdsl2PMLineCurrInitTable  see VDSL2-LINE-MIB xdsl2PMLineCurrInitTable
-- xdsl2PMChCurrTable        see VDSL2-LINE-MIB xdsl2PMChCurrTable
--------------------------------------------------------------------------------

------------------------------------------------------------------------------
-- zxAnXdsl2GlobalObjects
------------------------------------------------------------------------------
    
    ZxAnXdsl2OperationModes ::= TEXTUAL-CONVENTION
      STATUS      current
      DESCRIPTION
         "The VDSL2 management model specified includes an xDSL Mode
          attribute which identifies an instance of xDSL Mode-Specific
          PSD Configuration object in the xDSL Line Profile.  The
          following classes of xDSL operating mode are defined.
          The notes (F) and (L) denote Full-Rate and Lite/splitterless
          respectively:
          +-------+--------------------------------------------------+
          | Value |         xDSL operation mode description          |
          +-------+--------------------------------------------------+
              1   - The default/generic PSD configuration.  Default
                    configuration will be used when no other matching
                    mode specific configuration can be found.
              2   - Regional Std. (ANSI T1.413) (F)
              3   - Regional Std. (ETSI DTS/TM06006) (F)
              4   - G.992.1 POTS non-overlapped (F)
              5   - G.992.1 POTS overlapped (F)
              6   - G.992.1 ISDN non-overlapped (F)
              7   - G.992.1 ISDN overlapped (F)
              8   - G.992.1 TCM-ISDN non-overlapped (F)
              9   - G.992.1 TCM-ISDN overlapped (F)
             10   - G.992.2 POTS non-overlapped (L)
             11   - G.992.2 POTS overlapped (L)
             12   - G.992.2 with TCM-ISDN non-overlapped (L)
             13   - G.992.2 with TCM-ISDN overlapped (L)
             14   - G.992.1 TCM-ISDN symmetric (F) --- not in G.997.1
           15-19  - Unused. Reserved for future ITU-T specification.
             20   - G.992.3 POTS non-overlapped (F)
             21   - G.992.3 POTS overlapped (F)
             22   - G.992.3 ISDN non-overlapped (F)
             23   - G.992.3 ISDN overlapped (F)
           24-25  - Unused. Reserved for future ITU-T specification.
             26   - G.992.4 POTS non-overlapped (L)
             27   - G.992.4 POTS overlapped (L)
           28-29  - Unused. Reserved for future ITU-T specification.
             30   - G.992.3 Annex I All-Digital non-overlapped (F)
             31   - G.992.3 Annex I All-Digital overlapped (F)
             32   - G.992.3 Annex J All-Digital non-overlapped (F)
             33   - G.992.3 Annex J All-Digital overlapped (F)
             34   - G.992.4 Annex I All-Digital non-overlapped (L)
             35   - G.992.4 Annex I All-Digital overlapped (L)
             36   - G.992.3 Annex L POTS non-overlapped, mode 1,
                    wide U/S (F)
             37   - G.992.3 Annex L POTS non-overlapped, mode 2,
                    narrow U/S(F)
             38   - G.992.3 Annex L POTS overlapped, mode 3,
                    wide U/S (F)
             39   - G.992.3 Annex L POTS overlapped, mode 4,
                    narrow U/S (F)
             40   - G.992.3 Annex M POTS non-overlapped (F)
             41   - G.992.3 Annex M POTS overlapped (F)
             42   - G.992.5 POTS non-overlapped (F)
             43   - G.992.5 POTS overlapped (F)
             44   - G.992.5 ISDN non-overlapped (F)
             45   - G.992.5 ISDN overlapped (F)
           46-47  - Unused. Reserved for future ITU-T specification.
             48   - G.992.5 Annex I All-Digital non-overlapped (F)
             49   - G.992.5 Annex I All-Digital overlapped (F)
             50   - G.992.5 Annex J All-Digital non-overlapped (F)
             51   - G.992.5 Annex J All-Digital overlapped (F)
             52   - G.992.5 Annex M POTS non-overlapped (F)
             53   - G.992.5 Annex M POTS overlapped (F)
           54-57  - Unused. Reserved for future ITU-T specification.
             58   - G.993.2 Annex A
             59   - G.993.2 Annex B
             60   - G.993.2 Annex C
             250  - G.993.2 Annex A Protection
             251  - G.993.2 Annex B Protection
             252  - G.993.2 Annex C Protection
             253  - G.993.5 Annex A
             254  - G.993.5 Annex B
             255  - G.993.5 Annex C
         "
      SYNTAX      INTEGER {
                     defMode(1),
                     ansit1413(2),
                     etsi(3),
                     g9921PotsNonOverlapped(4),
                     g9921PotsOverlapped(5),
                     g9921IsdnNonOverlapped(6),
                     g9921isdnOverlapped(7),
                     g9921tcmIsdnNonOverlapped(8),
                     g9921tcmIsdnOverlapped(9),
                     g9922potsNonOverlapped(10),
                     g9922potsOverlapped(11),
                     g9922tcmIsdnNonOverlapped(12),
                     g9922tcmIsdnOverlapped(13),
                     g9921tcmIsdnSymmetric(14),
                     g9923PotsNonOverlapped(20),
                     g9923PotsOverlapped(21),
                     g9923IsdnNonOverlapped(22),
                     g9923isdnOverlapped(23),
                     g9924potsNonOverlapped(26),
                     g9924potsOverlapped(27),
                     g9923AnnexIAllDigNonOverlapped(30),
                     g9923AnnexIAllDigOverlapped(31),
                     g9923AnnexJAllDigNonOverlapped(32),
                     g9923AnnexJAllDigOverlapped(33),
                     g9924AnnexIAllDigNonOverlapped(34),
                     g9924AnnexIAllDigOverlapped(35),
                     g9923AnnexLMode1NonOverlapped(36),
                     g9923AnnexLMode2NonOverlapped(37),
                     g9923AnnexLMode3Overlapped(38),
                     g9923AnnexLMode4Overlapped(39),
                     g9923AnnexMPotsNonOverlapped(40),
                     g9923AnnexMPotsOverlapped(41),
                     g9925PotsNonOverlapped(42),
                     g9925PotsOverlapped(43),
                     g9925IsdnNonOverlapped(44),
                     g9925isdnOverlapped(45),
                     g9925AnnexIAllDigNonOverlapped(48),
                     g9925AnnexIAllDigOverlapped(49),
                     g9925AnnexJAllDigNonOverlapped(50),
                     g9925AnnexJAllDigOverlapped(51),
                     g9925AnnexMPotsNonOverlapped(52),
                     g9925AnnexMPotsOverlapped(53),
                     g9932AnnexA(58),
                     g9932AnnexB(59),
                     g9932AnnexC(60),
                     g9932AnnexAProtection(250),
                     g9932AnnexBProtection(251),
                     g9932AnnexCProtection(252),
                     g9935AnnexA(253),
                     g9935AnnexB(254),
                     g9935AnnexC(255)
                  }

    
    zxAnXdsl2Capabilities  OBJECT-TYPE 
        SYNTAX      BITS
            {
                maxDelay(0),
                chanInitPolicy(1),
                fextCancelNotReqBand(2),
                minSosBitRate(3),
                inpMinShineAndRein(4),
                esLossRatio(5),
                leftrsThresh(6)
            }
        MAX-ACCESS  read-only
        STATUS      current
        DESCRIPTION
            "The management capabilities of VDSL.
             The bit value 1 means the function represented by this bit is 
             supported by this equipment. 
             bit 0: value 1 means extend profile supports downstream and 
                    upstream maximum delay.                    
             bit 1: value 1 means extend profile supports downstream and 
                    upstream channel initialisation policy.
             bit 2: value 1 means extend profile supports downstream and 
                    upstream FEXT cancellation not required band.
             bit 3: value 1 means zxAnXdsl2DsDataRateConfPrfTable supports 
                    zxAnXdsl2ChConfMinSosBitRateDs and 
                    zxAnXdsl2UsDataRateConfPrfTable supports 
                    zxAnXdsl2ChConfMinSosBitRateUs.
             bit 4: value 1 means extend profile supports downstream and 
                    upstream INPMIN_SHINE_RTX, INPMIN8_SHINE_RTX and 
                    INPMIN8_REIN_RTX.
             bit 5: value 1 means alarm profile supports 
                    zxAnXdsl2XtucEsLossRatioThresh and 
                    zxAnXdsl2XturEsLossRatioThresh.
             bit 6: value 1 means alarm profile supports 
                    zxAnXdsl2XtucThreshInpLeftrs and 
                    zxAnXdsl2XturThreshInpLeftrs.
             NOTE: No recommended to display it in NMS."
        ::=  {  zxAnXdsl2GlobalObjects  1  }
    
------------------------------------------------------------------------------
-- zxAnXdsl2LnTable
------------------------------------------------------------------------------
    
    zxAnXdsl2LnTable  OBJECT-TYPE
        SYNTAX      SEQUENCE  OF  ZxAnXdsl2LnEntry
        MAX-ACCESS  not-accessible
        STATUS      current
        DESCRIPTION
          "The table zxAnXdsl2LnTable contains configuration,
           command and status parameters of the VDSL2/ADSL/ADSL2
           or ADSL2+ line.
           The index of this table is an interface index where the
           interface has an ifType of vdsl2(xxx).
    
           Several objects in this table MUST be maintained in a
            persistent manner. "
        ::= { zxAnXdsl2Line 10 }
    
    zxAnXdsl2LnEntry  OBJECT-TYPE
        SYNTAX      ZxAnXdsl2LnEntry
        MAX-ACCESS  not-accessible
        STATUS      current
        DESCRIPTION
           "The table zxAnXdsl2LnTable contains configuration,
           commands and status parameters of the VDSL2/ADSL/ADSL2
           or ADSL2+ line."
        INDEX  { ifIndex }
        ::= { zxAnXdsl2LnTable 1 }
     
    ZxAnXdsl2LnEntry  ::=
        SEQUENCE {
           zxAnXdsl2LnCh1DsDataRateConfPrf    DisplayString,
           zxAnXdsl2LnCh2DsDataRateConfPrf    DisplayString,
           zxAnXdsl2LnCh3DsDataRateConfPrf    DisplayString,
           zxAnXdsl2LnCh4DsDataRateConfPrf    DisplayString,
           zxAnXdsl2LnCh1UsDataRateConfPrf    DisplayString,
           zxAnXdsl2LnCh2UsDataRateConfPrf    DisplayString,
           zxAnXdsl2LnCh3UsDataRateConfPrf    DisplayString,
           zxAnXdsl2LnCh4UsDataRateConfPrf    DisplayString,
           zxAnXdsl2LnSpectrumConfPrf         DisplayString,
           zxAnXdsl2LnDpboConfPrf             DisplayString,
           zxAnXdsl2LnUpboConfPrf             DisplayString,
           zxAnXdsl2LnSnrMarginConfPrf        DisplayString,
           zxAnXdsl2LnCh1DelayInpConfPrf      DisplayString,
           zxAnXdsl2LnCh2DelayInpConfPrf      DisplayString,
           zxAnXdsl2LnCh3DelayInpConfPrf      DisplayString,
           zxAnXdsl2LnCh4DelayInpConfPrf      DisplayString,
           zxAnXdsl2LnRfiConfPrf              DisplayString,
           zxAnXdsl2LnVirtualNoiseConfPrf     DisplayString,
           zxAnXdsl2LnAlmThreshPrfName        DisplayString,

           zxAnXdsl2LnCmndConfPmsf            Xdsl2ConfPmsForce,
           zxAnXdsl2LnCmndConfLdsf            Xdsl2LineLdsf,
           zxAnXdsl2LnCmndConfLdsfFailReason  Xdsl2LdsfResult,
           zxAnXdsl2LnCmndConfBpsc            Xdsl2LineBpsc,
           zxAnXdsl2LnCmndConfBpscFailReason  Xdsl2BpscResult,
           zxAnXdsl2LnCmndConfBpscReqCount    Unsigned32,
           zxAnXdsl2LnCmndAutomodeColdStart   TruthValue,
           zxAnXdsl2LnCmndConfReset           Xdsl2LineReset,

           zxAnXdsl2LnStatusXtuTransSys       ZxAnXdsl2TransmissionModeType,
           zxAnXdsl2LnStatusPwrMngState       Xdsl2PowerMngState,
           zxAnXdsl2LnStatusInitResult        INTEGER,
           zxAnXdsl2LnStatusLastStateDs       Xdsl2LastTransmittedState,
           zxAnXdsl2LnStatusLastStateUs       Xdsl2LastTransmittedState,
           zxAnXdsl2LnStatusXtur              BITS,
           zxAnXdsl2LnStatusXtuc              BITS,
           zxAnXdsl2LnStatusAttainRateDs      Unsigned32,
           zxAnXdsl2LnStatusAttainRateUs      Unsigned32,
           zxAnXdsl2LnStatusActPsdDs          Integer32,
           zxAnXdsl2LnStatusActPsdUs          Integer32,
           zxAnXdsl2LnStatusActAtpDs          Integer32,
           zxAnXdsl2LnStatusActAtpUs          Integer32,
           zxAnXdsl2LnStatusActProfile        Xdsl2LineProfiles,
           zxAnXdsl2LnStatusActLimitMask      Xdsl2LineLimitMask,
           zxAnXdsl2LnStatusActUs0Mask        Xdsl2LineUs0Mask,
           zxAnXdsl2LnStatusActSnrModeDs      Xdsl2LineSnrMode,
           zxAnXdsl2LnStatusActSnrModeUs      Xdsl2LineSnrMode,
           zxAnXdsl2LnStatusActElPolicy       Unsigned32,
           zxAnXdsl2LnStatusElectLenDs        Unsigned32,
           zxAnXdsl2LnStatusElectLenUs        Unsigned32,
           zxAnXdsl2LnStatusActKl0            Unsigned32,
           zxAnXdsl2LnStatusTssiDs            Xdsl2Tssi,
           zxAnXdsl2LnStatusTssiUs            Xdsl2Tssi,
           zxAnXdsl2LnStatusMrefPsdDs         Xdsl2MrefPsdDs,
           zxAnXdsl2LnStatusMrefPsdUs         Xdsl2MrefPsdUs,
           zxAnXdsl2LnStatusTrellisDs         TruthValue,
           zxAnXdsl2LnStatusTrellisUs         TruthValue,
           zxAnXdsl2LnStatusActualCe          Unsigned32,
           zxAnXdsl2LnStatusClassMask         Xdsl2LineClassMask,
           zxAnXdsl2LnStatusOperState         INTEGER,
           zxAnXdsl2LnStatusActDataPathType   INTEGER,
           zxAnXdsl2LnStatusDataPathType      INTEGER,
           zxAnXdsl2LnStatusBitswapDs         INTEGER,
           zxAnXdsl2LnStatusBitswapUs         INTEGER,
           zxAnXdsl2LnStatusHighRateLimit     INTEGER,
           zxAnXdsl2LnExtConfPrf              DisplayString,
           zxAnXdsl2LnStatusPrevAttainRateDs  Unsigned32,
           zxAnXdsl2LnStatusPrevAttainRateUs  Unsigned32,
           zxAnXdsl2LnCmndPMReset             BITS,
           zxAnXdsl2LnCustomizedCapability    BITS,           
           zxAnXdsl2LnInpEtrDs                Unsigned32,
           zxAnXdsl2LnInpEtrUs                Unsigned32, 
           zxAnXdsl2LnInpEftrDs               Unsigned32,
           zxAnXdsl2LnInpEftrUs               Unsigned32,            
           zxAnXdsl2LnInpMinEftrDs            Unsigned32,
           zxAnXdsl2LnInpMinEftrUs            Unsigned32,        
           zxAnXdsl2LnInpActDelayDs           INTEGER,
           zxAnXdsl2LnInpActDelayUs           INTEGER,
           zxAnXdsl2LnFextCancellationDs      INTEGER,
           zxAnXdsl2LnFextCancellationUs      INTEGER,
           
           zxAnXdsl2LnSosConfPrf              DisplayString,
           
           zxAnXdsl2LnStatusLnAttenDs         Integer32,
           zxAnXdsl2LnStatusLnAttenUs         Integer32,
           zxAnXdsl2LnStatusSigAttenDs        Integer32,
           zxAnXdsl2LnStatusSigAttenUs        Integer32,
           zxAnXdsl2LnStatusSnrMarginDs       Integer32,
           zxAnXdsl2LnStatusSnrMarginUs       Integer32,
           zxAnXdsl2LnInmConfPrf              DisplayString,
           
           zxAnXdsl2LnLofStatsDs              Counter32,
           zxAnXdsl2LnLofStatsUs              Counter32,
           zxAnXdsl2LnLolStatsDs              Counter32,
           zxAnXdsl2LnLolStatsUs              Counter32,
           zxAnXdsl2LnLprStatsDs              Counter32,
           zxAnXdsl2LnLprStatsUs              Counter32,
           
           zxAnXdsl2LnActInpShineDs           Integer32,
           zxAnXdsl2LnActInpShineUs           Integer32,
           zxAnXdsl2LnActInpReinDs            Integer32,
           zxAnXdsl2LnActInpReinUs            Integer32,
           
           zxAnXdsl2LnStatusActRaModeDs       INTEGER,
           zxAnXdsl2LnStatusActRaModeUs       INTEGER,
           zxAnXdsl2LnStatusRtxUsedDs         INTEGER,
           zxAnXdsl2LnStatusRtxUsedus         INTEGER
           
        }
      
     zxAnXdsl2LnCh1DsDataRateConfPrf  OBJECT-TYPE
        SYNTAX      DisplayString (SIZE(1..32))
        MAX-ACCESS  read-write
        STATUS      current
        DESCRIPTION
           "The value of this object identifies the row in the xDSL2
           Line DsDataRate Profile Table, (zxAnXdsl2DsDataRateConfPrfTable),
            which applies for this line.
     
            This object MUST be maintained in a persistent manner."
        REFERENCE    "DSL Forum TR-129, paragraph #5.1"
        DEFVAL       { "VDEFVAL" }
        ::= { zxAnXdsl2LnEntry 1 }
        
     zxAnXdsl2LnCh2DsDataRateConfPrf  OBJECT-TYPE
        SYNTAX      DisplayString (SIZE(1..32))
        MAX-ACCESS  read-write
        STATUS      current
        DESCRIPTION
           "The value of this object identifies the row in the xDSL2
           Line DsDataRate Profile Table, (zxAnXdsl2DsDataRateConfPrfTable),
            which applies for this line.
     
            This object MUST be maintained in a persistent manner."
        REFERENCE    "DSL Forum TR-129, paragraph #5.1"
        DEFVAL       { "VDEFVAL" }
        ::= { zxAnXdsl2LnEntry 2 }
        
     zxAnXdsl2LnCh3DsDataRateConfPrf  OBJECT-TYPE
        SYNTAX      DisplayString (SIZE(1..32))
        MAX-ACCESS  read-write
        STATUS      current
        DESCRIPTION
           "The value of this object identifies the row in the xDSL2
           Line DsDataRate Profile Table, (zxAnXdsl2DsDataRateConfPrfTable),
            which applies for this line.
     
            This object MUST be maintained in a persistent manner."
        REFERENCE    "DSL Forum TR-129, paragraph #5.1"
        DEFVAL       { "VDEFVAL" }
        ::= { zxAnXdsl2LnEntry 3 }
        
     zxAnXdsl2LnCh4DsDataRateConfPrf  OBJECT-TYPE
        SYNTAX      DisplayString (SIZE(1..32))
        MAX-ACCESS  read-write
        STATUS      current
        DESCRIPTION
           "The value of this object identifies the row in the xDSL2
           Line DsDataRate Profile Table, (zxAnXdsl2DsDataRateConfPrfTable),
            which applies for this line.
     
            This object MUST be maintained in a persistent manner."
        REFERENCE    "DSL Forum TR-129, paragraph #5.1"
        DEFVAL       { "VDEFVAL" }
        ::= { zxAnXdsl2LnEntry 4 }
        
     zxAnXdsl2LnCh1UsDataRateConfPrf  OBJECT-TYPE
        SYNTAX      DisplayString (SIZE(1..32))
        MAX-ACCESS  read-write
        STATUS      current
        DESCRIPTION
           "The value of this object identifies the row in the xDSL2
           Line UsDataRate Profile Table, (zxAnXdsl2UsDataRateConfPrfTable),
            which applies for this line.
     
            This object MUST be maintained in a persistent manner."
        REFERENCE    "DSL Forum TR-129, paragraph #5.1"
        DEFVAL       { "VDEFVAL" }
        ::= { zxAnXdsl2LnEntry 5 }       
           
     zxAnXdsl2LnCh2UsDataRateConfPrf  OBJECT-TYPE
        SYNTAX      DisplayString (SIZE(1..32))
        MAX-ACCESS  read-write
        STATUS      current
        DESCRIPTION
           "The value of this object identifies the row in the xDSL2
           Line UsDataRate Profile Table, (zxAnXdsl2UsDataRateConfPrfTable),
            which applies for this line.
     
            This object MUST be maintained in a persistent manner."
        REFERENCE    "DSL Forum TR-129, paragraph #5.1"
        DEFVAL       { "VDEFVAL" }
        ::= { zxAnXdsl2LnEntry 6 }  
            
     zxAnXdsl2LnCh3UsDataRateConfPrf  OBJECT-TYPE
        SYNTAX      DisplayString (SIZE(1..32))
        MAX-ACCESS  read-write
        STATUS      current
        DESCRIPTION
           "The value of this object identifies the row in the xDSL2
           Line UsDataRate Profile Table, (zxAnXdsl2UsDataRateConfPrfTable),
            which applies for this line.
     
            This object MUST be maintained in a persistent manner."
        REFERENCE    "DSL Forum TR-129, paragraph #5.1"
        DEFVAL       { "VDEFVAL" }
        ::= { zxAnXdsl2LnEntry 7 }  
            
     zxAnXdsl2LnCh4UsDataRateConfPrf  OBJECT-TYPE
        SYNTAX      DisplayString (SIZE(1..32))
        MAX-ACCESS  read-write
        STATUS      current
        DESCRIPTION
           "The value of this object identifies the row in the xDSL2
           Line UsDataRate Profile Table, (zxAnXdsl2UsDataRateConfPrfTable),
            which applies for this line.
     
            This object MUST be maintained in a persistent manner."
        REFERENCE    "DSL Forum TR-129, paragraph #5.1"
        DEFVAL       { "VDEFVAL" }
        ::= { zxAnXdsl2LnEntry 8 }  
     
     zxAnXdsl2LnSpectrumConfPrf  OBJECT-TYPE
        SYNTAX      DisplayString (SIZE(1..32))
        MAX-ACCESS  read-write
        STATUS      current
        DESCRIPTION
           "The value of this object identifies the row in the xDSL2
           Line Spectrum Profile Table, (zxAnXdsl2SpectrumConfPrfTable),
            which applies for this line.
     
            This object MUST be maintained in a persistent manner."
        REFERENCE    "DSL Forum TR-129, paragraph #5.1"
        DEFVAL       { "VDEFVAL" }
        ::= { zxAnXdsl2LnEntry 9 }   
     
     
     zxAnXdsl2LnDpboConfPrf  OBJECT-TYPE
        SYNTAX      DisplayString (SIZE(1..32))
        MAX-ACCESS  read-write
        STATUS      current
        DESCRIPTION
           "The value of this object identifies the row in the xDSL2
           Line Dpbo Profile Table, (zxAnXdsl2DpboConfPrfTable),
            which applies for this line.
     
            This object MUST be maintained in a persistent manner."
        REFERENCE    "DSL Forum TR-129, paragraph #5.1"
        DEFVAL       { "VDEFVAL" }
        ::= { zxAnXdsl2LnEntry 10 }
     

     zxAnXdsl2LnUpboConfPrf  OBJECT-TYPE
        SYNTAX      DisplayString (SIZE(1..32))
        MAX-ACCESS  read-write
        STATUS      current
        DESCRIPTION
           "The value of this object identifies the row in the xDSL2
           Line Upbo Profile Table, (zxAnXdsl2UpboConfPrfTable),
            which applies for this line.
     
            This object MUST be maintained in a persistent manner."
        REFERENCE    "DSL Forum TR-129, paragraph #5.1"
        DEFVAL       { "VDEFVAL" }
        ::= { zxAnXdsl2LnEntry 11 }
     

     zxAnXdsl2LnSnrMarginConfPrf  OBJECT-TYPE
        SYNTAX      DisplayString (SIZE(1..32))
        MAX-ACCESS  read-write
        STATUS      current
        DESCRIPTION
           "The value of this object identifies the row in the xDSL2
           Noise Margin Profile Table, (zxAnXdsl2SnrMarginConfPrfTable),
            which applies for this line.
     
            This object MUST be maintained in a persistent manner."
        REFERENCE    "DSL Forum TR-129, paragraph #5.1"
        DEFVAL       { "VDEFVAL" }
        ::= { zxAnXdsl2LnEntry 12 }

    zxAnXdsl2LnCh1DelayInpConfPrf  OBJECT-TYPE
        SYNTAX      DisplayString (SIZE(1..32))
        MAX-ACCESS  read-write
        STATUS      current
        DESCRIPTION
           "The value of this object identifies the row in the xDSL2
           Delay AND INP Profile Table, (zxAnXdsl2DelayInpConfPrfTable),
            which applies for this line.
     
            This object MUST be maintained in a persistent manner."
        REFERENCE    "DSL Forum TR-129, paragraph #5.1"
        DEFVAL       { "VDEFVAL" }
        ::= { zxAnXdsl2LnEntry 13 }
        
     zxAnXdsl2LnCh2DelayInpConfPrf  OBJECT-TYPE
        SYNTAX      DisplayString (SIZE(1..32))
        MAX-ACCESS  read-write
        STATUS      current
        DESCRIPTION
           "The value of this object identifies the row in the xDSL2
           Delay AND INP Profile Table, (zxAnXdsl2DelayInpConfPrfTable),
            which applies for this line.
     
            This object MUST be maintained in a persistent manner."
        REFERENCE    "DSL Forum TR-129, paragraph #5.1"
        DEFVAL       { "VDEFVAL" }
        ::= { zxAnXdsl2LnEntry 14 }
        
     zxAnXdsl2LnCh3DelayInpConfPrf  OBJECT-TYPE
        SYNTAX      DisplayString (SIZE(1..32))
        MAX-ACCESS  read-write
        STATUS      current
        DESCRIPTION
           "The value of this object identifies the row in the xDSL2
           Delay AND INP Profile Table, (zxAnXdsl2DelayInpConfPrfTable),
            which applies for this line.
     
            This object MUST be maintained in a persistent manner."
        REFERENCE    "DSL Forum TR-129, paragraph #5.1"
        DEFVAL       { "VDEFVAL" }
        ::= { zxAnXdsl2LnEntry 15 }
        
     zxAnXdsl2LnCh4DelayInpConfPrf  OBJECT-TYPE
        SYNTAX      DisplayString (SIZE(1..32))
        MAX-ACCESS  read-write
        STATUS      current
        DESCRIPTION
           "The value of this object identifies the row in the xDSL2
           Delay AND INP Profile Table, (zxAnXdsl2DelayInpConfPrfTable),
            which applies for this line.
     
            This object MUST be maintained in a persistent manner."
        REFERENCE    "DSL Forum TR-129, paragraph #5.1"
        DEFVAL       { "VDEFVAL" }
        ::= { zxAnXdsl2LnEntry 16 }
        
     zxAnXdsl2LnRfiConfPrf  OBJECT-TYPE
        SYNTAX      DisplayString (SIZE(1..32))
        MAX-ACCESS  read-write
        STATUS      current
        DESCRIPTION
           "The value of this object identifies the row in the xDSL2
           RFI Profile Table, (zxAnXdsl2RfiConfPrfTable),
            which applies for this line.
     
            This object MUST be maintained in a persistent manner."
        REFERENCE    "DSL Forum TR-129, paragraph #5.1"
        DEFVAL       { "VDEFVAL" }
        ::= { zxAnXdsl2LnEntry 17 }        

     zxAnXdsl2LnVirtualNoiseConfPrf  OBJECT-TYPE
        SYNTAX      DisplayString (SIZE(1..32))
        MAX-ACCESS  read-write
        STATUS      current
        DESCRIPTION
           "The value of this object identifies the row in the xDSL2
           Virtual Noise Profile Table, (zxAnXdsl2VirtualNoiseConfPrfTable),
            which applies for this line.
     
            This object MUST be maintained in a persistent manner."
        REFERENCE    "DSL Forum TR-129, paragraph #5.1"
        DEFVAL       { "VDEFVAL" }
        ::= { zxAnXdsl2LnEntry 18 } 
                       
     zxAnXdsl2LnAlmThreshPrfName  OBJECT-TYPE
        SYNTAX      DisplayString (SIZE(1..32))
        MAX-ACCESS  read-write
        STATUS      current
        DESCRIPTION
           "The value of this object identifies the row in the xDSL2
           Line Alarm Configuration Profile Table,
           (zxAnXdsl2LnAlarmConfPrfTable), which applies to this line.
     
           This object MUST be maintained in a persistent manner."
        REFERENCE    "DSL Forum TR-129, paragraph #5.1"
        DEFVAL       { "VDEFVAL" }
        ::= { zxAnXdsl2LnEntry 19 }
     
     zxAnXdsl2LnCmndConfPmsf  OBJECT-TYPE
        SYNTAX      Xdsl2ConfPmsForce
        MAX-ACCESS  read-write
        STATUS      current
        DESCRIPTION
           "Command:Power management state forced (PMSF).  Defines the line
            states to be forced by the near-end xTU on this line.
            The various possible values are:
               l3toL0 (0),
               l0toL2 (2),
               l0orL2toL3 (3).
     
            This object MUST be maintained in a persistent manner."
        REFERENCE    "ITU-T G.997.1, paragraph #7.3.1.1.3"
        DEFVAL       { l3toL0 }
        ::= { zxAnXdsl2LnEntry 20 }
     
     zxAnXdsl2LnCmndConfLdsf  OBJECT-TYPE
        SYNTAX      Xdsl2LineLdsf
        MAX-ACCESS  read-write
        STATUS      current
        DESCRIPTION
           "Command:Loop diagnostics mode forced (LDSF).  Defines whether the
           line should be forced into the loop diagnostics mode by the
            near-end xTU on this line or only be responsive to loop
            diagnostics initiated by the far-end xTU.
     
            This object MUST be maintained in a persistent manner.
            However, in case the operator forces loop diagnostics mode
            then the access node should reset the object (inhibit) when
            loop diagnostics mode procedures are completed."
        REFERENCE    "ITU-T G.997.1, paragraph #7.3.1.1.8"
        DEFVAL       { inhibit }
        ::= { zxAnXdsl2LnEntry 21 }
     
     zxAnXdsl2LnCmndConfLdsfFailReason  OBJECT-TYPE
        SYNTAX      Xdsl2LdsfResult
        MAX-ACCESS  read-only
        STATUS      current
        DESCRIPTION
           "Command:The status of the recent occasion the Loop diagnostics mode
            forced (LDSF) was issued for the associated line.  Possible
            values are:
               none        (1) - The default value in case LDSF was never
                                 requested for the associated line.
               success     (2) - The recent command completed
                                 successfully.
               inProgress  (3) - The Loop Diagnostics process is in
                                 progress.
               unsupported (4) - The NE or the line card doesn't support
                                 LDSF.
               cannotRun   (5) - The NE cannot initiate the command, due
                                 to a non specific reason.
               aborted     (6) - The Loop Diagnostics process aborted.
               failed      (7) - The Loop Diagnostics process failed.
               illegalMode (8) - The NE cannot initiate the command, due
                                 to the specific mode of the relevant
                                 line.
               adminUp     (9) - The NE cannot initiate the command, as
                                 the relevant line is administratively
                                 'Up'.
               tableFull   (10)- The NE cannot initiate the command, due
                                 to reaching the maximum number of rows
                                 in the results table.
               noResources (11)- The NE cannot initiate the command, due
                                 to lack of internal memory resources."
        DEFVAL       { none }
        ::= { zxAnXdsl2LnEntry 22 }
             
             
        zxAnXdsl2LnCmndConfBpsc  OBJECT-TYPE
           SYNTAX      Xdsl2LineBpsc
           MAX-ACCESS  read-write
           STATUS      current
           DESCRIPTION
              "Command:Request a bits per sub-carrier measurement to be made.
        
               A request for a bits per sub-carrier measurement is made
               by setting this attribute to the value of measure(2).
               Upon completion of the measurement request,
               the Access Node shall set this attribute to idle(1).
        
               Note that a bits per sub-carrier measurement is also
               performed during a line diagnostic procedure. This
               attribute provides an additional mechanism to fetch
               the bits per sub-carrier data. This additional
               mechanism is provided so that bits per sub-carrier
               data may be fetched without forcing the line into no
               power state. This is useful because the bits per
               sub-carrier allocation may be adjusted at show time
               due to rate adaption and bit swapping.
        
               The implementation of this additional mechanism for
               measuring bits per sub-carrier is not mandatory.
        
               The results of the bits per sub-carrier measurement are
               stored in xdsl2LineSegmentTable. The status of the bits
               per sub-carrier measurement is indicated by
               xdsl2LineCmndConfBpscFailReason."
           DEFVAL       { idle }
           ::= { zxAnXdsl2LnEntry 23 }
        
        zxAnXdsl2LnCmndConfBpscFailReason  OBJECT-TYPE
           SYNTAX      Xdsl2BpscResult
           MAX-ACCESS  read-only
           STATUS      current
           DESCRIPTION
              "Command:The status of the most recent bits per sub-carrier
               measurement request issued for the associated line.
               Possible values are:
        
                  none        (1) - The default value, in case a measurement
                                    was never requested for the associated line.
                  success     (2) - The recent measurement request completed
                                    successfully.
                  inProgress  (3) - The bits per sub-carrier measurement is in
                                    progress.
                  unsupported (4) - The bits per sub-carrier request mechanism
                                    is not supported.
                  failed      (5) - The measurement request has failed and no
                                    results are available.
                  noResources (6) - The NE cannot initiate the command, due
                                    to lack of internal memory resources."
           DEFVAL       { none }
           ::= { zxAnXdsl2LnEntry 24 }
  
        zxAnXdsl2LnCmndConfBpscReqCount  OBJECT-TYPE
           SYNTAX      Unsigned32
           MAX-ACCESS  read-only
           STATUS      current
           DESCRIPTION
              "Command:Measurement request counter.
               This counter is incremented by one every time a request
               for a measurement is made. A measurement request is made
               by setting the xdsl2LineCmndConfBpsc attribute to the
               value measure(2).
               SNMP managers can use this attribute to check that the
               measurement results retrieved by the manager where not
               interupted by another measurement request."
           DEFVAL       { 0 }
           ::= { zxAnXdsl2LnEntry 25 }     
             
             
        zxAnXdsl2LnCmndAutomodeColdStart   OBJECT-TYPE
           SYNTAX      TruthValue
           MAX-ACCESS  read-write
           STATUS      current
           DESCRIPTION
              "Command: Automode cold start forced.  This parameter is defined
               in order to improve testing of the performance of xTUs
               supporting automode when it is enabled in the MIB.
               Change the value of this parameter to 'true' indicates
               a change in loop conditions applied to the devices under
               test.  The xTUs shall reset any historical information
               used for automode and for shortening G.994.1 handshake
               and initialization.
     
               Automode is the case where multiple operation-modes are
               enabled through the zxAnXdsl2LConfXtuTransSysEna object
               in the line configuration profile being used for the
               line, and where the selection of the actual
               operation-mode depends not only on the common
               capabilities of both xTUs (as exchanged in G.994.1), but
               also on achievable data rates under given loop
               conditions.
     
               This object MUST be maintained in a persistent manner."
     
           REFERENCE    "ITU-T G.997.1, paragraph #7.3.1.1.10"
           DEFVAL       { false }
           ::= { zxAnXdsl2LnEntry 26 }
     

    zxAnXdsl2LnCmndConfReset   OBJECT-TYPE
          SYNTAX      Xdsl2LineReset
          MAX-ACCESS  read-write
          STATUS      current
          DESCRIPTION
             "Command: Request a line reset to occur.
              If this attribute is set to the value of reset(2), then
              force the line to reset ( i.e. the modems will retrain ).
              When the line has successfully reset, the SNMP agent will
              set the value of this attribute to idle(1).
    
              Note that the xdsl2LineCmndConfPmsf attribute will always
              take precedence over this attribute.
              If the xdsl2LineCmndConfPmsf attribute is set to the value
              l0orL2toL3(3), then the line must not return to the
              showtime state due to a reset request action performed
              using this attribute."
       DEFVAL       { idle }
          ::= { zxAnXdsl2LnEntry 27 }
    
     
     zxAnXdsl2LnStatusXtuTransSys  OBJECT-TYPE
        SYNTAX      ZxAnXdsl2TransmissionModeType
        MAX-ACCESS  read-only
        STATUS      current
        DESCRIPTION
           "The xTU Transmission System (xTS) in use.
            It is coded in a bit-map representation with one bit set to
            '1' (the selected coding for the DSL line).  This
            parameter
            may be derived from the handshaking procedures defined in
            Recommendation G.994.1.  A set of xDSL line transmission
            modes, with one bit per mode.  "
        REFERENCE    "ITU-T G.997.1, paragraph #7.5.1.1"
        ::= { zxAnXdsl2LnEntry 28 }
     
     zxAnXdsl2LnStatusPwrMngState  OBJECT-TYPE
        SYNTAX      Xdsl2PowerMngState
        MAX-ACCESS  read-only
        STATUS      current
        DESCRIPTION
           "The current power management state.  One of four possible
            power management states:
               L0 - Synchronized and full transmission (i.e., Showtime),
               L1 - Low Power with reduced net data rate (G.992.2 only),
               L2 - Low Power with reduced net data rate (G.992.3 and
                    G.992.4 only),
               L3 - No power
           The various possible values are:l0(1), l1(2), l2(3), l3(4)."
        REFERENCE    "ITU-T G.997.1, paragraph #7.5.1.2"
           ::= { zxAnXdsl2LnEntry 29 }
     
     zxAnXdsl2LnStatusInitResult  OBJECT-TYPE
        SYNTAX      INTEGER {
                       noFail              (0),
                       configError         (1),
                       configNotFeasible   (2),
                       commFail            (3),
                       noPeerAtu           (4),
                       otherCause          (5),
                       protocolInitFailure (254)
                      }
        MAX-ACCESS  read-only
        STATUS      current
        DESCRIPTION
           "Indicates the result of the last full initialization
            performed on the line. It is an enumeration type with the following
            values: noFail(0), configError(1), configNotFeasible(2),      
            commFail(3), noPeerAtu(4), otherCause(5), protocolInitFailure(254).
            
            noFail              (0)   - Successful initialization.
            configError         (1)   - Configuration failure.
            configNotFeasible   (2)   - Configuration details not supported.
            commFail            (3)   - Communication failure.
            noPeerAtu           (4)   - Peer ATU not detected.
            otherCause          (5)   - Other initialization failure.
            protocolInitFailure (254) - Protocol initialization failure.
            "
        ::= { zxAnXdsl2LnEntry 30 }
     
     zxAnXdsl2LnStatusLastStateDs  OBJECT-TYPE
        SYNTAX      Xdsl2LastTransmittedState
        MAX-ACCESS  read-only
        STATUS      current
        DESCRIPTION
           "The last successful transmitted initialization state in
            the downstream direction in the last full initialization
            performed on the line."
        REFERENCE    "ITU-T G.997.1, paragraph #7.5.1.7"
        ::= { zxAnXdsl2LnEntry 31 }
     
     zxAnXdsl2LnStatusLastStateUs  OBJECT-TYPE
        SYNTAX      Xdsl2LastTransmittedState
        MAX-ACCESS  read-only
        STATUS      current
        DESCRIPTION
           "The last successful transmitted initialization state in the
            upstream direction in the last full initialization performed
            on the line."
        REFERENCE    "ITU-T G.997.1, paragraph #7.5.1.8"
        ::= { zxAnXdsl2LnEntry 32 }
     
     zxAnXdsl2LnStatusXtur  OBJECT-TYPE
        SYNTAX BITS {
            noDefect            (0),
            lossOfFraming       (1),
            lossOfSignal        (2),
            lossOfPower         (3),
            unused              (4),
            lossOfSignalQuality (5)
           }
        MAX-ACCESS  read-only
        STATUS      current
        DESCRIPTION
           "Indicates current state (existing failures) of the xTU-R.
            This is a bit-map of possible conditions. 
            
            This BITS structure can report the following failures:
            
            noDefect            (0) - This bit position positively reports that 
                                     no defect or failure exist.
            
            lossOfFraming       (1) - xTU-R failure due to loss of frame 
                                      synchronization.
            
            lossOfSignal        (2) - xTU-R failure due to loss of signal.
            
            lossOfPower         (3) - xTU-R failure due to loss of power.Usually 
                                      this failure may be reported for CPE units
                                      only.
            
            unused              (4) - This bit is never active on xTU-R.  
                             
            lossOfSignalQuality (5) - Loss of Signal Quality is declared when 
                                      the Noise Margin falls below the Minimum 
                                      Noise Margin, or the bit-error-rate 
                                      exceeds 10^-7.
            "
        ::= { zxAnXdsl2LnEntry 33 }
     
     zxAnXdsl2LnStatusXtuc  OBJECT-TYPE
        SYNTAX BITS {
            noDefect            (0),
            lossOfFraming       (1),
            lossOfSignal        (2),
            lossOfPower         (3),
            initFailure         (4),
            lossOfSignalQuality (5),
            lossOfLink          (6)
           }
        MAX-ACCESS  read-only
        STATUS      current
        DESCRIPTION
           "Indicates current state (existing failures) of the xTU-C.
            This is a bit-map of possible conditions. 
            
            This BITS structure can report the following failures:
            
            noDefect            (0) - This bit position positively reports that 
                                      no defect or failure exist.
            
            lossOfFraming       (1) - xTU-C failure due to loss of frame 
                                      synchronization.
            
            lossOfSignal        (2) - xTU-C failure due to loss of signal.
            
            lossOfPower         (3) - xTU-C failure due to loss of power.Usually
                                      this failure may be reported for CPE units
                                      only.
            
            initFailure         (4) - Recent initialization process failed.
            
            lossOfSignalQuality (5) - Loss of Signal Quality is declared when 
                                      the Noise Margin falls below the Minimum 
                                      Noise Margin, or the bit-error-rate 
                                      exceeds 10^-7.
            
            lossOfLink          (6) - xTU-C failure due to inability to link 
                                      with xTU-R.
            "
        ::= { zxAnXdsl2LnEntry 34 }
     
     zxAnXdsl2LnStatusAttainRateDs  OBJECT-TYPE
        SYNTAX      Unsigned32
        UNITS       "kbps"
        MAX-ACCESS  read-only
        STATUS      current
        DESCRIPTION
           "Maximum Attainable Data Rate Downstream.
            The maximum downstream net data rate currently attainable by
            the xTU-C transmitter and the xTU-R receiver, coded in
            bit/s."
        REFERENCE    "ITU-T G.997.1, paragraph #7.5.1.12"
        ::= { zxAnXdsl2LnEntry 35 }
     
     zxAnXdsl2LnStatusAttainRateUs  OBJECT-TYPE
        SYNTAX      Unsigned32
        UNITS       "kbps"
        MAX-ACCESS  read-only
        STATUS      current
        DESCRIPTION
           "Maximum Attainable Data Rate Upstream.
            The maximum upstream net data rate currently attainable by the
            xTU-R transmitter and the xTU-C receiver, coded in bit/s."
        REFERENCE    "ITU-T G.997.1, paragraph #7.5.1.13"
        ::= { zxAnXdsl2LnEntry 36 }
     
     zxAnXdsl2LnStatusActPsdDs OBJECT-TYPE
        SYNTAX      Integer32 (-900..0 | 2147483647)
        UNITS       "0.1 dBm/Hz"
        MAX-ACCESS  read-only
        STATUS      current
        DESCRIPTION
           "Actual Power Spectrum Density (PSD) Downstream.  The average
            downstream transmit PSD over the sub-carriers used for
            downstream.  It ranges from -900 to 0 units of 0.1 dB
            (Physical values are -90 to 0 dBm/Hz).
            A value of 0x7FFFFFFF (2147483647) indicates the measurement
            is out of range to be represented."
        REFERENCE    "ITU-T G.997.1, paragraph #7.5.1.14"
        ::= { zxAnXdsl2LnEntry 37 }
     
     zxAnXdsl2LnStatusActPsdUs OBJECT-TYPE
        SYNTAX      Integer32 (-900..0 | 2147483647)
        UNITS       "0.1 dBm/Hz"
        MAX-ACCESS  read-only
        STATUS      current
        DESCRIPTION
           "Actual Power Spectrum Density (PSD) Upstream.  The average
            upstream transmit PSD over the sub-carriers used for upstream.
            It ranges from -900 to 0 units of 0.1 dB (Physical values
            are -90 to 0 dBm/Hz).
            A value of 0x7FFFFFFF (2147483647) indicates the measurement
            is out of range to be represented."
        REFERENCE    "ITU-T G.997.1, paragraph #7.5.1.15"
        ::= { zxAnXdsl2LnEntry 38 }
     
     zxAnXdsl2LnStatusActAtpDs  OBJECT-TYPE
        SYNTAX      Integer32 (-310..310 | 2147483647)
        UNITS       "0.1 dBm"
        MAX-ACCESS  read-only
        STATUS      current
        DESCRIPTION
           "Actual Aggregate Transmit Power Downstream.  The total
           amount
            of transmit power delivered by the xTU-C at the U-C reference
            point, at the instant of measurement.  It ranges from -310 to
            310 units of 0.1 dB (Physical values are -31 to 31 dBm).
            A value of 0x7FFFFFFF (2147483647) indicates the measurement
            is out of range to be represented."
        REFERENCE    "ITU-T G.997.1, paragraph #7.5.1.16"
        ::= { zxAnXdsl2LnEntry 39 }
     
     zxAnXdsl2LnStatusActAtpUs  OBJECT-TYPE
        SYNTAX      Integer32 (-310..310 | 2147483647)
        UNITS       "0.1 dBm"
        MAX-ACCESS  read-only
        STATUS      current
        DESCRIPTION
           "Actual Aggregate Transmit Power Upstream.  The total amount
           of
            transmit power delivered by the xTU-R at the U-R
            reference point, at the instant of measurement.  It ranges
            from -310 to 310 units of 0.1 dB (Physical values are -31
            to 31 dBm).
            A value of 0x7FFFFFFF (2147483647) indicates the measurement
            is out of range to be represented."
        REFERENCE    "ITU-T G.997.1, paragraph #7.5.1.17"
        ::= { zxAnXdsl2LnEntry 40 }


    zxAnXdsl2LnStatusActProfile  OBJECT-TYPE
        SYNTAX      Xdsl2LineProfiles
        MAX-ACCESS  read-only
        STATUS      current
        DESCRIPTION
             "Actual Standard Profile used by this connection."
        ::= { zxAnXdsl2LnEntry 41 }


    zxAnXdsl2LnStatusActLimitMask  OBJECT-TYPE
       SYNTAX      Xdsl2LineLimitMask 
       MAX-ACCESS  read-only
       STATUS      current
       DESCRIPTION
          "The Limit PSD mask and band plan in use.
           The configuration parameter xdsl2LConfPrfLimitMask defines
           the set of allowed G.993.2 limit PSD masks.
           This parameter indicates the limit PSD mask in use on
           this line."
       REFERENCE    "ITU-T G.997.1, paragraph #7.5.1.3"
       DEFVAL       { {} }
       ::= { zxAnXdsl2LnEntry 42 }
    
    
    
    zxAnXdsl2LnStatusActUs0Mask  OBJECT-TYPE
       SYNTAX      Xdsl2LineUs0Mask
       MAX-ACCESS  read-only
       STATUS      current
       DESCRIPTION
          "The US0 PSD mask in use.
           The configuration parameter xdsl2LConfPrfUs0Mask defines
           the set of allowed US0 PSD masks.
           This parameter indicates the US0 PSD mask in use on
           this line.
           This parameter may be derived from the handshaking
           procedures defined in ITU-T Rec. G.994.1."
       REFERENCE    "ITU-T G.997.1, paragraph #7.5.1.4"
       DEFVAL       { {} }
       ::= { zxAnXdsl2LnEntry 43 }
    
    zxAnXdsl2LnStatusActSnrModeDs  OBJECT-TYPE
       SYNTAX      Xdsl2LineSnrMode
       MAX-ACCESS  read-only
       STATUS      current
       DESCRIPTION
          "This parameter indicates if the transmitter
           referred virtual noise is active on the line in the
           downstream direction.  "
       REFERENCE    "ITU-T G.997.1, paragraph #7.5.1.15 (ACTSNRMODEds)"
       ::= { zxAnXdsl2LnEntry 44 }
    
    zxAnXdsl2LnStatusActSnrModeUs  OBJECT-TYPE
       SYNTAX      Xdsl2LineSnrMode
       MAX-ACCESS  read-only
       STATUS      current
       DESCRIPTION
          "This parameter indicates if the transmitter
           referred virtual noise is active on the line in the
           upstream direction. "
       REFERENCE    "ITU-T G.997.1, paragraph #7.5.1.18 (ACTSNRMODEus)"
       ::= { zxAnXdsl2LnEntry 45 }
    
    
    zxAnXdsl2LnStatusActElPolicy  OBJECT-TYPE
       SYNTAX      Unsigned32
       MAX-ACCESS  read-only
       STATUS      current
       DESCRIPTION
          "The actual UPBO kl0 policy."

       ::= { zxAnXdsl2LnEntry 46 }    
    
    zxAnXdsl2LnStatusElectLenDs  OBJECT-TYPE
       SYNTAX      Unsigned32 (0..1280)
       UNITS       "0.1 dB"
       MAX-ACCESS  read-only
       STATUS      current
       DESCRIPTION
          "(UPBOKLE)
           This parameter contains the estimated electrical length of downstream
           expressed in dB at 1 MHz, kl0. This is the final electrical
           length that would have been sent from the VTU-O to VTU-R if
           the electrical length was not forced by the CO-MIB.
           The value ranges from 0 to 128 dB in steps of 0.1 dB."
       REFERENCE    "ITU-T G.997.1, paragraph #7.5.1.23"
       DEFVAL       { 0 }
       ::= { zxAnXdsl2LnEntry 47 }


    zxAnXdsl2LnStatusElectLenUs  OBJECT-TYPE
       SYNTAX      Unsigned32 (0..1280)
       UNITS       "0.1 dB"
       MAX-ACCESS  read-only
       STATUS      current
       DESCRIPTION
          "(UPBOKLE)
           This parameter contains the estimated electrical length of upstream
           expressed in dB at 1 MHz, kl0. This is the final electrical
           length that would have been sent from the VTU-O to VTU-R if
           the electrical length was not forced by the CO-MIB.
           The value ranges from 0 to 128 dB in steps of 0.1 dB."
       REFERENCE    "ITU-T G.997.1, paragraph #7.5.1.23"
       DEFVAL       { 0 }
       ::= { zxAnXdsl2LnEntry 48 }
    


    zxAnXdsl2LnStatusActKl0  OBJECT-TYPE
       SYNTAX      Unsigned32 (0..1280)
       UNITS       "0.1 dB"
       MAX-ACCESS  read-only
       STATUS      current
       DESCRIPTION
          " The actual kl0 used by the line."
       ::= { zxAnXdsl2LnEntry 49 }


    zxAnXdsl2LnStatusTssiDs  OBJECT-TYPE
     SYNTAX      Xdsl2Tssi
     MAX-ACCESS  read-only
     STATUS      current
     DESCRIPTION
         "The transmit spectrum shaping (TSSi) breakpoints of downstream expressed
         as the set of breakpoints exchanged during G.994.1.
         Each breakpoint is a pair of values occupying 3 octets with the
         following structure:
         First 2 octets - Index of the subcarrier used in the context of
                          the breakpoint.
         Third octet    - The shaping parameter at the breakpoint.
         Subcarrier index is an unsigned number in the range 1 to either
         NSCds (downstream direction) or NSCus (upstream direction).
         The shaping parameter value is in the range 0 to 127 (units of
         -0.5dB). The special value 127 indicates that the subcarrier
         is not transmitted."
     REFERENCE  "ITU-T G.997.1, paragraph #7.5.1.29.5 (TSSpsds)
               and paragraph #7.5.1.29.6 (TSSpsus)"
     ::= { zxAnXdsl2LnEntry 50 }


    zxAnXdsl2LnStatusTssiUs  OBJECT-TYPE
     SYNTAX      Xdsl2Tssi
     MAX-ACCESS  read-only
     STATUS      current
     DESCRIPTION
         "The transmit spectrum shaping (TSSi) breakpoints of upstream expressed
         as the set of breakpoints exchanged during G.994.1.
         Each breakpoint is a pair of values occupying 3 octets with the
         following structure:
         First 2 octets - Index of the subcarrier used in the context of
                          the breakpoint.
         Third octet    - The shaping parameter at the breakpoint.
         Subcarrier index is an unsigned number in the range 1 to either
         NSCds (downstream direction) or NSCus (upstream direction).
         The shaping parameter value is in the range 0 to 127 (units of
         -0.5dB). The special value 127 indicates that the subcarrier
         is not transmitted."
     REFERENCE  "ITU-T G.997.1, paragraph #7.5.1.29.5 (TSSpsds)
               and paragraph #7.5.1.29.6 (TSSpsus)"
     ::= { zxAnXdsl2LnEntry 51 }



    zxAnXdsl2LnStatusMrefPsdDs  OBJECT-TYPE
        SYNTAX      Xdsl2MrefPsdDs
        MAX-ACCESS  read-only
        STATUS      current
        DESCRIPTION
        "The MEDLEY Reference PSD status parameters on
         downstreasm direction expressed as the set of breakpoints
         exchanged at initialization.
         The OCTET STRING contains up to 48 pairs
         of values in the following structure:
         Octets 0&1 -- Index of 1st subcarrier used
              in the context of a first breakpoint.
         Octets 2&3 -- The PSD level for the
              subcarrier indicated in octets 0&1.
         Octets 4-7 -- Same, for a 2nd breakpoint
         Octets 8-11 -- Same, for a 3rd breakpoint
         And so on until
         Octets 188-191 -- Same, for a 48th breakpoint.
         Each subcarrier index is an unsigned number
         in the range 1 and  NSds (i.e., highest
         supported sub carrier index on downstream
         direction).
         The PSD level is an integer value in the 0 to
         4095 range. It is represented in units of 0.1
         dB offset from -140dBm/Hz."
      REFERENCE  "ITU-T G.997.1, paragraph #7.5.1.29.7 (MREFpsds)"
         ::= { zxAnXdsl2LnEntry 52 }


   zxAnXdsl2LnStatusMrefPsdUs  OBJECT-TYPE
        SYNTAX      Xdsl2MrefPsdUs
        MAX-ACCESS  read-only
        STATUS      current
        DESCRIPTION
        "The MEDLEY Reference PSD status parameters on
         upstreasm direction expressed as the set of breakpoints
         exchanged at initialization.
         The OCTET STRING contains up to 32 pairs
         of values in the following structure:
         Octets 0&1 -- Index of 1st subcarrier used
              in the context of a first breakpoint.
         Octets 2&3 -- The PSD level for the
              subcarrier indicated in octets 0&1.
         Octets 4-7 -- Same, for a 2nd breakpoint
         Octets 8-11 -- Same, for a 3rd breakpoint
         And so on until
         Octets 124-127 -- Same, for a 32nd breakpoint.
         Each subcarrier index is an unsigned number
         in the range 1 and  NSus (i.e., highest
         supported sub carrier index on upstream
         direction).
         The PSD level is an integer value in the 0 to
         4095 range. It is represented in units of 0.1
         dB offset from -140dBm/Hz."
      REFERENCE  "ITU-T G.997.1, paragraph #7.5.1.29.8 (MREFpsus)"
      ::= { zxAnXdsl2LnEntry 53 }



    zxAnXdsl2LnStatusTrellisDs  OBJECT-TYPE
       SYNTAX      TruthValue
       MAX-ACCESS  read-only
       STATUS      current
       DESCRIPTION
          "This parameter reports whether trellis coding
           is in use in the downstream direction."
       REFERENCE    "ITU-T G.997.1, paragraph #7.5.1.30"
       DEFVAL       { false }
       ::= { zxAnXdsl2LnEntry 54 }
    
    zxAnXdsl2LnStatusTrellisUs  OBJECT-TYPE
       SYNTAX      TruthValue
       MAX-ACCESS  read-only
       STATUS      current
       DESCRIPTION
          "This parameter reports whether trellis coding
           is in use in the upstream direction."
       REFERENCE    "ITU-T G.997.1, paragraph #7.5.1.31"
       DEFVAL       { false }
       ::= { zxAnXdsl2LnEntry 55 }
    
    zxAnXdsl2LnStatusActualCe  OBJECT-TYPE
       SYNTAX      Unsigned32 (2..16)
       UNITS       "N/32 samples"
       MAX-ACCESS  read-only
       STATUS      current
       DESCRIPTION
          "(ACTUALCE)
           This parameter reports the cyclic extension
           used on the line. It is coded as an unsigned integer from
           2 to 16 in units of N/32 samples, where 2N is the IDFT size."
       REFERENCE    "ITU-T G.997.1, paragraph #7.5.1.32"
       DEFVAL       { 2 }
       ::= { zxAnXdsl2LnEntry 56 }
    
    zxAnXdsl2LnStatusClassMask  OBJECT-TYPE
       SYNTAX      Xdsl2LineClassMask
       MAX-ACCESS  read-only
       STATUS      current
       DESCRIPTION
          "(CLASSMASK).
          In order to reduce the number of configuration
          possibilities, the limit Power Spectral Density masks
          (see LIMITMASK) are grouped in PSD mask classes.
          Each class is designed such that the PSD levels of each
          limit PSD mask of a specific class are equal in their
          respective passband above 276 kHz.
          This parameter is defined per VDSL2 Annex enabled in the
          xdsl2LConfPrfXtuTransSysEna object. It selects a single
          PSD mask class per Annex that is activated at the
          VTU-O."
       REFERENCE    "ITU-T G.997.1, paragraph #7.3.1.2.15"
       DEFVAL       { a998ORb997M1cORc998B }
       ::= { zxAnXdsl2LnEntry 57 }
    
    zxAnXdsl2LnStatusOperState    OBJECT-TYPE
        SYNTAX      INTEGER 
        {
            idle(1), 
            handshake(2),
            training(3),
            testing(4), --  such as DELT,HYBRID,TX test.
            showtime(5),
            waiting(6)  -- waiting for trainng.          
        }
        MAX-ACCESS  read-only
        STATUS      current
        DESCRIPTION
             "The operational status of the line."
        ::= { zxAnXdsl2LnEntry 58 }    
    

    zxAnXdsl2LnStatusActDataPathType  OBJECT-TYPE    
        SYNTAX      INTEGER {
            atm(1), 
            ptm(2),
            stm(3)
        }
        MAX-ACCESS  read-only
        STATUS      current
        DESCRIPTION
             "Actual data path type of this line."
        ::= { zxAnXdsl2LnEntry 59 } 
           
    zxAnXdsl2LnStatusDataPathType  OBJECT-TYPE
        SYNTAX      INTEGER {
            atm(1), 
            ptm(2),
            stm(3),
            auto(4) -- negotiate automatically
        }
        MAX-ACCESS  read-write
        STATUS      current
        DESCRIPTION
             "Data path type of this line."
        ::= { zxAnXdsl2LnEntry 60 }          
    
    zxAnXdsl2LnStatusBitswapDs  OBJECT-TYPE
        SYNTAX      INTEGER {
             enabled (1),
             disabled (2)
        }
        MAX-ACCESS  read-write
        STATUS      current
        DESCRIPTION
             "Enabled or disabled the Bitswap of downstream."
        ::= { zxAnXdsl2LnEntry 61 }

    zxAnXdsl2LnStatusBitswapUs  OBJECT-TYPE
        SYNTAX      INTEGER {
             enabled (1),
             disabled (2)
        }
        MAX-ACCESS  read-write
        STATUS      current
        DESCRIPTION
             "Enabled or disabled the Bitswap of upstream."
        ::= { zxAnXdsl2LnEntry 62 }

    zxAnXdsl2LnStatusHighRateLimit  OBJECT-TYPE
        SYNTAX      INTEGER {
             noLimit (1),
             limited (2)
        }
        MAX-ACCESS  read-write
        STATUS      current
        DESCRIPTION
             "Enabled or disabled the high rate limitation."
        ::= { zxAnXdsl2LnEntry 63 }         
     
     zxAnXdsl2LnExtConfPrf  OBJECT-TYPE
        SYNTAX      DisplayString (SIZE(1..32))
        MAX-ACCESS  read-write
        STATUS      current
        DESCRIPTION
           "The value of this object identifies the row in the xDSL2
           Line Dpbo Profile Table, (zxAnXdsl2LnExtConfPrfTable),
            which applies for this line.
     
            This object MUST be maintained in a persistent manner."
        DEFVAL       { "VDEFVAL" }
        ::= { zxAnXdsl2LnEntry 64 }         
                              
     zxAnXdsl2LnStatusPrevAttainRateDs  OBJECT-TYPE
        SYNTAX      Unsigned32
        UNITS       "kbps"
        MAX-ACCESS  read-only
        STATUS      current
        DESCRIPTION
           "Last Maximum Attainable Data Rate Downstream.
            The maximum downstream net data rate attainable by
            the xTU-C transmitter and the xTU-R receiver last time, 
            coded in kbit/s."
        ::= { zxAnXdsl2LnEntry 65 }        
     
     zxAnXdsl2LnStatusPrevAttainRateUs  OBJECT-TYPE
        SYNTAX      Unsigned32
        UNITS       "kbps"
        MAX-ACCESS  read-only
        STATUS      current
        DESCRIPTION
           "Last Maximum Attainable Data Rate Upstream.
            The maximum upstream net data rate attainable by the
            xTU-R transmitter and the xTU-C receiver last time, 
            coded in kbit/s."
        ::= { zxAnXdsl2LnEntry 66 }          
        
     zxAnXdsl2LnCmndPMReset  OBJECT-TYPE        
        SYNTAX BITS {  
             currentPerf(0) 
        }
        MAX-ACCESS  read-write
        STATUS      current
        DESCRIPTION
           "Reset the performance monitoring results of single line.           
           
            currentPerf(0) - reset the current performance monitoring results.
                         it will affect only current real-time PM object, 
                         such as zxAnXdsl2PMChCurrTransmittedBlks, 
                         zxAnXdsl2PMChCurrOverflowBlks and 
                         zxAnXdsl2PMChCurrErroredBlks.   
                                                  
                         The PM result of history will not be reset, 
                         and the current PM result of 15 minutes and 1 day 
                         will be unaffected too.                         
           "
        ::= { zxAnXdsl2LnEntry 67 }                     
               
     zxAnXdsl2LnCustomizedCapability    OBJECT-TYPE
        SYNTAX      BITS 
        MAX-ACCESS  read-write
        STATUS      current
        DESCRIPTION
             "The specific functions reserved by ZTE."
        ::= { zxAnXdsl2LnEntry 80 }                        
                  
    zxAnXdsl2LnInpEtrDs OBJECT-TYPE
        SYNTAX      Unsigned32(0..200000)
        UNITS       "kbps"
        MAX-ACCESS  read-only
        STATUS      current
        DESCRIPTION
            "The expected throughput (ETR)."
        ::= { zxAnXdsl2LnEntry 81 } 

    zxAnXdsl2LnInpEtrUs OBJECT-TYPE
        SYNTAX      Unsigned32(0..200000)
        UNITS       "kbps"
        MAX-ACCESS  read-only
        STATUS      current
        DESCRIPTION
            "The expected throughput (ETR)."
        ::= { zxAnXdsl2LnEntry 82 }       
               
    zxAnXdsl2LnInpEftrDs OBJECT-TYPE
        SYNTAX      Unsigned32(0..200000)
        UNITS       "kbps"
        MAX-ACCESS  read-only
        STATUS      current
        DESCRIPTION
            "The error-free throughput (EFTR is defined as the average 
             bit-rate at the alpha1/beta1 reference point, of bits originating
             from DTU's which have been detected to contain no error at the 
             moment of crossing the alpha1/beta1 reference point."
        ::= { zxAnXdsl2LnEntry 83 }
      
    zxAnXdsl2LnInpEftrUs OBJECT-TYPE
        SYNTAX      Unsigned32(0..200000)
        UNITS       "kbps"
        MAX-ACCESS  read-only
        STATUS      current
        DESCRIPTION
            "The error-free throughput (EFTR is defined as the average 
             bit-rate at the alpha1/beta1 reference point, of bits 
             originating from DTU's which have been detected to contain
             no error at the moment of crossing the alpha1/beta1 reference 
             point."
        ::= { zxAnXdsl2LnEntry 84 }    
                           
    zxAnXdsl2LnInpMinEftrDs OBJECT-TYPE
        SYNTAX      Unsigned32(0..200000)
        UNITS       "kbps"
        MAX-ACCESS  read-only
        STATUS      deprecated
        DESCRIPTION
            "The minimum error-free throughput (EFTR_min is defined as the 
             minimum of the EFTR observed since the last reading of the 
             EFTR_min."
        ::= { zxAnXdsl2LnEntry 85 }    
      
    zxAnXdsl2LnInpMinEftrUs OBJECT-TYPE
        SYNTAX      Unsigned32(0..200000)
        UNITS       "kbps"
        MAX-ACCESS  read-only
        STATUS      deprecated
        DESCRIPTION
            "The minimum error-free throughput (EFTR_min is defined as the 
             minimum of the EFTR observed since the last reading of the 
             EFTR_min."
        ::= { zxAnXdsl2LnEntry 86 } 
               
    zxAnXdsl2LnInpActDelayDs OBJECT-TYPE
        SYNTAX      INTEGER(0..63)
        UNITS       "ms"
        MAX-ACCESS  read-only
        STATUS      current
        DESCRIPTION
            "If retransmission is used in a given transmit direction, this 
             Object is defined as the actual value of the time-independent 
             component of the delay between the alfa1 and beta1 reference 
             points. 
             This can be calculated as the minimum possible instantaneous 
             delay between the alfa1 and beta1 reference points, based on 
             the actual settings of the framing parameters."
        ::= { zxAnXdsl2LnEntry 87 }    
      
    zxAnXdsl2LnInpActDelayUs OBJECT-TYPE
        SYNTAX      INTEGER(0..63)
        UNITS       "ms"
        MAX-ACCESS  read-only
        STATUS      current
        DESCRIPTION
            "If retransmission is used in a given transmit direction, this 
             Object is defined as the actual value of the time-independent 
             component of the delay between the alfa1 and beta1 reference 
             points. 
             This can be calculated as the minimum possible instantaneous 
             delay between the alfa1 and beta1 reference points, based on 
             the actual settings of the framing parameters."
        ::= { zxAnXdsl2LnEntry 88 }
    
    zxAnXdsl2LnFextCancellationDs OBJECT-TYPE
        SYNTAX      INTEGER
        {
            enabled(1),
            disabled(2)
        }
        MAX-ACCESS  read-write
        STATUS      current
        DESCRIPTION
            "Enable/disable downstream FEXT cancellation.
             This configuration parameter shall be defined for each line in a 
             group of vectored lines. It enables or disables FEXT cancellation 
             from all the other vectored lines into a line in the vectored 
             group. If FEXT cancellation is disabled for a line, then no FEXT 
             cancellation shall occur from any other line in the vectored group 
             into that line."
        REFERENCE   "ITU-T G.993.5, paragraph #11.1.1"
        DEFVAL  { enabled }
        ::= { zxAnXdsl2LnEntry 89 }
        
    zxAnXdsl2LnFextCancellationUs OBJECT-TYPE
        SYNTAX      INTEGER
        {
            enabled(1),
            disabled(2)
        }
        MAX-ACCESS  read-write
        STATUS      current
        DESCRIPTION
            "Enable/disable upstream FEXT cancellation.
             This configuration parameter shall be defined for each line in a 
             group of vectored lines. It enables or disables FEXT cancellation 
             from all the other vectored lines into a line in the vectored 
             group. If FEXT cancellation is disabled for a line, then no FEXT 
             cancellation shall occur from any other line in the vectored group 
             into that line."
        REFERENCE   "ITU-T G.993.5, paragraph #11.1.1"
        DEFVAL  { enabled }
        ::= { zxAnXdsl2LnEntry 90 }
        
    zxAnXdsl2LnSosConfPrf  OBJECT-TYPE
        SYNTAX      DisplayString (SIZE(1..32))
        MAX-ACCESS  read-write
        STATUS      current
        DESCRIPTION
            "The value of this object identifies the row in the xDSL2
             Line SOS Profile Table, (zxAnXdsl2SosConfPrfTable),
             which applies for this line.
     
             This object MUST be maintained in a persistent manner."
        REFERENCE    "Broadband Forum TR-252, paragraph #5.4"
        DEFVAL       { "VSOSDEFVAL" }
        ::= { zxAnXdsl2LnEntry 91 }

    zxAnXdsl2LnStatusLnAttenDs  OBJECT-TYPE
        SYNTAX      Integer32(0..1270)
        UNITS       "0.1 dB"
        MAX-ACCESS  read-only
        STATUS      current
        DESCRIPTION
            "Downstream line Attenuation.
             When referring to a band in the downstream direction, it is the
             measured difference in the total power transmitted by the xTU-C
             and the total power received by the xTU-R over all sub-carriers
             of that band during initialization.

             When referring to a band in the upstream direction, it is the
             measured difference in the total power transmitted by the xTU-R
             and the total power received by the xTU-C over all sub-carriers
             of that band during initialization.

             Values range from 0 to 1270 in units of 0.1 dB (Physical values
             are 0 to 127 dB)."
        REFERENCE
            "ITU-T G.997.1, paragraph #7.5.1.9 (LATNds) 
             and paragraph #7.5.1.10 (LATNus)6"
        ::= { zxAnXdsl2LnEntry 92 }
        
    zxAnXdsl2LnStatusLnAttenUs  OBJECT-TYPE
        SYNTAX      Integer32(0..1270)
        UNITS       "0.1 dB"
        MAX-ACCESS  read-only
        STATUS      current
        DESCRIPTION
            "Upstream line Attenuation.
             When referring to a band in the downstream direction, it is the
             measured difference in the total power transmitted by the xTU-C
             and the total power received by the xTU-R over all sub-carriers
             of that band during initialization.

             When referring to a band in the upstream direction, it is the
             measured difference in the total power transmitted by the xTU-R
             and the total power received by the xTU-C over all sub-carriers
             of that band during initialization.

             Values range from 0 to 1270 in units of 0.1 dB (Physical values
             are 0 to 127 dB)."
        REFERENCE
            "ITU-T G.997.1, paragraph #7.5.1.9 (LATNds)
             and paragraph #7.5.1.10 (LATNus)6"
        ::= { zxAnXdsl2LnEntry 93 }
        
    zxAnXdsl2LnStatusSigAttenDs  OBJECT-TYPE
        SYNTAX      Integer32(0..1270)
        UNITS       "0.1 dB"
        MAX-ACCESS  read-only
        STATUS      current
        DESCRIPTION
            "Downstream signal Attenuation.
             When referring to a band in the downstream direction, it is the
             measured difference in the total power transmitted by the xTU-C
             and the total power received by the xTU-R over all sub-carriers
             of that band during Showtime.
             
             When referring to a band in the upstream direction, it is the
             measured difference in the total power transmitted by the xTU-R
             and the total power received by the xTU-C over all sub-carriers
             of that band during Showtime.
             
             Values range from 0 to 1270 in units of 0.1 dB (Physical values
             are 0 to 127 dB)."
        REFERENCE
            "ITU-T G.997.1, paragraph #7.5.1.11 (SATNds)
             and paragraph #7.5.1.12 (SATNus)"
        ::= { zxAnXdsl2LnEntry 94 }
        
    zxAnXdsl2LnStatusSigAttenUs  OBJECT-TYPE
        SYNTAX      Integer32(0..1270)
        UNITS       "0.1 dB"
        MAX-ACCESS  read-only
        STATUS      current
        DESCRIPTION
            "Upstream signal Attenuation.
             When referring to a band in the downstream direction, it is the
             measured difference in the total power transmitted by the xTU-C
             and the total power received by the xTU-R over all sub-carriers
             of that band during Showtime.
             
             When referring to a band in the upstream direction, it is the
             measured difference in the total power transmitted by the xTU-R
             and the total power received by the xTU-C over all sub-carriers
             of that band during Showtime.
             
             Values range from 0 to 1270 in units of 0.1 dB (Physical values
             are 0 to 127 dB)."
        REFERENCE
            "ITU-T G.997.1, paragraph #7.5.1.11 (SATNds)
             and paragraph #7.5.1.12 (SATNus)"
        ::= { zxAnXdsl2LnEntry 95 }
        
    zxAnXdsl2LnStatusSnrMarginDs  OBJECT-TYPE
        SYNTAX      Integer32(-640..630)
        UNITS       "0.1 dB"
        MAX-ACCESS  read-only
        STATUS      current
        DESCRIPTION
            "SNR Margin is the maximum increase in dB of the noise power
             received at the XTU (xTU-R for a band in the downstream direction
             and xTU-C for a band in the upstream direction), such that
             the BER requirements are met for all bearer channels received
             at the XTU. Values range from -640 to 630 in units of 0.1 dB
             (Physical values are -64 to 63 dB)."
        REFERENCE
            "ITU-T G.997.1, paragraph #7.5.1.13 (SNRMds)
             and paragraph #7.5.1.14 (SNRMpbds) 
             and paragraph #7.5.1.16 (SNRMus) 
             and paragraph #7.5.1.17 (SNRMpbus)"             
        ::= { zxAnXdsl2LnEntry 96 }
    
    zxAnXdsl2LnStatusSnrMarginUs  OBJECT-TYPE
        SYNTAX      Integer32(-640..630)
        UNITS       "0.1 dB"
        MAX-ACCESS  read-only
        STATUS      current
        DESCRIPTION
            "SNR Margin is the maximum increase in dB of the noise power
             received at the XTU (xTU-R for a band in the downstream direction
             and xTU-C for a band in the upstream direction), such that
             the BER requirements are met for all bearer channels received
             at the XTU. Values range from -640 to 630 in units of 0.1 dB
             (Physical values are -64 to 63 dB)."
        REFERENCE
            "ITU-T G.997.1, paragraph #7.5.1.13 (SNRMds)
             and paragraph #7.5.1.14 (SNRMpbds) 
             and paragraph #7.5.1.16 (SNRMus) 
             and paragraph #7.5.1.17 (SNRMpbus)"
        ::= { zxAnXdsl2LnEntry 97 }
    
    zxAnXdsl2LnInmConfPrf  OBJECT-TYPE
        SYNTAX      DisplayString (SIZE(1..32))
        MAX-ACCESS  read-write
        STATUS      current
        DESCRIPTION
            "The value of this object identifies the row in the xDSL2
             Line INM Profile Table, (zxAnXdsl2InmConfPrfTable),
             which applies for this line.
     
             This object MUST be maintained in a persistent manner."
        REFERENCE    "Broadband Forum TR-252, paragraph #5.4"
        DEFVAL       { "VINMDEFVAL" }
        ::= { zxAnXdsl2LnEntry 98 }
        
    zxAnXdsl2LnLofStatsDs  OBJECT-TYPE
        SYNTAX      Counter32
        MAX-ACCESS  read-only
        STATUS      current
        DESCRIPTION
            "Downstream count of times that there was LOF."
        REFERENCE    "ITU-T G.997.1, paragraph #7.2.1"
        ::= { zxAnXdsl2LnEntry 99 }
        
    zxAnXdsl2LnLofStatsUs  OBJECT-TYPE
        SYNTAX      Counter32
        MAX-ACCESS  read-only
        STATUS      current
        DESCRIPTION
            "Upstream count of times that there was LOF."
        REFERENCE    "ITU-T G.997.1, paragraph #7.2.1"
        ::= { zxAnXdsl2LnEntry 100 }
       
    zxAnXdsl2LnLolStatsDs  OBJECT-TYPE
        SYNTAX      Counter32
        MAX-ACCESS  read-only
        STATUS      current
        DESCRIPTION
            "Downstream count of times that there was LOL."
        REFERENCE    "ITU-T G.997.1, paragraph #7.2.1"
        ::= { zxAnXdsl2LnEntry 101 }
        
    zxAnXdsl2LnLolStatsUs  OBJECT-TYPE
        SYNTAX      Counter32
        MAX-ACCESS  read-only
        STATUS      current
        DESCRIPTION
            "Upstream count of times that there was LOF."
        REFERENCE    "ITU-T G.997.1, paragraph #7.2.1"
        ::= { zxAnXdsl2LnEntry 102 }
       
    zxAnXdsl2LnLprStatsDs  OBJECT-TYPE
        SYNTAX      Counter32
        MAX-ACCESS  read-only
        STATUS      current
        DESCRIPTION
            "Downstream count of times that there was LPR."
        REFERENCE    "ITU-T G.997.1, paragraph #7.2.1"
        ::= { zxAnXdsl2LnEntry 103 }
        
    zxAnXdsl2LnLprStatsUs  OBJECT-TYPE
        SYNTAX      Counter32
        MAX-ACCESS  read-only
        STATUS      current
        DESCRIPTION
            "Upstream count of times that there was LPR."
        REFERENCE    "ITU-T G.997.1, paragraph #7.2.1"
        ::= { zxAnXdsl2LnEntry 104 }
        
    zxAnXdsl2LnActInpShineDs  OBJECT-TYPE
        SYNTAX      Integer32
        UNITS       "DMT Symbol"
        MAX-ACCESS  read-only
        STATUS      current
        DESCRIPTION
            "The test parameter INP_act_SHINE is defined as the actual INP
             against SHINE of the latency path with retransmission under 
             following specific conditions:
             Assuming impulse noise protection against REIN equal to INPmin_rein
             Assuming EFTR>=ETR
             It shall be calculated by the transmitter during initialization 
             and updated upon OLR.
             The test parameter INP_act_SHINE shall be represented as a 16-bit 
             unsigned integer expressing the value in fractions of DMT symbols 
             witch a granularity of 0.1 symbols.
             The valid range is from 0 to 204.6. The special value 204.7 
             indicates a value of 204.7 or higher."
        REFERENCE    "ITU-T G.998.4, paragraph #11.2.3"
        ::= { zxAnXdsl2LnEntry 105 }
        
    zxAnXdsl2LnActInpShineUs  OBJECT-TYPE
        SYNTAX      Integer32
        UNITS       "DMT Symbol"
        MAX-ACCESS  read-only
        STATUS      current
        DESCRIPTION
            "The test parameter INP_act_SHINE is defined as the actual INP
             against SHINE of the latency path with retransmission under 
             following specific conditions:
             Assuming impulse noise protection against REIN equal to INPmin_rein
             Assuming EFTR>=ETR
             It shall be calculated by the transmitter during initialization 
             and updated upon OLR.
             The test parameter INP_act_SHINE shall be represented as a 16-bit 
             unsigned integer expressing the value in fractions of DMT symbols 
             witch a granularity of 0.1 symbols.
             The valid range is from 0 to 204.6. The special value 204.7 
             indicates a value of 204.7 or higher."
        REFERENCE    "ITU-T G.998.4, paragraph #11.2.3"
        ::= { zxAnXdsl2LnEntry 106 }
        
    zxAnXdsl2LnActInpReinDs  OBJECT-TYPE
        SYNTAX      Integer32
        UNITS       "DMT Symbol"
        MAX-ACCESS  read-only
        STATUS      current
        DESCRIPTION
            "The test parameter INP_act_REIN is defined as the minimum of
             1) the actual INP against REIN of the latency path with 
             retransmission under the following specific conditions:
             Assuming impulse noise protection against REIN equal to INPmin_rein
             Assuming EFTR>=ETR
             2) the actual INP in the latency path carrying the overhead 
             channel.
             It shall be calculated by the transmitter during initialization 
             and updated upon OLR.
             The test parameter INP_act_REIN shall be represented as a 8 bit 
             unsigned integer expressing the value in fractions of DMT symbols 
             witch a granularity of 0.1 symbols.
             The valid range is from 0 to 25.4. The special value 25.5
             indicates a value of 25.5 or higher."
        REFERENCE    "ITU-T G.998.4, paragraph #11.2.4"
        ::= { zxAnXdsl2LnEntry 107 }
        
    zxAnXdsl2LnActInpReinUs  OBJECT-TYPE
        SYNTAX      Integer32
        UNITS       "DMT Symbol"
        MAX-ACCESS  read-only
        STATUS      current
        DESCRIPTION
            "The test parameter INP_act_REIN is defined as the minimum of
             1) the actual INP against REIN of the latency path with 
             retransmission under the following specific conditions:
             Assuming impulse noise protection against REIN equal to INPmin_rein
             Assuming EFTR>=ETR
             2) the actual INP in the latency path carrying the overhead 
             channel.
             It shall be calculated by the transmitter during initialization 
             and updated upon OLR.
             The test parameter INP_act_REIN shall be represented as a 8 bit 
             unsigned integer expressing the value in fractions of DMT symbols 
             witch a granularity of 0.1 symbols.
             The valid range is from 0 to 25.4. The special value 25.5
             indicates a value of 25.5 or higher."
        REFERENCE    "ITU-T G.998.4, paragraph #11.2.4"
        ::= { zxAnXdsl2LnEntry 108 }
 
    zxAnXdsl2LnStatusActRaModeDs  OBJECT-TYPE
        SYNTAX      INTEGER
            {
                manual(1),
                atInit(2),
                dynamic(3),
                dynamicWithSos(4)
            }
        MAX-ACCESS  read-only
        STATUS      current
        DESCRIPTION
            "This parameter indicates the actual active RA-MODE in the 
            downstream direction. 
            If ACT-RA-MODEds equals 1, the link is operating in RA-MODE 1 
            (MANUAL).
            If ACT-RA-MODEds equals 2, the link is operating in RA-MODE 2 
            (AT_INIT).
            If ACT-RA-MODEds equals 3, the link is operating in RA-MODE 3 
            (DYNAMIC).
            NOTE 1 - In [ITU-T G.992.3] ACT-RA-MODEds=3 corresponds to SRA 
            supported. In [ITU-T G.993.2] ACT-RA-MODEds=3 corresponds to 
            SRA supported by both XTUs in the downstream direction, but SOS 
            not supported by both XTUs in the downstream direction. If 
            ACT-RA-MODEds equals 4, the link is operating in RA-MODE 4 
            (DYNAMIC with SOS).
            NOTE 2 - In [ITU-T G.992.3] ACT-RA-MODEds=4 is not defined. 
            In [ITU-T G.993.2] ACT-RA-MODEds=4 corresponds to SOS and SRA 
            supported by both XTUs in the downstream direction."
        REFERENCE  
            "ITU-T G.997.1, paragraph #7.5.1.33.1"
        ::= { zxAnXdsl2LnEntry 109 }     

    zxAnXdsl2LnStatusActRaModeUs  OBJECT-TYPE
        SYNTAX      INTEGER
            {
                manual(1),
                atInit(2),
                dynamic(3),
                dynamicWithSos(4)
            }
        MAX-ACCESS  read-only
        STATUS      current
        DESCRIPTION
            "This parameter indicates the actual active RA-MODE in the upstream 
            direction.
            If ACT-RA-MODEus equals 1, the link is operating in RA-MODE 1 
            (MANUAL).
            If ACT-RA-MODEus equals 2, the link is operating in RA-MODE 2 
            (AT_INIT).
            If ACT-RA-MODEus equals 3, the link is operating in RA-MODE 3 
            (DYNAMIC).
            NOTE 1 - In [ITU-T G.992.3] ACT-RA-MODEus=3 corresponds to SRA 
            supported. In [ITU-T G.993.2] ACT-RA-MODEus=3 corresponds to SRA 
            supported by both XTUs in the upstream direction, but SOS not 
            supported by both XTUs in the upstream direction. If ACT-RA-MODEus 
            equals 4, the link is operating in RA-MODE 4 (DYNAMIC with SOS).
            NOTE 2 - In [ITU-T G.992.3] ACT-RA-MODEus=4 is not defined. 
            In [ITU-T G.993.2] ACT-RA-MODEus=4 corresponds to SOS and SRA 
            supported by both XTUs in the upstream direction."
        REFERENCE  
            "ITU-T G.997.1, paragraph #7.5.1.33.2"
        ::= { zxAnXdsl2LnEntry 110 }  
        
    zxAnXdsl2LnStatusRtxUsedDs  OBJECT-TYPE
        SYNTAX      INTEGER
            {
                used(1),
                forbidden(2),
                xtucUnsupported(3),
                xturUnsupported(4),
                xtucAndXturUnsupported(5)
            }
        MAX-ACCESS  read-only
        STATUS      current
        DESCRIPTION
            "This parameter specifies whether ITU-T G.998.4 retransmission 
            is used (i.e., active in showtime) in a given transmit direction. 
            The parameter in downstream is RTX_USED_ds, and the parameter in 
            upstream is RTX_USED_us. In [ITU-T G.992.3] and [ITU-T G.992.5] 
            only the downstream parameter RTX_USED_ds is relevant, the value 
            in the upstream direction shall be ignored. In [ITU-T G.993.2], 
            both parameters are relevant.
            1: RTX in use.
            2: RTX not in use, due to RTX_MODE = FORBIDDEN.
            3: RTX not in use, due to not supported by the XTU-C.
            4: RTX not in use, due to not supported by the XTU-R.
            5: RTX not in use, due to not supported by the XTU-C and XTU-R.
            This parameter shall also be reported in the case of 
            RTX_MODE = RTX_FORCED with INIT FAILURE or with 
            RTX_MODE = RTX_TESTMODE with INIT FAILURE.
            NOTE - In the latter case, this parameter will give detailed 
            information on top of the INIT FAILURE reason code."
        REFERENCE  
            "ITU-T G.997.1, paragraph #7.5.1.38"
        ::= { zxAnXdsl2LnEntry 111}   
        
    zxAnXdsl2LnStatusRtxUsedUs  OBJECT-TYPE
        SYNTAX      INTEGER
            {
                used(1),
                forbidden(2),
                xtucUnsuppoted(3),
                xturUnsuppoted(4),
                xtucAndXturUnsuppoted(5)
            }
        MAX-ACCESS  read-only
        STATUS      current
        DESCRIPTION
            "This parameter specifies whether ITU-T G.998.4 retransmission 
            is used (i.e., active in showtime) in a given transmit direction. 
            The parameter in downstream is RTX_USED_ds, and the parameter in 
            upstream is RTX_USED_us. In [ITU-T G.992.3] and [ITU-T G.992.5] 
            only the downstream parameter RTX_USED_ds is relevant, the value 
            in the upstream direction shall be ignored. In [ITU-T G.993.2], 
            both parameters are relevant.
            1: RTX in use.
            2: RTX not in use, due to RTX_MODE = FORBIDDEN.
            3: RTX not in use, due to not supported by the XTU-C.
            4: RTX not in use, due to not supported by the XTU-R.
            5: RTX not in use, due to not supported by the XTU-C and XTU-R.
            This parameter shall also be reported in the case of 
            RTX_MODE = RTX_FORCED with INIT FAILURE or with 
            RTX_MODE = RTX_TESTMODE with INIT FAILURE.
            NOTE - In the latter case, this parameter will give detailed 
            information on top of the INIT FAILURE reason code."
        REFERENCE  
            "ITU-T G.997.1, paragraph #7.5.1.38"
        ::= { zxAnXdsl2LnEntry 112}  

-----------------------------------------------------------------------------
-- zxAnXdsl2LnBandTable
-----------------------------------------------------------------------------         
      
   zxAnXdsl2LnBandTable  OBJECT-TYPE
       SYNTAX      SEQUENCE  OF  ZxAnXdsl2LnBandEntry
       MAX-ACCESS  not-accessible
       STATUS      current
       DESCRIPTION
          "The table zxAnXdsl2LnBandTable contains the,
           per-band line status parameters of the VDSL2/ADSL/ADSL2
           or ADSL2+ line.
           The indexes of this table consist of an interface index where the
           interface has an ifType of vdsl2(xxx), together with a
           per-band index covering both VDSL2 and ADSL/ADSL2/ADSL2+.
           The parameters in this table are updated at
           line initialisation time and at showtime."
       ::= { zxAnXdsl2Line 11 }
    
   zxAnXdsl2LnBandEntry  OBJECT-TYPE
       SYNTAX      ZxAnXdsl2LnBandEntry
       MAX-ACCESS  not-accessible
       STATUS      current
       DESCRIPTION
          "The table zxAnXdsl2LnBandTable contains the,
           per-band line status parameters of the VDSL2/ADSL/ADSL2
           or ADSL2+ line."
       AUGMENTS  { xdsl2LineBandEntry }
       ::= { zxAnXdsl2LnBandTable 1 }
    
   ZxAnXdsl2LnBandEntry  ::=
       SEQUENCE {                
          zxAnXdsl2LineBandStatusPrevSnrMargin          Integer32          
       }    
        
   zxAnXdsl2LineBandStatusPrevSnrMargin  OBJECT-TYPE
      SYNTAX      Integer32 (-640..630 | 2147483646 | 2147483647)
      UNITS       "0.1 dB"
      MAX-ACCESS  read-only
      STATUS      current
      DESCRIPTION
         "The Last SNR Margin.
          SNR Margin is the maximum increase in dB of the noise power
          received at the XTU (xTU-R for a band in the downstream direction
          and xTU-C for a band in the upstream direction), such that
          the BER requirements are met for all bearer channels received
          at the XTU. Values range from -640 to 630 in units of 0.1 dB
          (Physical values are -64 to 63 dB).
          A special value of 0x7FFFFFFF (2147483647) indicates the
          SNR Margin is out of range to be represented.
          A special value of 0x7FFFFFFE (2147483646) indicates the
          SNR Margin measurement is currently unavailable."
      REFERENCE    "ITU-T G.997.1, paragraph #7.5.1.13 (SNRMds)
                  and paragraph #7.5.1.14 (SNRMpbds)
                  and paragraph #7.5.1.16 (SNRMus)
                  and paragraph #7.5.1.17 (SNRMpbus)"
      DEFVAL       { 2147483646 }
      ::= { zxAnXdsl2LnBandEntry 1 }
        
-----------------------------------------------------------------------------
-- zxAnXdsl2DsDataRateConfPrfTable
------------------------------------------------------------------------------
   zxAnXdsl2DsDataRateConfPrfTable  OBJECT-TYPE
        SYNTAX      SEQUENCE  OF  ZxAnXdsl2DsDataRateConfPrfEntry
        MAX-ACCESS  not-accessible
        STATUS      current
        DESCRIPTION
            "The DsDataRate Profile contains the downstream parameters related to the service 
            offer of all bearers.
            
            Entries in this table MUST be maintained in a
            persistent manner."
        ::= { zxAnXdsl2LineProfile 10 }


   zxAnXdsl2DsDataRateConfPrfEntry  OBJECT-TYPE
        SYNTAX      ZxAnXdsl2DsDataRateConfPrfEntry
        MAX-ACCESS  not-accessible
        STATUS      current
        DESCRIPTION
         "The table zxAnXdsl2DsDataRateConfPrfTable contains VDSL2/ADSL/
          ADSL2 and ADSL2+ basic configuration profile.

          A default profile with an index of 'VDEFVAL' will
          always exist and its parameters will be set to vendor-specific
          values, unless otherwise specified in this document"
        INDEX  { zxAnXdsl2DsDataRateConfPrfName }
        ::= { zxAnXdsl2DsDataRateConfPrfTable 1 }

   ZxAnXdsl2DsDataRateConfPrfEntry  ::=
        SEQUENCE {
            zxAnXdsl2DsDataRateConfPrfName       DisplayString,
            
            zxAnXdsl2ChConfChannRaRatioDs        Unsigned32,
            zxAnXdsl2ChConfMinDataRateDs         Unsigned32,
            zxAnXdsl2ChConfMaxDataRateDs         Unsigned32,
            zxAnXdsl2ChConfMinResRateDs          Unsigned32,
            zxAnXdsl2ChConfMinRateLowPwrDs       Unsigned32,                      
            zxAnXdsl2ChConfMaxBerDs              Xdsl2MaxBer,
            zxAnXdsl2ChConfDsDataRateDs          Unsigned32,
            zxAnXdsl2ChConfUsDataRateDs          Unsigned32,
            zxAnXdsl2ChConfMinSosBitRateDs       Unsigned32,
            
            zxAnXdsl2DsDataRatePrfRowStatus  RowStatus
      }

   zxAnXdsl2DsDataRateConfPrfName  OBJECT-TYPE
        SYNTAX      DisplayString (SIZE(1..32))
        MAX-ACCESS  not-accessible
        STATUS      current
        DESCRIPTION
            "This object identifies a row in this table."
        ::= { zxAnXdsl2DsDataRateConfPrfEntry 1 }

   zxAnXdsl2ChConfChannRaRatioDs  OBJECT-TYPE
      SYNTAX      Unsigned32(0..100)
      UNITS       "percents"
      MAX-ACCESS  read-create
      STATUS      current
      DESCRIPTION
         "Rate Adaptation Ratio.  The ratio (in %) that should be taken
          into account for the bearer channel #1 when performing rate
          adaptation on Downstream.  The ratio refers to the available
          data rate in excess of the Minimum Data Rate, summed over all
          bearer channels.  Also, the 100 -
          Xdsl2ConfTemplateChan1RaRatioDs is the ratio of excess data
          rate to be assigned to all other bearer channels on Downstream
          direction.  The sum of rate adaptation ratios over all bearers
          on the same direction shall be equal to 100%."
      REFERENCE    "ITU-T G.997.1, paragraph 7.3.2.1"
      DEFVAL       { 100 }
      ::= { zxAnXdsl2DsDataRateConfPrfEntry 2 }
    
    zxAnXdsl2ChConfMinDataRateDs  OBJECT-TYPE
       SYNTAX      Unsigned32(0..200000)
       UNITS       "kbps"
       MAX-ACCESS  read-create
       STATUS      current
       DESCRIPTION
          "Minimum Data Rate on Downstream direction.  The minimum net
           data rate for the bearer channel, coded in bit/s."
       REFERENCE    "ITU-T G.997.1, paragraph #7.3.2.1"
       DEFVAL       { 32 }
       ::= { zxAnXdsl2DsDataRateConfPrfEntry 3 }       
    
    zxAnXdsl2ChConfMaxDataRateDs  OBJECT-TYPE
       SYNTAX      Unsigned32(0..200000)
       UNITS       "kbps"
       MAX-ACCESS  read-create
       STATUS      current
       DESCRIPTION
          "Maximum Data Rate on Downstream direction.  The maximum net
           data rate for the bearer channel, coded in bit/s."
       REFERENCE    "ITU-T G.997.1, paragraph #7.3.2.1"
       ::= { zxAnXdsl2DsDataRateConfPrfEntry 4 }    

    zxAnXdsl2ChConfMinResRateDs  OBJECT-TYPE
        SYNTAX      Unsigned32(0..200000)
        UNITS       "kbps"
        MAX-ACCESS  read-create
        STATUS      current
        DESCRIPTION
           "Minimum Reserved Data Rate on Downstream direction.  The
            minimum reserved net data rate for the bearer channel, coded
            in bit/s.  This parameter is used only if the Rate Adaptation
            Mode in the direction of the bearer channel (i.e.,
            Xdsl2LineConfRaModeDs) is set to DynamicRa."
        REFERENCE    "ITU-T G.997.1, paragraph 7.3.2.1"
        ::= { zxAnXdsl2DsDataRateConfPrfEntry 5 }
  

    zxAnXdsl2ChConfMinRateLowPwrDs  OBJECT-TYPE
        SYNTAX      Unsigned32(0..200000)
        UNITS       "kbps"
        MAX-ACCESS  read-create
        STATUS      current
        DESCRIPTION
           "Minimum Data Rate in Low Power state on Downstream direction.
            The minimum net data rate for the bearer channel, coded in
            bit/s., during the low power state (L1 in G.992.2, L2 in
            G.992.3)."
        REFERENCE    "ITU-T G.997.1, paragraph 7.3.2.1"
        ::= { zxAnXdsl2DsDataRateConfPrfEntry 6 }
                                    
    zxAnXdsl2ChConfMaxBerDs  OBJECT-TYPE
       SYNTAX      Xdsl2MaxBer
       MAX-ACCESS  read-create
       STATUS      current
       DESCRIPTION
          "Maximum Bit Error Ratio on Downstream direction.  The
          maximum
           bit error ratio for the bearer channel.  The parameter can
           take the following values (for 1E-3, 1E-5 or 1E-7):
              eminus3 (1),
              eminus5 (2),
              eminus7 (3)"
       REFERENCE    "ITU-T G.997.1, paragraph #7.3.2.6"
       DEFVAL       { eminus7 }
      ::= { zxAnXdsl2DsDataRateConfPrfEntry 7 }
      
      
    zxAnXdsl2ChConfDsDataRateDs  OBJECT-TYPE
       SYNTAX      Unsigned32(0..200000000)
       UNITS       "bits/second"
       MAX-ACCESS  read-create
       STATUS      current
       DESCRIPTION
          "Data Rate Threshold Downshift for downstream direction.  A
           'Down-shift rate change' event is triggered when the
           actual
           downstream data rate is below the data rate at the last entry
           into Showtime, by more than the threshold.  The parameter is
           coded in bit/s."
       REFERENCE    "ITU-T G.997.1, paragraph #7.3.2.8.1"
       ::= { zxAnXdsl2DsDataRateConfPrfEntry 8 }    

    zxAnXdsl2ChConfUsDataRateDs  OBJECT-TYPE
       SYNTAX      Unsigned32(0..200000000)
       UNITS       "bits/second"
       MAX-ACCESS  read-create
       STATUS      current
       DESCRIPTION
          "Data Rate Threshold Up shift for downstream direction.  An
           'Up-shift rate change' event is triggered when the
           actual
           downstream data rate exceeds, by more than the threshold, the
           data rate at the last entry into Showtime.  The parameter is
           coded in bit/s."
       REFERENCE    "ITU-T G.997.1, paragraph #7.3.2.8.1"
       ::= { zxAnXdsl2DsDataRateConfPrfEntry 9 }
       
   zxAnXdsl2ChConfMinSosBitRateDs  OBJECT-TYPE
       SYNTAX      Unsigned32(0..200000)
       UNITS       "kbps"
       MAX-ACCESS  read-create
       STATUS      current
       DESCRIPTION
          "This parameter specifies the minimum net data rate required for a
           valid SOS request in the downstream direction. 
           The value shall be coded as an unsigned integer representing the 
           data rate as a multiple of 8 kbit/s."
       REFERENCE    "ITU-T G.997.1, paragraph #7.3.2.1.6"
       ::= { zxAnXdsl2DsDataRateConfPrfEntry 10 }
                                
   zxAnXdsl2DsDataRatePrfRowStatus  OBJECT-TYPE
        SYNTAX      RowStatus
        MAX-ACCESS  read-create
        STATUS      current
        DESCRIPTION
           "This object is used to create a new row or to modify or
           delete an existing row in this table.
  
           A profile is activated by setting this object to 'active'.
           When 'active' is set, the system will validate the profile.
           Profile modification is prohibited while this object is set
           to 'active'.
  
           Before a profile can be deleted or taken out of service
           (by setting this object to 'destroy' or 'notInService'),
           it must be first unreferenced from all associated
           ports."
        ::= { zxAnXdsl2DsDataRateConfPrfEntry 80 }      
    
    
    
-----------------------------------------------------------------------------
-- zxAnXdsl2UsDataRateConfPrfTable
------------------------------------------------------------------------------
   zxAnXdsl2UsDataRateConfPrfTable  OBJECT-TYPE
        SYNTAX      SEQUENCE  OF  ZxAnXdsl2UsDataRateConfPrfEntry
        MAX-ACCESS  not-accessible
        STATUS      current
        DESCRIPTION
            "The UsDataRate Profile contains the upstream parameters related to the service 
            offer of all bearers.
            
            Entries in this table MUST be maintained in a
            persistent manner."
        ::= { zxAnXdsl2LineProfile 11 }

   zxAnXdsl2UsDataRateConfPrfEntry  OBJECT-TYPE
        SYNTAX      ZxAnXdsl2UsDataRateConfPrfEntry
        MAX-ACCESS  not-accessible
        STATUS      current
        DESCRIPTION
         "The table zxAnXdsl2UsDataRateConfPrfTable contains VDSL2/ADSL/
          ADSL2 and ADSL2+ basic configuration profile.

          A default profile with an index of 'VDEFVAL' will
          always exist and its parameters will be set to vendor-specific
          values, unless otherwise specified in this document"
        INDEX  { zxAnXdsl2UsDataRateConfPrfName }
        ::= { zxAnXdsl2UsDataRateConfPrfTable 1 }

   ZxAnXdsl2UsDataRateConfPrfEntry  ::=
        SEQUENCE {
            zxAnXdsl2UsDataRateConfPrfName       DisplayString,
            
            zxAnXdsl2ChConfChannRaRatioUs        Unsigned32,
            zxAnXdsl2ChConfMinDataRateUs         Unsigned32,
            zxAnXdsl2ChConfMaxDataRateUs         Unsigned32,
            zxAnXdsl2ChConfMinResRateUs          Unsigned32,
            zxAnXdsl2ChConfMinRateLowPwrUs       Unsigned32,                      
            zxAnXdsl2ChConfMaxBerUs              Xdsl2MaxBer,
            zxAnXdsl2ChConfDsDataRateUs          Unsigned32,
            zxAnXdsl2ChConfUsDataRateUs          Unsigned32,
            zxAnXdsl2ChConfMinSosBitRateUs       Unsigned32,
            
            zxAnXdsl2UsDataRatePrfRowStatus  RowStatus
      }

   zxAnXdsl2UsDataRateConfPrfName  OBJECT-TYPE
        SYNTAX      DisplayString (SIZE(1..32))
        MAX-ACCESS  not-accessible
        STATUS      current
        DESCRIPTION
            "This object identifies a row in this table."
        ::= { zxAnXdsl2UsDataRateConfPrfEntry 1 }
        
   zxAnXdsl2ChConfChannRaRatioUs  OBJECT-TYPE
      SYNTAX      Unsigned32(0..100)
      UNITS       "percents"
      MAX-ACCESS  read-create
      STATUS      current
      DESCRIPTION
         "Rate Adaptation Ratio.  The ratio (in %) that should be taken
          into account for the bearer channel #1 when performing rate
          adaptation on Upstream.  The ratio refers to the available
          data rate in excess of the Minimum Data Rate, summed over all
          bearer channels.  Also, the
          100 - Xdsl2ConfTemplateChan1RaRatioUs is the ratio of excess
          data rate to be assigned to all other bearer channels on
          Upstream direction.  The sum of rate adaptation ratios over
          all bearers on the same direction shall be equal to 100 %."
      REFERENCE    "ITU-T G.997.1, paragraph 7.3.2.1"
      DEFVAL       { 100 }
      ::= { zxAnXdsl2UsDataRateConfPrfEntry 2 }


    zxAnXdsl2ChConfMinDataRateUs  OBJECT-TYPE
       SYNTAX      Unsigned32(0..200000)
       UNITS       "kbps"
       MAX-ACCESS  read-create
       STATUS      current
       DESCRIPTION
          "Minimum Data Rate on Upstream direction.  The minimum net
          data rate for the bearer channel, coded in bit/s."
       REFERENCE    "ITU-T G.997.1, paragraph #7.3.2.1"
       DEFVAL       { 32 }
       ::= { zxAnXdsl2UsDataRateConfPrfEntry 3 }


    zxAnXdsl2ChConfMaxDataRateUs  OBJECT-TYPE
       SYNTAX      Unsigned32(0..200000)
       UNITS       "kbps"
       MAX-ACCESS  read-create
       STATUS      current
       DESCRIPTION
          "Maximum Data Rate on Upstream direction.  The maximum net
          data rate for the bearer channel, coded in bit/s."
       REFERENCE    "ITU-T G.997.1, paragraph #7.3.2.1"
       ::= { zxAnXdsl2UsDataRateConfPrfEntry 4 }
    
    
    zxAnXdsl2ChConfMinResRateUs  OBJECT-TYPE
        SYNTAX      Unsigned32(0..200000)
        UNITS       "kbps"
        MAX-ACCESS  read-create
        STATUS      current
        DESCRIPTION
           "Minimum Reserved Data Rate on Upstream direction.  The minimum
            reserved net data rate for the bearer channel, coded in
            bit/s.  This parameter is used only if the Rate Adaptation
            Mode in the direction of the bearer channel (i.e.,
            Xdsl2LineConfRaModeUs) is set to DynamicRa."
        REFERENCE    "ITU-T G.997.1, paragraph 7.3.2.1"
        ::= { zxAnXdsl2UsDataRateConfPrfEntry 5 }


   zxAnXdsl2ChConfMinRateLowPwrUs  OBJECT-TYPE
        SYNTAX      Unsigned32(0..200000)
        UNITS       "kbps"
        MAX-ACCESS  read-create
        STATUS      current
        DESCRIPTION
           "Minimum Data Rate in Low Power state on upstream direction.
            The minimum net data rate for the bearer channel, coded in
            bit/s., during the low power state (L1 in G.992.2, L2 in
            G.992.3)."
        REFERENCE    "ITU-T G.997.1, paragraph 7.3.2.1"
        ::= { zxAnXdsl2UsDataRateConfPrfEntry 6 }
         
    zxAnXdsl2ChConfMaxBerUs  OBJECT-TYPE
       SYNTAX      Xdsl2MaxBer
       MAX-ACCESS  read-create
       STATUS      current
       DESCRIPTION
          "Maximum Bit Error Ratio on Upstream direction.  The maximum
           bit error ratio for the bearer channel.  The parameter can
           take the following values (for 1E-3, 1E-5 or 1E-7):
              eminus3 (1),
              eminus5 (2),
              eminus7 (3)"
       REFERENCE    "ITU-T G.997.1, paragraph #7.3.2.6"
       DEFVAL       { eminus7 }
       ::= { zxAnXdsl2UsDataRateConfPrfEntry 7 }  
       
    zxAnXdsl2ChConfDsDataRateUs  OBJECT-TYPE
       SYNTAX      Unsigned32(0..200000000)
       UNITS       "bits/second"
       MAX-ACCESS  read-create
       STATUS      current
       DESCRIPTION
          "Data Rate Threshold Downshift for upstream direction.  A
           'Down-shift rate change' event is triggered when the
           actual
           upstream data rate is below the data rate at the last entry
           into Showtime, by more than the threshold.  The parameter is
           coded in bit/s."
       REFERENCE    "ITU-T G.997.1, paragraph #7.3.2.8.1"
       ::= { zxAnXdsl2UsDataRateConfPrfEntry 8 }      
       
       
    zxAnXdsl2ChConfUsDataRateUs  OBJECT-TYPE
       SYNTAX      Unsigned32(0..200000000)
       UNITS       "bits/second"
       MAX-ACCESS  read-create
       STATUS      current
       DESCRIPTION
          "Data Rate Threshold Up shift for upstream direction.  An
           'Up-shift rate change' event is triggered when the
           actual
           upstream data rate exceeds, by more than the threshold, the
           data rate at the last entry into Showtime.  The parameter is
           coded in bit/s."
       REFERENCE    "ITU-T G.997.1, paragraph #7.3.2.8.1"
       ::= { zxAnXdsl2UsDataRateConfPrfEntry 9 }    
       
   zxAnXdsl2ChConfMinSosBitRateUs  OBJECT-TYPE
       SYNTAX      Unsigned32(0..200000)
       UNITS       "kbps"
       MAX-ACCESS  read-create
       STATUS      current
       DESCRIPTION
          "This parameter specifies the minimum net data rate required for a
           valid SOS request in the upstream direction. 
           The value shall be coded as an unsigned integer representing the 
           data rate as a multiple of 8 kbit/s."
       REFERENCE    "ITU-T G.997.1, paragraph #7.3.2.1.7"
       ::= { zxAnXdsl2UsDataRateConfPrfEntry 10 }
                                
   zxAnXdsl2UsDataRatePrfRowStatus  OBJECT-TYPE
        SYNTAX      RowStatus
        MAX-ACCESS  read-create
        STATUS      current
        DESCRIPTION
           "This object is used to create a new row or to modify or
           delete an existing row in this table.
  
           A profile is activated by setting this object to 'active'.
           When 'active' is set, the system will validate the profile.
           Profile modification is prohibited while this object is set
           to 'active'.
  
           Before a profile can be deleted or taken out of service
           (by setting this object to 'destroy' or 'notInService'),
           it must be first unreferenced from all associated
           ports."
        ::= { zxAnXdsl2UsDataRateConfPrfEntry 80 }          
    
------------------------------------------------------------------------------
-- zxAnXdsl2SpectrumConfPrfTable
------------------------------------------------------------------------------
            
   zxAnXdsl2SpectrumConfPrfTable  OBJECT-TYPE
        SYNTAX      SEQUENCE  OF  ZxAnXdsl2SpectrumConfPrfEntry
        MAX-ACCESS  not-accessible
        STATUS      current
        DESCRIPTION
            "The Line Spectrum Profile contains the parameters that identify the 
            basic characteristics of the spectrum used on the line 
            (xDSL mode, PSD, aggregate power).
            
            Entries in this table MUST be maintained in a
            persistent manner."
        ::= { zxAnXdsl2LineProfile 12 }


   zxAnXdsl2SpectrumConfPrfEntry  OBJECT-TYPE
        SYNTAX      ZxAnXdsl2SpectrumConfPrfEntry
        MAX-ACCESS  not-accessible
        STATUS      current
        DESCRIPTION
         " A default profile with an index of 'VDEFVAL' will
          always exist and its parameters will be set to vendor-specific
          values, unless otherwise specified in this document"
        INDEX  { zxAnXdsl2SpectrumConfPrfName }
        ::= { zxAnXdsl2SpectrumConfPrfTable 1 }

   ZxAnXdsl2SpectrumConfPrfEntry  ::=
        SEQUENCE {
            zxAnXdsl2SpectrumConfPrfName    DisplayString,
            zxAnXdsl2LConfXtuTransSysEna        ZxAnXdsl2TransmissionModeType,
            zxAnXdsl2LConfScMaskDs              Xdsl2ScMaskDs,
            zxAnXdsl2LConfScMaskUs              Xdsl2ScMaskUs,
            zxAnXdsl2LConfVdsl2CarMask          Xdsl2CarMask,
            zxAnXdsl2LConfMsgMinDs              Unsigned32,
            zxAnXdsl2LConfMsgMinUs              Unsigned32,           
            zxAnXdsl2LConfCeFlag                Xdsl2LineCeFlag,
            
            zxAnXdsl2LConfPmMode                Xdsl2LinePmMode,
            zxAnXdsl2LConfL0Time                Unsigned32,
            zxAnXdsl2LConfL2Time                Unsigned32,
            zxAnXdsl2LConfL2Atpr                Unsigned32,
            zxAnXdsl2LConfL2Atprt               Unsigned32,
            zxAnXdsl2LConfProfiles              Xdsl2LineProfiles,
            zxAnXdsl2LConfUs0Mask               Xdsl2LineUs0Mask,
                        
            zxAnXdsl2SpectrumPrfRowStatus             RowStatus
        }
         
    zxAnXdsl2SpectrumConfPrfName  OBJECT-TYPE
        SYNTAX      DisplayString (SIZE(1..32))
        MAX-ACCESS  not-accessible
        STATUS      current
        DESCRIPTION
            "This object identifies a row in this table."
        ::= { zxAnXdsl2SpectrumConfPrfEntry 1 }
        
                            
    zxAnXdsl2LConfXtuTransSysEna  OBJECT-TYPE
        SYNTAX      ZxAnXdsl2TransmissionModeType
        MAX-ACCESS  read-create
        STATUS      current
        DESCRIPTION
         "xTU Transmission System Enabling (xTSE).  A list of the
          different coding types enabled in this profile.  It is coded
          in a bit-map representation with 1 or more bits set.  A bit
          set to  '1' means that the xTUs may apply the respective
          coding for the DSL line.  A bit set to '0' means that
          the xTUs cannot apply the respective coding for the ADSL
          line.  All 'reserved' bits should be set to '0'."
        REFERENCE    "ITU-T G.997.1, paragraph 7.3.1.1.1"
        ::= { zxAnXdsl2SpectrumConfPrfEntry 2 }


     
     zxAnXdsl2LConfScMaskDs  OBJECT-TYPE
        SYNTAX      Xdsl2ScMaskDs
        MAX-ACCESS  read-create
        STATUS      current
        DESCRIPTION
           "Sub-carriers mask.  A bitmap of 4096 bits that allows
           masking
            up to 4096 downstream sub-carriers, depending on NSCds.  If
            bit i (0 <= i < NSCds) is set to '1', the
            respective
            downstream sub-carrier i is masked, and if set to '0',
            the
            respective sub-carrier is unmasked.  Note that there should
            always be unmasked sub-carriers (i.e., the object cannot be
            all 1's).  Also note that if NSCds < 4096, all bits
            i (NSCds i <= 4096) should be set to '1'."
        REFERENCE    "ITU-T G.997.1, paragraph #7.3.1.2.6"
        ::= { zxAnXdsl2SpectrumConfPrfEntry 3 }
     
     zxAnXdsl2LConfScMaskUs  OBJECT-TYPE
        SYNTAX      Xdsl2ScMaskUs
        MAX-ACCESS  read-create
        STATUS      current
        DESCRIPTION
           "Sub-carriers mask.  A bitmap of 4096 bits that allows
           masking
            up to 4096 downstream sub-carriers, depending on NSCds.  If
            bit i (0 <= i < NSCus) is set to '1', the
            respective
            upstream sub-carrier i is masked, and if set to '0',
            the
            respective sub-carrier is unmasked.  Note that there
            should always be unmasked sub-carriers (i.e., the object
            cannot be all 1's).  Also note that if NSCus <
            4096, all bits i (NSCus < i <= 4096) should be set to
            '1'."
        REFERENCE    "ITU-T G.997.1, paragraph #7.3.1.2.7"
        ::= { zxAnXdsl2SpectrumConfPrfEntry 4 }
        

    zxAnXdsl2LConfVdsl2CarMask  OBJECT-TYPE
        SYNTAX      Xdsl2CarMask
        MAX-ACCESS  read-create
        STATUS      current
        DESCRIPTION
           "(VDSL2-CARMASK).
           VDSL2 specific Sub-carriers mask.  This configuration
           parameter defines the restrictions, additional to the band
           plan, to determine the set of subcarriers allowed for
           transmission in both upstream and downstream directions.
           The parameter shall describe the not masked subcarriers as
           one or more frequency bands. Each band is represented by
           start and stop subcarrier indices with a subcarrier
           spacing of 4.3125kHz. The valid range of subcarrier indices
           run from 0 to at least the index of the highest allowed
           subcarrier in both transmission directions among all
           profiles enabled by the parameter zxAnXdsl2LConfPrfiles.
           Up to 32 bands may be specified. Other subcarriers shall
           be masked."
        REFERENCE    "ITU-T G.997.1, paragraph #7.3.1.2.8"
        ::= { zxAnXdsl2SpectrumConfPrfEntry 5 }

     
     zxAnXdsl2LConfMsgMinDs  OBJECT-TYPE
        SYNTAX      Unsigned32(4..248)
        UNITS       "kbps"
        MAX-ACCESS  read-create
        STATUS      current
        DESCRIPTION
           "Minimum Overhead Rate Downstream.  Defines the minimum rate
           of
            the message-based overhead that shall be maintained by the xTU
            in downstream direction.  Expressed in bits per second and
            ranges from 4000 to 63000 bps."
        REFERENCE    "ITU-T G.997.1, paragraph #7.3.1.5.2"
        DEFVAL       { 4 }
        ::= { zxAnXdsl2SpectrumConfPrfEntry 6 }


    zxAnXdsl2LConfMsgMinUs  OBJECT-TYPE
        SYNTAX      Unsigned32(4..248)
        UNITS       "kbps"
        MAX-ACCESS  read-create
        STATUS      current
        DESCRIPTION
           "Minimum Overhead Rate Upstream.  Defines the minimum rate of
            the message-based overhead that shall be maintained by the xTU
            in upstream direction.  Expressed in bits per second and
            ranges from 4000 to 63000 bps."
        REFERENCE    "ITU-T G.997.1, paragraph #7.3.1.5.1"
        DEFVAL       { 4 }
       ::= { zxAnXdsl2SpectrumConfPrfEntry 7 }
       
    
    zxAnXdsl2LConfCeFlag     OBJECT-TYPE
       SYNTAX      Xdsl2LineCeFlag
       MAX-ACCESS  read-create
       STATUS      current
       DESCRIPTION
          "(CEFLAG).
           This parameter is a bit that enables the use of the optional
           cyclic extension values. If the bit is set to 1, the optional
           cyclic extension values may be used. Otherwise, the cyclic
           extension shall be forced to the mandatory length (5N/32)."
       REFERENCE    "ITU-T G.997.1, paragraph #7.3.1.6.1"
       DEFVAL       { { } }
       ::= { zxAnXdsl2SpectrumConfPrfEntry 8 }
    

     zxAnXdsl2LConfPmMode  OBJECT-TYPE
        SYNTAX      Xdsl2LinePmMode
        MAX-ACCESS  read-create
        STATUS      current
        DESCRIPTION
           "Power management state Enabling (PMMode).  Defines the power
            states the xTU-C or xTU-R may autonomously transition to on
            this line.
            The various bit positions are: allowTransitionsToIdle (0) and
            allowTransitionsToLowPower (1).  A bit with a '1' value
            means
            that the xTU is allowed to transit into the respective state
            and a '0' value means that the xTU is not allowed
            to transit into the respective state."
        REFERENCE    "ITU-T G.997.1, paragraph #7.3.1.1.4"
        DEFVAL  { { } }
        ::= { zxAnXdsl2SpectrumConfPrfEntry 9 }
        

     zxAnXdsl2LConfL0Time  OBJECT-TYPE
        SYNTAX      Unsigned32 (0..255)
        UNITS       "seconds"
        MAX-ACCESS  read-create
        STATUS      current
        DESCRIPTION
           "The minimum time (in seconds) between an Exit from the L2
            state and the next Entry into the L2 state (L0-TIME).
            It ranges from 0 to 255 seconds."
        REFERENCE    "ITU-T G.997.1, paragraph #7.3.1.1.5"
        DEFVAL       { 255 }
        ::= { zxAnXdsl2SpectrumConfPrfEntry 10 }
        
        
     zxAnXdsl2LConfL2Time  OBJECT-TYPE
        SYNTAX      Unsigned32 (0..255)
        UNITS       "seconds"
        MAX-ACCESS  read-create
        STATUS      current
        DESCRIPTION
           "The minimum time (in seconds) between an Entry into the
           L2 state and the first Power Trim in the L2 state and between
           two consecutive Power Trims in the L2 State (L2-TIME).
           It ranges from 0 to 255 seconds."
        REFERENCE    "ITU-T G.997.1, paragraph #7.3.1.1.6"
        DEFVAL       { 255 }
        ::= { zxAnXdsl2SpectrumConfPrfEntry 11 }
        

     zxAnXdsl2LConfL2Atpr  OBJECT-TYPE
        SYNTAX      Unsigned32 (0..31)
        UNITS       "dB"
        MAX-ACCESS  read-create
        STATUS      current
        DESCRIPTION
           "The maximum aggregate transmit power reduction (in dB) that
            can be performed at transition of L0 to L2 state or through a
            single Power Trim in the L2 state (L2-ATPR).
            It ranges from 0 dB to 31 dB."
        REFERENCE    "ITU-T G.997.1, paragraph #7.3.1.1.7"
        DEFVAL       { 3 }
        ::= { zxAnXdsl2SpectrumConfPrfEntry 12 }      
        
        
     zxAnXdsl2LConfL2Atprt  OBJECT-TYPE
        SYNTAX      Unsigned32 (0..31)
        UNITS       "dB"
        MAX-ACCESS  read-create
        STATUS      current
        DESCRIPTION
           "The total maximum aggregate transmit power reduction
           (in dB) that can be performed in an L2 state. This is the
           sum of all reductions of L2 Request (i.e., at transition of
           L0 to L2 state) and Power Trims (L2-ATPRT)."
        REFERENCE    "ITU-T G.997.1, paragraph #7.3.1.1.9"
        DEFVAL       { 31 }
        ::= { zxAnXdsl2SpectrumConfPrfEntry 13 }
        

     zxAnXdsl2LConfProfiles  OBJECT-TYPE
       SYNTAX      Xdsl2LineProfiles
       MAX-ACCESS  read-create
       STATUS      current
       DESCRIPTION
          " The configuration parameter contains the G.993.2
          profiles to be allowed by the near-end xTU on this line
          (PROFILES).
          It is coded in a bitmap representation (0 if not allowed,
          1 if allowed) "
       REFERENCE    "ITU-T G.997.1, paragraph #7.3.1.1.11"
       DEFVAL       { { profile17a } }
       ::= { zxAnXdsl2SpectrumConfPrfEntry 14 }  
       

    zxAnXdsl2LConfUs0Mask  OBJECT-TYPE
        SYNTAX      Xdsl2LineUs0Mask
        MAX-ACCESS  read-create
        STATUS      current
        DESCRIPTION
            "The set of profiles which allows the transceivers to support 
            a subset of allowed settings, as defined in G.993.2 Recommendation."
        ::= { zxAnXdsl2SpectrumConfPrfEntry 15 }


    zxAnXdsl2SpectrumPrfRowStatus  OBJECT-TYPE
        SYNTAX      RowStatus
        MAX-ACCESS  read-create
        STATUS      current
        DESCRIPTION
           "This object is used to create a new row or to modify or
           delete an existing row in this table.
  
           A profile is activated by setting this object to 'active'.
           When 'active' is set, the system will validate the profile.
           Profile modification is prohibited while this object is set
           to 'active'.
  
           Before a profile can be deleted or taken out of service
           (by setting this object to 'destroy' or 'notInService'),
           it must be first unreferenced from all associated
           ports."
        ::= { zxAnXdsl2SpectrumConfPrfEntry 30 }      


    
  
-----------------------------------------------------------------------------
-- zxAnXdsl2DpboConfPrfTable
------------------------------------------------------------------------------

   zxAnXdsl2DpboConfPrfTable  OBJECT-TYPE
        SYNTAX      SEQUENCE  OF  ZxAnXdsl2DpboConfPrfEntry
        MAX-ACCESS  not-accessible
        STATUS      current
        DESCRIPTION
            "The DPBO Profile contains all the parameters related to the 
            ownstream PBO shaping.
            
            Entries in this table MUST be maintained in a
            persistent manner."
        ::= { zxAnXdsl2LineProfile 13 }


   zxAnXdsl2DpboConfPrfEntry  OBJECT-TYPE
        SYNTAX      ZxAnXdsl2DpboConfPrfEntry
        MAX-ACCESS  not-accessible
        STATUS      current
        DESCRIPTION
         " A default profile with an index of 'VDEFVAL' will
          always exist and its parameters will be set to vendor-specific
          values, unless otherwise specified in this document"
        INDEX  { zxAnXdsl2DpboConfPrfName }
        ::= { zxAnXdsl2DpboConfPrfTable 1 }

   ZxAnXdsl2DpboConfPrfEntry  ::=
        SEQUENCE {
            zxAnXdsl2DpboConfPrfName            DisplayString,
            zxAnXdsl2LConfDpboEPsd              Xdsl2PsdMaskDs,
            zxAnXdsl2LConfDpboEsEL              Unsigned32,
            zxAnXdsl2LConfDpboEscmA             Unsigned32,
            zxAnXdsl2LConfDpboEscmB             Unsigned32,
            zxAnXdsl2LConfDpboEscmC             Unsigned32,
            zxAnXdsl2LConfDpboMus               Unsigned32,
            zxAnXdsl2LConfDpboFMin              Unsigned32,
            zxAnXdsl2LConfDpboFMax              Unsigned32,
            zxAnXdsl2DpboConfPrfRowStatus       RowStatus
            }            


    zxAnXdsl2DpboConfPrfName  OBJECT-TYPE
        SYNTAX      DisplayString (SIZE(1..32))
        MAX-ACCESS  not-accessible
        STATUS      current
        DESCRIPTION
            "This object identifies a row in this table."
        ::= { zxAnXdsl2DpboConfPrfEntry 1 }

    zxAnXdsl2LConfDpboEPsd  OBJECT-TYPE
        SYNTAX      Xdsl2PsdMaskDs
        MAX-ACCESS  read-create
        STATUS      current
        DESCRIPTION
           "(DPBOEPSD).
           This configuration parameter defines the PSD mask that
           is assumed to be permitted at the exchange. This parameter
           shall use the same format as zxAnXdsl2LConfPsdMaskDs (PSDMASKds).
           The maximum number of breakpoints for zxAnXdsl2LConfDpboEPsd is
           16."
        REFERENCE   "ITU-T G.997.1, paragraph #7.3.1.2.13"
        ::= { zxAnXdsl2DpboConfPrfEntry 2 }
     
    zxAnXdsl2LConfDpboEsEL  OBJECT-TYPE
        SYNTAX      Unsigned32 (0..511)
        UNITS       "0.5 dB"
        MAX-ACCESS  read-create
        STATUS      current
        DESCRIPTION
           "(DPBOESEL).
           This configuration parameter defines the assumed
           electrical length of cables (E-side cables) connecting
           exchange based DSL services to a remote flexibility point
           (cabinet), that hosts the xTU-C that is subject to
           spectrally shaped downstream power back-off (DPBO)
           depending on this length. The electrical length is
           defined as the loss (in dB) of an equivalent length of
           hypothetical cable at a reference frequency defined by
           the network operator or in spectrum management regulations.
           This parameter shall be coded as an unsigned integer
           representing an electrical length from 0 dB (coded as 0)
           to 255.5 dB (coded as 511) in steps of 0.5 dB. All values
           in the range are valid. If this parameter is set to zero,
           the DPBO shall be disabled."
        REFERENCE   "ITU-T G.997.1, paragraph #7.3.1.2.13"
        DEFVAL      { 0 }
        ::= { zxAnXdsl2DpboConfPrfEntry 3 }
     
    zxAnXdsl2LConfDpboEscmA  OBJECT-TYPE
        SYNTAX      Unsigned32 (0..640)
        UNITS       "2^-8"
        MAX-ACCESS  read-create
        STATUS      current
        DESCRIPTION
           "(DPBOESCMA).
           The E-side Cable Model parameter A (DPBOESCMA) of the
           cable model (DPBOESCM) for cables connecting exchange based DSL
           services to a remote flexibility point (cabinet), that hosts
           the xTU-C that is subject to spectrally shaped downstream
           power back-off (DPBO) depending on this value.
           The cable model is in terms of three
           scalars zxAnXdsl2LConfDpboEsCableModelA (DPBOESCMA),
          zxAnXdsl2LConfDpboEsCableModelB(DPBOESCMB),
           and zxAnXdsl2LConfDpboEsCableModelC (DPBOESCMC),
           that are used to estimate the frequency dependent loss of E-side
           cables calculated from the zxAnXdsl2LConfDpboEsEL (DPBOESEL)
           parameter. Possible values shall be coded as unsigned integers
           representing a scalar value from -1 (coded as 0) to
           1.5 (coded as 640) in steps of 2^-8. All values in the range are
           valid. This parameter is used only for G.993.2."
        REFERENCE   "ITU-T G.997.1, paragraph #7.3.1.2.13"
        DEFVAL      { 263 }
        ::= { zxAnXdsl2DpboConfPrfEntry 4 }
     
    zxAnXdsl2LConfDpboEscmB  OBJECT-TYPE
        SYNTAX      Unsigned32 (0..640)
        UNITS       "2^-8"
        MAX-ACCESS  read-create
        STATUS      current
        DESCRIPTION
           "(DPBOESCMB).
           The E-side Cable Model parameter B (DPBOESCMB) of the
           cable model (DPBOESCM) for cables connecting exchange based DSL
           services to a remote flexibility point (cabinet), that hosts
           the xTU-C that is subject to spectrally shaped downstream
           power back-off (DPBO) depending on this value.
           The cable model is in terms of three
           scalars zxAnXdsl2LConfDpboEsCableModelA (DPBOESCMA),
           zxAnXdsl2LConfDpboEsCableModelB(DPBOESCMB),
           and zxAnXdsl2LConfDpboEsCableModelC (DPBOESCMC),
           that are used to estimate the frequency dependent loss of E-side
           cables calculated from the zxAnXdsl2LConfDpboEsEL (DPBOESEL)
           parameter. Possible values shall be coded as unsigned integers
           representing a scalar value from -1 (coded as 0) to
           1.5 (coded as 640) in steps of 2^-8. All values in the range are
           valid. This parameter is used only for G.993.2."
        REFERENCE   "ITU-T G.997.1, paragraph #7.3.1.2.13"
        DEFVAL      { 509 }
        ::= { zxAnXdsl2DpboConfPrfEntry 5 }
     
    zxAnXdsl2LConfDpboEscmC  OBJECT-TYPE
        SYNTAX      Unsigned32 (0..640)
        UNITS       "2^-8"
        MAX-ACCESS  read-create
        STATUS      current
        DESCRIPTION
           "(DPBOESCMC).
           The E-side Cable Model parameter C (DPBOESCMC) of the
           cable model (DPBOESCM) for cables connecting exchange based DSL
           services to a remote flexibility point (cabinet), that hosts
           the xTU-C that is subject to spectrally shaped downstream
           power back-off (DPBO) depending on this value.
           The cable model is in terms of three
           scalars zxAnXdsl2LConfDpboEsCableModelA (DPBOESCMA),
           zxAnXdsl2LConfDpboEsCableModelB(DPBOESCMB),
           and zxAnXdsl2LConfDpboEsCableModelC (DPBOESCMC),
           that are used to estimate the frequency dependent loss of E-side
           cables calculated from the zxAnXdsl2LConfDpboEsEL (DPBOESEL)
           parameter. Possible values shall be coded as unsigned integers
           representing a scalar value from -1 (coded as 0) to
           1.5 (coded as 640) in steps of 2^-8. All values in the range are
           valid. This parameter is used only for G.993.2."
        REFERENCE   "ITU-T G.997.1, paragraph #7.3.1.2.13"
        DEFVAL      { 261 }
        ::= { zxAnXdsl2DpboConfPrfEntry 6 }
     
    zxAnXdsl2LConfDpboMus OBJECT-TYPE
        SYNTAX      Unsigned32 (0..255)
        UNITS       "0.5 dB"
        MAX-ACCESS  read-create
        STATUS      current
        DESCRIPTION
           "(DPBOMUS).
           This configuration parameter defines the assumed Minimum Usable
           receive PSD mask (in dBm/Hz) for exchange based services,
           used to modify parameter zxAnXdsl2LConfDpboFMax (DPBOFMAX) defined
           below [to determine the DPBO]. It shall be coded as an unsigned
           integer representing a PSD mask level from 0 dBm/Hz (coded as 0)
           to -127.5 dBm/Hz (coded as 255) in steps of 0.5 dB. All values
           in the range are valid.
           NOTE - The PSD mask level is 3.5 dB above the signal PSD
           level. This parameter is used only for G.993.2."
        REFERENCE   "ITU-T G.997.1, paragraph #7.3.1.2.13"
        DEFVAL      { 190 }
        ::= { zxAnXdsl2DpboConfPrfEntry 7 }
     
    zxAnXdsl2LConfDpboFMin OBJECT-TYPE
        SYNTAX      Unsigned32 (0..2048)
        UNITS       "4.3125 kHz"
        MAX-ACCESS  read-create
        STATUS      current
        DESCRIPTION
           "(DPBOFMIN).
           This configuration parameter defines the minimum frequency
           from which the DPBO shall be applied. It ranges from
           0 kHz (coded as 0) to 8832 kHz (coded as 2048) in steps
           of 4.3125 kHz. This parameter is used only for G.993.2."
        REFERENCE   "ITU-T G.997.1, paragraph #7.3.1.2.13"
        DEFVAL      { 32 }
        ::= { zxAnXdsl2DpboConfPrfEntry 8 }
     
    zxAnXdsl2LConfDpboFMax OBJECT-TYPE
        SYNTAX      Unsigned32 (32..6956)
        UNITS       "4.3125 kHz"
        MAX-ACCESS  read-create
        STATUS      current
        DESCRIPTION
           "(DPBOFMAX).
           This configuration parameter defines the maximum frequency at
           which DPBO may be applied. It ranges from 138 kHz (coded as 32)
           to 29997.75 kHz (coded as 6956) in steps of 4.3125 kHz.
           This parameter is used only for G.993.2."
        REFERENCE   "ITU-T G.997.1, paragraph #7.3.1.2.13"
        DEFVAL      { 511 }
        ::= { zxAnXdsl2DpboConfPrfEntry 9 }
     
     
   zxAnXdsl2DpboConfPrfRowStatus  OBJECT-TYPE
        SYNTAX      RowStatus
        MAX-ACCESS  read-create
        STATUS      current
        DESCRIPTION
           "This object is used to create a new row or to modify or
           delete an existing row in this table.
  
           A profile is activated by setting this object to 'active'.
           When 'active' is set, the system will validate the profile.
           Profile modification is prohibited while this object is set
           to 'active'.
  
           Before a profile can be deleted or taken out of Dpbo
           (by setting this object to 'destroy' or 'notInService'),
           it must be first unreferenced from all associated
           ports."
        ::= { zxAnXdsl2DpboConfPrfEntry 30 }



-----------------------------------------------------------------------------
-- zxAnXdsl2UpboConfPrfTable
-----------------------------------------------------------------------------

   zxAnXdsl2UpboConfPrfTable  OBJECT-TYPE
        SYNTAX      SEQUENCE  OF  ZxAnXdsl2UpboConfPrfEntry
        MAX-ACCESS  not-accessible
        STATUS      current
        DESCRIPTION
            "The UPBO Profile contains all the parameters related to the 
            Upstream PBO shaping.
            
            Entries in this table MUST be maintained in a
            persistent manner."
        ::= { zxAnXdsl2LineProfile 14 }


   zxAnXdsl2UpboConfPrfEntry  OBJECT-TYPE
        SYNTAX      ZxAnXdsl2UpboConfPrfEntry
        MAX-ACCESS  not-accessible
        STATUS      current
        DESCRIPTION
         "
          A default profile with an index of 'VDEFVAL' will
          always exist and its parameters will be set to vendor-specific
          values, unless otherwise specified in this document"
        INDEX  { zxAnXdsl2LUpboConfPrfName }
        ::= { zxAnXdsl2UpboConfPrfTable 1 }

   ZxAnXdsl2UpboConfPrfEntry  ::=
        SEQUENCE {
            zxAnXdsl2LUpboConfPrfName        DisplayString,
            zxAnXdsl2LConfUpboKL             Unsigned32,
            zxAnXdsl2LConfUpboKLF            Xdsl2UpboKLF,
            zxAnXdsl2LConfUpboU1bandPsdA     Unsigned32,
            zxAnXdsl2LConfUpboU1bandPsdB     Unsigned32,
            zxAnXdsl2LConfUpboU2bandPsdA     Unsigned32,
            zxAnXdsl2LConfUpboU2bandPsdB     Unsigned32,
            zxAnXdsl2LConfUpboU3bandPsdA     Unsigned32,
            zxAnXdsl2LConfUpboU3bandPsdB     Unsigned32,
            zxAnXdsl2LConfUpboU4bandPsdA     Unsigned32,
            zxAnXdsl2LConfUpboU4bandPsdB     Unsigned32,
            
            zxAnXdsl2LConfUpboU1bandKLRef    Unsigned32,
            zxAnXdsl2LConfUpboU2bandKLRef    Unsigned32,
            zxAnXdsl2LConfUpboU3bandKLRef    Unsigned32,
            zxAnXdsl2LConfUpboU4bandKLRef    Unsigned32,
            
            zxAnXdsl2LUpboConfPrfRowStatus   RowStatus
            }
            
    zxAnXdsl2LUpboConfPrfName  OBJECT-TYPE
        SYNTAX      DisplayString (SIZE(1..32))
        MAX-ACCESS  not-accessible
        STATUS      current
        DESCRIPTION
            "This object identifies a row in this table."
        ::= { zxAnXdsl2UpboConfPrfEntry 1 }

             
    zxAnXdsl2LConfUpboKL  OBJECT-TYPE
        SYNTAX      Unsigned32 (0..1280)
        UNITS       "0.1 dB"
        MAX-ACCESS  read-create
        STATUS      current
        DESCRIPTION
           "(UPBOKL).
           This configuration parameter defines the electrical length
           expressed in dB at 1MHz, kl0, configured by the CO-MIB.
           The value ranges from 0 (coded as 0) to 128 dB (coded as 1280)
           in steps of 0.1 dB. This parameter is relevant only if
           zxAnXdsl2LConfUpboKLF is set to override(2), which indicates
           that this parameter's value will override the VTUs'
           determination of the electrical length. If zxAnXdsl2LConfUpboKLF
           is set either to auto(1) or disableUpbo(3), then this parameter
           will be ignored."
        REFERENCE   "ITU-T G.997.1, paragraph #7.3.1.2.14"
        DEFVAL      { 0 }
        ::= { zxAnXdsl2UpboConfPrfEntry 2 }
     
    zxAnXdsl2LConfUpboKLF OBJECT-TYPE
        SYNTAX      Xdsl2UpboKLF
        MAX-ACCESS  read-create
        STATUS      current
        DESCRIPTION
           "Defines the upstream power backoff force mode (UPBOKLF).  "
        REFERENCE   "ITU-T G.997.1, paragraph #7.3.1.2.14"
        DEFVAL      { disableUpbo }
        ::= { zxAnXdsl2UpboConfPrfEntry 3 }
     
         
     
     
    zxAnXdsl2LConfUpboU1bandPsdA  OBJECT-TYPE
        SYNTAX      Unsigned32(4000..8095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfUpboPsdA) ranges from 40 dBm/Hz (coded as 4000) to
           80.95 dBm/Hz (coded as 8095) in steps of 0.01 dBm/Hz; and
           parameter 'b' (zxAnXdsl2LConfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfUpboPsdA to 4000 and zxAnXdsl2LConfUpboPsdB to 0 is
           a special configuration to disable UPBO in the respective
           upstream band."
        REFERENCE   "ITU-T G.997.1, paragraph #7.3.1.2.14"
        DEFVAL      { 5650 }
       ::= { zxAnXdsl2UpboConfPrfEntry 4 }
       
       
         
    zxAnXdsl2LConfUpboU1bandPsdB  OBJECT-TYPE
        SYNTAX      Unsigned32(0..4095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfUpboPsdA) ranges from 40 dBm/Hz (coded as 4000) to
           80.95 dBm/Hz (coded as 8095) in steps of 0.01 dBm/Hz; and
           parameter 'b' (zxAnXdsl2LConfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfUpboPsdA to 4000 and zxAnXdsl2LConfUpboPsdB to 0 is
           a special configuration to disable UPBO in the respective
           upstream band."
        REFERENCE   "ITU-T G.997.1, paragraph #7.3.1.2.14"
        DEFVAL      { 1020 }
       ::= { zxAnXdsl2UpboConfPrfEntry 5 }   
               
     
     
     
    zxAnXdsl2LConfUpboU2bandPsdA  OBJECT-TYPE
        SYNTAX      Unsigned32(4000..8095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfUpboPsdA) ranges from 40 dBm/Hz (coded as 4000) to
           80.95 dBm/Hz (coded as 8095) in steps of 0.01 dBm/Hz; and
           parameter 'b' (zxAnXdsl2LConfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfUpboPsdA to 4000 and zxAnXdsl2LConfUpboPsdB to 0 is
           a special configuration to disable UPBO in the respective
           upstream band."
        REFERENCE   "ITU-T G.997.1, paragraph #7.3.1.2.14"
        DEFVAL      { 5650 }
       ::= { zxAnXdsl2UpboConfPrfEntry 6 }
       
       
         
    zxAnXdsl2LConfUpboU2bandPsdB  OBJECT-TYPE
        SYNTAX      Unsigned32(0..4095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfUpboPsdA) ranges from 40 dBm/Hz (coded as 4000) to
           80.95 dBm/Hz (coded as 8095) in steps of 0.01 dBm/Hz; and
           parameter 'b' (zxAnXdsl2LConfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfUpboPsdA to 4000 and zxAnXdsl2LConfUpboPsdB to 0 is
           a special configuration to disable UPBO in the respective
           upstream band."
        REFERENCE   "ITU-T G.997.1, paragraph #7.3.1.2.14"
        DEFVAL      { 615 }
       ::= { zxAnXdsl2UpboConfPrfEntry 7 }
       
       
     
    zxAnXdsl2LConfUpboU3bandPsdA  OBJECT-TYPE
        SYNTAX      Unsigned32(4000..8095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfUpboPsdA) ranges from 40 dBm/Hz (coded as 4000) to
           80.95 dBm/Hz (coded as 8095) in steps of 0.01 dBm/Hz; and
           parameter 'b' (zxAnXdsl2LConfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfUpboPsdA to 4000 and zxAnXdsl2LConfUpboPsdB to 0 is
           a special configuration to disable UPBO in the respective
           upstream band."
        REFERENCE   "ITU-T G.997.1, paragraph #7.3.1.2.14"
        DEFVAL      { 5650 }
       ::= { zxAnXdsl2UpboConfPrfEntry 8 }
       
       
         
    zxAnXdsl2LConfUpboU3bandPsdB  OBJECT-TYPE
        SYNTAX      Unsigned32(0..4095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfUpboPsdA) ranges from 40 dBm/Hz (coded as 4000) to
           80.95 dBm/Hz (coded as 8095) in steps of 0.01 dBm/Hz; and
           parameter 'b' (zxAnXdsl2LConfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfUpboPsdA to 4000 and zxAnXdsl2LConfUpboPsdB to 0 is
           a special configuration to disable UPBO in the respective
           upstream band."
        REFERENCE   "ITU-T G.997.1, paragraph #7.3.1.2.14"
        DEFVAL      { 615 }
       ::= { zxAnXdsl2UpboConfPrfEntry 9 }



    zxAnXdsl2LConfUpboU4bandPsdA  OBJECT-TYPE
        SYNTAX      Unsigned32(4000..8095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfUpboPsdA) ranges from 40 dBm/Hz (coded as 4000) to
           80.95 dBm/Hz (coded as 8095) in steps of 0.01 dBm/Hz; and
           parameter 'b' (zxAnXdsl2LConfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfUpboPsdA to 4000 and zxAnXdsl2LConfUpboPsdB to 0 is
           a special configuration to disable UPBO in the respective
           upstream band."
        REFERENCE   "ITU-T G.997.1, paragraph #7.3.1.2.14"
        DEFVAL      { 4000 }
       ::= { zxAnXdsl2UpboConfPrfEntry 10 }
       
       
         
    zxAnXdsl2LConfUpboU4bandPsdB  OBJECT-TYPE
        SYNTAX      Unsigned32(0..4095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfUpboPsdA) ranges from 40 dBm/Hz (coded as 4000) to
           80.95 dBm/Hz (coded as 8095) in steps of 0.01 dBm/Hz; and
           parameter 'b' (zxAnXdsl2LConfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfUpboPsdA to 4000 and zxAnXdsl2LConfUpboPsdB to 0 is
           a special configuration to disable UPBO in the respective
           upstream band."
        REFERENCE   "ITU-T G.997.1, paragraph #7.3.1.2.14"
        DEFVAL      { 0 }
       ::= { zxAnXdsl2UpboConfPrfEntry 11 }      
          
                       
         
    zxAnXdsl2LConfUpboU1bandKLRef OBJECT-TYPE
        SYNTAX      Unsigned32
        UNITS       "0.1 dB"
        MAX-ACCESS  read-create
        STATUS      current
        DESCRIPTION
            "
            This parameter defines the UPBO reference electrical length used to 
            compute the upstream power back-off for each upstream band except US0, 
            for the optional Equalized FEXT UPBO method. The value ranges from 
            1.8 to 63.5 dB in steps of 0.1 dB with special value 0. 
            The use of the special value 0 is described in 7.2.1.3.2/G.993.2.
            "
        DEFVAL      { 0 }
       ::= { zxAnXdsl2UpboConfPrfEntry 12 }   
              
         
    zxAnXdsl2LConfUpboU2bandKLRef OBJECT-TYPE
        SYNTAX      Unsigned32
        UNITS       "0.1 dB"
        MAX-ACCESS  read-create
        STATUS      current
        DESCRIPTION
            "
            This parameter defines the UPBO reference electrical length used to 
            compute the upstream power back-off for each upstream band except US0, 
            for the optional Equalized FEXT UPBO method. The value ranges from 
            1.8 to 63.5 dB in steps of 0.1 dB with special value 0. 
            The use of the special value 0 is described in 7.2.1.3.2/G.993.2.
            "
        DEFVAL      { 0 }
       ::= { zxAnXdsl2UpboConfPrfEntry 13 }      
           
         
    zxAnXdsl2LConfUpboU3bandKLRef OBJECT-TYPE
        SYNTAX      Unsigned32
        UNITS       "0.1 dB"
        MAX-ACCESS  read-create
        STATUS      current
        DESCRIPTION
            "
            This parameter defines the UPBO reference electrical length used to 
            compute the upstream power back-off for each upstream band except US0, 
            for the optional Equalized FEXT UPBO method. The value ranges from 
            1.8 to 63.5 dB in steps of 0.1 dB with special value 0. 
            The use of the special value 0 is described in 7.2.1.3.2/G.993.2.
            "
        DEFVAL      { 0 }
       ::= { zxAnXdsl2UpboConfPrfEntry 14 }       
          
         
    zxAnXdsl2LConfUpboU4bandKLRef OBJECT-TYPE
        SYNTAX      Unsigned32
        UNITS       "0.1 dB"
        MAX-ACCESS  read-create
        STATUS      current
        DESCRIPTION
            "
            This parameter defines the UPBO reference electrical length used to 
            compute the upstream power back-off for each upstream band except US0, 
            for the optional Equalized FEXT UPBO method. The value ranges from 
            1.8 to 63.5 dB in steps of 0.1 dB with special value 0. 
            The use of the special value 0 is described in 7.2.1.3.2/G.993.2.
            "
        DEFVAL      { 0 }
       ::= { zxAnXdsl2UpboConfPrfEntry 15 }   
  
  
    zxAnXdsl2LUpboConfPrfRowStatus  OBJECT-TYPE
        SYNTAX      RowStatus
        MAX-ACCESS  read-create
        STATUS      current
        DESCRIPTION
           "This object is used to create a new row or to modify or
           delete an existing row in this table.
  
           A profile is activated by setting this object to 'active'.
           When 'active' is set, the system will validate the profile.
           Profile modification is prohibited while this object is set
           to 'active'.
  
           Before a profile can be deleted or taken out of Upbo
           (by setting this object to 'destroy' or 'notInService'),
           it must be first unreferenced from all associated
           ports."
        ::= { zxAnXdsl2UpboConfPrfEntry 30 }



-----------------------------------------------------------------------------
-- zxAnXdsl2SnrMarginConfPrfTable
------------------------------------------------------------------------------
   zxAnXdsl2SnrMarginConfPrfTable  OBJECT-TYPE
        SYNTAX      SEQUENCE  OF  ZxAnXdsl2SnrMarginConfPrfEntry
        MAX-ACCESS  not-accessible
        STATUS      current
        DESCRIPTION
            "The Noise Margin Profile contains all the noise margin parameters 
            to be defined for the line.
            
            Entries in this table MUST be maintained in a
            persistent manner."
        ::= { zxAnXdsl2LineProfile 15 }


   zxAnXdsl2SnrMarginConfPrfEntry  OBJECT-TYPE
        SYNTAX      ZxAnXdsl2SnrMarginConfPrfEntry
        MAX-ACCESS  not-accessible
        STATUS      current
        DESCRIPTION
         "A default profile with an index of 'VDEFVAL' will
          always exist and its parameters will be set to vendor-specific
          values, unless otherwise specified in this document"
        INDEX  { zxAnXdsl2SnrMarginConfPrfName }
        ::= { zxAnXdsl2SnrMarginConfPrfTable 1 }

   ZxAnXdsl2SnrMarginConfPrfEntry  ::=
        SEQUENCE {
            zxAnXdsl2SnrMarginConfPrfName       DisplayString,
            zxAnXdsl2LConfTargetSnrmDs          Unsigned32,
            zxAnXdsl2LConfTargetSnrmUs          Unsigned32,
            zxAnXdsl2LConfMaxSnrmDs             Unsigned32,
            zxAnXdsl2LConfMaxSnrmUs             Unsigned32,
            zxAnXdsl2LConfMinSnrmDs             Unsigned32,
            zxAnXdsl2LConfMinSnrmUs             Unsigned32,
            
            zxAnXdsl2LConfRaUsNrmDs             Unsigned32,
            zxAnXdsl2LConfRaUsNrmUs             Unsigned32,
            zxAnXdsl2LConfRaUsTimeDs            Unsigned32,
            zxAnXdsl2LConfRaUsTimeUs            Unsigned32,
            zxAnXdsl2LConfRaDsNrmDs             Unsigned32,
            zxAnXdsl2LConfRaDsNrmUs             Unsigned32,
            zxAnXdsl2LConfRaDsTimeDs            Unsigned32,
            zxAnXdsl2LConfRaDsTimeUs            Unsigned32,
            zxAnXdsl2LConfSnrModeDs             Xdsl2LineSnrMode,
            zxAnXdsl2LConfSnrModeUs             Xdsl2LineSnrMode,
            zxAnXdsl2LConfRaModeDs              Xdsl2RaMode,
            zxAnXdsl2LConfRaModeUs              Xdsl2RaMode,
            
            zxAnXdsl2SnrMarginConfRowStatus     RowStatus
      }


    zxAnXdsl2SnrMarginConfPrfName  OBJECT-TYPE
        SYNTAX      DisplayString (SIZE(1..32))
        MAX-ACCESS  not-accessible
        STATUS      current
        DESCRIPTION
            "This object identifies a row in this table."
        ::= { zxAnXdsl2SnrMarginConfPrfEntry 1 }
                        
   zxAnXdsl2LConfTargetSnrmDs  OBJECT-TYPE
      SYNTAX      Unsigned32(0..310)
      UNITS       "0.1 dB"
      MAX-ACCESS  read-create
      STATUS      current
      DESCRIPTION
         "The minimum Noise Margin the xTU-R receiver shall achieve,

          relative to the BER requirement for each of the downstream

          bearer channels, to successfully complete initialization.
          The target noise margin ranges from 0 to 310 units of 0.1 dB
          (Physical values are 0 to 31 dB)."
      REFERENCE    "ITU-T G.997.1, paragraph 7.3.1.3.1"
      DEFVAL       { 60 }
      ::= { zxAnXdsl2SnrMarginConfPrfEntry 2 }

   zxAnXdsl2LConfTargetSnrmUs  OBJECT-TYPE
      SYNTAX      Unsigned32(0..310)
      UNITS       "0.1 dB"
      MAX-ACCESS  read-create
      STATUS      current
      DESCRIPTION
         "The minimum Noise Margin the xTU-C receiver shall achieve,

          relative to the BER requirement for each of the upstream

          bearer channels, to successfully complete initialization.
          The target noise margin ranges from 0 to 310 units of 0.1 dB
          (Physical values are 0 to 31 dB)."
      REFERENCE    "ITU-T G.997.1, paragraph 7.3.1.3.2"
      DEFVAL       { 60 }
      ::= { zxAnXdsl2SnrMarginConfPrfEntry 3 }

    
    
    zxAnXdsl2LConfMaxSnrmDs  OBJECT-TYPE
       SYNTAX      Unsigned32 (0..310 | 2147483647)
       UNITS       "0.1 dB"
       MAX-ACCESS  read-create
       STATUS      current
       DESCRIPTION
          "The maximum Noise Margin the xTU-R receiver shall try to
           sustain.  If the Noise Margin is above this level, the xTU-R
           shall request that the xTU-C reduce the xTU-C transmit power
           to get a noise margin below this limit (if this functionality
           is supported).  The maximum noise margin ranges from 0 to 310
           units of 0.1 dB (Physical values are 0 to 31 dB).  A value of
           0x7FFFFFFF (2147483647) means that there is no maximum."
       REFERENCE    "ITU-T G.997.1, paragraph #7.3.1.3.3"
       DEFVAL       { 300 }
       ::= { zxAnXdsl2SnrMarginConfPrfEntry 4 }
    
    zxAnXdsl2LConfMaxSnrmUs  OBJECT-TYPE
       SYNTAX      Unsigned32 (0..310 | 2147483647)
       UNITS       "0.1 dB"
       MAX-ACCESS  read-create
       STATUS      current
       DESCRIPTION
          "The maximum Noise Margin the xTU-C receiver shall try to
           sustain.  If the Noise Margin is above this level, the xTU-C
           shall request that the xTU-R reduce the xTU-R transmit power
           to get a noise margin below this limit (if this functionality
           is supported).  The maximum noise margin ranges from 0 to 310
           units of 0.1 dB (Physical values are 0 to 31 dB).  A value of
           0x7FFFFFFF (2147483647) means that there is no maximum."
       REFERENCE    "ITU-T G.997.1, paragraph #7.3.1.3.4"
       DEFVAL       { 300 }
       ::= { zxAnXdsl2SnrMarginConfPrfEntry 5 }
    
    zxAnXdsl2LConfMinSnrmDs  OBJECT-TYPE
       SYNTAX      Unsigned32(0..310)
       UNITS       "0.1 dB"
       MAX-ACCESS  read-create
       STATUS      current
       DESCRIPTION
          "The minimum Noise Margin the xTU-R receiver shall tolerate.
           If the noise margin falls below this level, the xTU-R shall
           request that the xTU-C increase the xTU-C transmit power.
           If an increase to xTU-C transmit power is not possible, a
           loss-of-margin (LOM) defect occurs, the xTU-R shall fail and
           attempt to reinitialize and the NMS shall be notified.  The
           minimum noise margin ranges from 0 to 310 units of
           0.1 dB (Physical values are 0 to 31 dB).  A value of 0 means
           that there is no minimum."
       REFERENCE    "ITU-T G.997.1, paragraph #7.3.1.3.5"
       DEFVAL       { 0 }
       ::= { zxAnXdsl2SnrMarginConfPrfEntry 6 }
    
    zxAnXdsl2LConfMinSnrmUs  OBJECT-TYPE
       SYNTAX      Unsigned32(0..310)
       UNITS       "0.1 dB"
       MAX-ACCESS  read-create
       STATUS      current
       DESCRIPTION
          "The minimum Noise Margin the xTU-C receiver shall tolerate.
           If the noise margin falls below this level, the xTU-C shall
           request that the xTU-R increase the xTU-R transmit power.
           If an increase of xTU-R transmit power is not possible, a
           loss-of-margin (LOM) defect occurs, the xTU-C shall fail and
           attempt to re-initialize and the NMS shall be notified.  The
           minimum noise margin ranges from 0 to 310 units of
           0.1 dB (Physical values are 0 to 31 dB).  A value of 0 means
           that there is no minimum."
       REFERENCE    "ITU-T G.997.1, paragraph #7.3.1.3.6"
       DEFVAL       { 0 }
       ::= { zxAnXdsl2SnrMarginConfPrfEntry 7 }
    
          
    
     zxAnXdsl2LConfRaUsNrmDs  OBJECT-TYPE
        SYNTAX      Unsigned32(0..310)
        UNITS       "0.1 dB"
        MAX-ACCESS  read-create
        STATUS      current
        DESCRIPTION
           "The Downstream Up-Shift Noise Margin value, to be used when
            zxAnXdsl2LConfRaModeDs is set to dynamicRa.  If the downstream
            noise margin is above this value and stays above it for
            more than the time specified by the zxAnXdsl2LConfRaUsTimeDs,
            the xTU-R shall attempt to increase the downstream net data
            rate.  The Downstream Up-shift Noise Margin ranges from 0 to
            310 units of 0.1 dB (Physical values are 0 to 31 dB)."
        REFERENCE    "ITU-T G.997.1, paragraph #7.3.1.4.3"
        DEFVAL       { 90 }
        ::= { zxAnXdsl2SnrMarginConfPrfEntry 8 }
     
     zxAnXdsl2LConfRaUsNrmUs  OBJECT-TYPE
        SYNTAX      Unsigned32(0..310)
        UNITS       "0.1 dB"
        MAX-ACCESS  read-create
        STATUS      current
        DESCRIPTION
           "The Upstream Up-Shift Noise Margin value, to be used when
            zxAnXdsl2LConfRaModeUs is set to dynamicRa.  If the upstream
            noise margin is above this value and stays above it for more
            than the time specified by the zxAnXdsl2LConfRaUsTimeUs, the
            xTU-C shall attempt to increase the upstream net data rate.
            The Upstream Up-shift Noise Margin ranges from 0 to 310 units
            of 0.1 dB (Physical values are 0 to 31 dB)."
        REFERENCE    "ITU-T G.997.1, paragraph #7.3.1.4.4"
        DEFVAL       { 90 }
        ::= { zxAnXdsl2SnrMarginConfPrfEntry 9 }
        
     
     zxAnXdsl2LConfRaUsTimeDs  OBJECT-TYPE
        SYNTAX      Unsigned32(0..16383)
        UNITS       "seconds"
        MAX-ACCESS  read-create
        STATUS      current
        DESCRIPTION
           "The Downstream Up-Shift Time Interval, to be used when
            zxAnXdsl2LConfRaModeDs is set to dynamicRa.  The interval of
            time that the downstream noise margin should stay above the
            Downstream Up-shift Noise Margin before the xTU-R shall
            attempt to increase the downstream net data rate.  The time
            interval ranges from 0 to 16383 seconds."
        REFERENCE    "ITU-T G.997.1, paragraph #7.3.1.4.5"
        DEFVAL       { 60 }
        ::= { zxAnXdsl2SnrMarginConfPrfEntry 10 }
     
     zxAnXdsl2LConfRaUsTimeUs  OBJECT-TYPE
        SYNTAX      Unsigned32(0..16383)
        UNITS       "seconds"
        MAX-ACCESS  read-create
        STATUS      current
        DESCRIPTION
           "The Upstream Up-Shift Time Interval, to be used when
            zxAnXdsl2LConfRaModeUs is set to dynamicRa.  The interval of
            time the upstream noise margin should stay above the
            Upstream Up-shift Noise Margin before the xTU-C shall
            attempt to increase the upstream net data rate.  The time
            interval ranges from 0 to 16383 seconds."
        REFERENCE    "ITU-T G.997.1, paragraph #7.3.1.4.6"
        DEFVAL       { 60 }
        ::= { zxAnXdsl2SnrMarginConfPrfEntry 11 }
     
     zxAnXdsl2LConfRaDsNrmDs  OBJECT-TYPE
        SYNTAX      Unsigned32(0..310)
        UNITS       "0.1 dB"
        MAX-ACCESS  read-create
        STATUS      current
        DESCRIPTION
           "The Downstream Down-Shift Noise Margin value, to be used
           when
            zxAnXdsl2LConfRaModeDs is set to dynamicRa.  If the downstream
            noise margin is below this value and stays below that for more
            than the time specified by the zxAnXdsl2LConfRaDsTimeDs, the
            xTU-R shall attempt to decrease the downstream net data rate.
            The Downstream Down-shift Noise Margin ranges from 0 to 310
            units of 0.1 dB (Physical values are 0 to 31 dB)."
        REFERENCE    "ITU-T G.997.1, paragraph #7.3.1.4.7"
        DEFVAL       { 30 }
        ::= { zxAnXdsl2SnrMarginConfPrfEntry 12 }
     
     zxAnXdsl2LConfRaDsNrmUs  OBJECT-TYPE
        SYNTAX      Unsigned32(0..310)
        UNITS       "0.1 dB"
        MAX-ACCESS  read-create
        STATUS      current
        DESCRIPTION
           "The Upstream Downshift Noise Margin value, to be used when
            zxAnXdsl2LConfRaModeUs is set to dynamicRa.  If the upstream
            noise margin is below this value and stays below that for more
            than the time specified by the zxAnXdsl2LConfRaDsTimeUs, the
            xTU-C shall attempt to decrease the upstream net data rate.
            The Upstream Down-shift Noise Margin ranges from 0 to 310
            units of 0.1 dB (Physical values are 0 to 31 dB)."
        REFERENCE    "ITU-T G.997.1, paragraph #7.3.1.4.8"
        DEFVAL       { 30 }
        ::= { zxAnXdsl2SnrMarginConfPrfEntry 13 }
     
     zxAnXdsl2LConfRaDsTimeDs  OBJECT-TYPE
        SYNTAX      Unsigned32(0..16383)
        UNITS       "seconds"
        MAX-ACCESS  read-create
        STATUS      current
        DESCRIPTION
           "The Downstream Downshift Time Interval, to be used when
            zxAnXdsl2LConfRaModeDs is set to dynamicRa.  The interval of
            time the downstream noise margin should stay below the
            Downstream Down-shift Noise Margin before the xTU-R shall
            attempt to decrease the downstream net data rate.  The time
            interval ranges from 0 to 16383 seconds."
        REFERENCE    "ITU-T G.997.1, paragraph #7.3.1.4.9"
        DEFVAL       { 60 }
        ::= { zxAnXdsl2SnrMarginConfPrfEntry 14 }
     
     zxAnXdsl2LConfRaDsTimeUs  OBJECT-TYPE
        SYNTAX      Unsigned32(0..16383)
        UNITS       "seconds"
        MAX-ACCESS  read-create
        STATUS      current
        DESCRIPTION
           "The Upstream Down-Shift Time Interval, to be used when
            zxAnXdsl2LConfRaModeUs is set to dynamicRa.  The interval of
            time the upstream noise margin should stay below the Upstream
            Down-shift Noise Margin before the xTU-C shall attempt to
            decrease the upstream net data rate.  The time interval ranges
            from 0 to 16383 seconds."
        REFERENCE    "ITU-T G.997.1, paragraph #7.3.1.4.10"
        DEFVAL       { 60 }
        ::= { zxAnXdsl2SnrMarginConfPrfEntry 15 }

    zxAnXdsl2LConfSnrModeDs  OBJECT-TYPE
        SYNTAX      Xdsl2LineSnrMode
        MAX-ACCESS  read-create
        STATUS      current
        DESCRIPTION
             "This parameter enables/disables the transmitter referred virtual 
             noise in the downstream direction."
        DEFVAL      { virtualNoiseDisabled }
        ::= { zxAnXdsl2SnrMarginConfPrfEntry 16 }


    zxAnXdsl2LConfSnrModeUs  OBJECT-TYPE
        SYNTAX     Xdsl2LineSnrMode
        MAX-ACCESS  read-create
        STATUS      current
        DESCRIPTION
             "This parameter enables/disables the transmitter referred virtual 
             noise in the upstream direction."
        DEFVAL      { virtualNoiseDisabled }
        ::= { zxAnXdsl2SnrMarginConfPrfEntry 17 }                    

   zxAnXdsl2LConfRaModeDs  OBJECT-TYPE
      SYNTAX      Xdsl2RaMode
      MAX-ACCESS  read-create
      STATUS      current
      DESCRIPTION
         "The mode of operation of a rate-adaptive xTU-C in the transmit
          direction.  The parameter can take three values:
             fixed (1),
             raInit (2),
             dynamicRa (3)."
      REFERENCE    "ITU-T G.997.1, paragraph 7.3.1.4.1"
      DEFVAL       { raInit }
      ::= { zxAnXdsl2SnrMarginConfPrfEntry 18  }

   zxAnXdsl2LConfRaModeUs  OBJECT-TYPE
      SYNTAX      Xdsl2RaMode
      MAX-ACCESS  read-create
      STATUS      current
      DESCRIPTION
         "The mode of operation of a rate-adaptive xTU-R in the transmit
          direction.  The parameter can take three values:
             fixed (1),
             raInit (2),
             dynamicRa (3)."
      REFERENCE    "ITU-T G.997.1, paragraph 7.3.1.4.2"
      DEFVAL       { raInit }
      ::= { zxAnXdsl2SnrMarginConfPrfEntry 19  }
           

    zxAnXdsl2SnrMarginConfRowStatus  OBJECT-TYPE
        SYNTAX      RowStatus
        MAX-ACCESS  read-create
        STATUS      current
        DESCRIPTION
           "This object is used to create a new row or to modify or
           delete an existing row in this table.
  
           A profile is activated by setting this object to 'active'.
           When 'active' is set, the system will validate the profile.
           Profile modification is prohibited while this object is set
           to 'active'.  "
        ::= { zxAnXdsl2SnrMarginConfPrfEntry 30 }



-----------------------------------------------------------------------------
-- zxAnXdsl2DelayInpConfPrfTable
------------------------------------------------------------------------------
   zxAnXdsl2DelayInpConfPrfTable  OBJECT-TYPE
        SYNTAX      SEQUENCE  OF  ZxAnXdsl2DelayInpConfPrfEntry
        MAX-ACCESS  not-accessible
        STATUS      current
        DESCRIPTION
            "The Delay-Inp Profile contains the INP and Delay values to be 
            defined for the enabled bearer.
            
            Entries in this table MUST be maintained in a
            persistent manner."
        ::= { zxAnXdsl2LineProfile 16 }


   zxAnXdsl2DelayInpConfPrfEntry  OBJECT-TYPE
        SYNTAX      ZxAnXdsl2DelayInpConfPrfEntry
        MAX-ACCESS  not-accessible
        STATUS      current
        DESCRIPTION
         " A default profile with an index of 'VDEFVAL' will
          always exist and its parameters will be set to vendor-specific
          values, unless otherwise specified in this document"
        INDEX  { zxAnXdsl2DelayInpConfPrfName }
        ::= { zxAnXdsl2DelayInpConfPrfTable 1 }

   ZxAnXdsl2DelayInpConfPrfEntry  ::=
        SEQUENCE {
            zxAnXdsl2DelayInpConfPrfName     DisplayString,
            
            zxAnXdsl2ChConfMaxDelayDs          Unsigned32,
            zxAnXdsl2ChConfMaxDelayUs          Unsigned32,
            zxAnXdsl2ChConfMinProtectDs        Xdsl2SymbolProtection,
            zxAnXdsl2ChConfMinProtectUs        Xdsl2SymbolProtection,          
            zxAnXdsl2ChConfMinProtect8Ds       Xdsl2SymbolProtection8,
            zxAnXdsl2ChConfMinProtect8Us       Xdsl2SymbolProtection8,
            zxAnXdsl2ChConfForceInpDs          TruthValue,
            zxAnXdsl2ChConfForceInpUs          TruthValue,   
            zxAnXdsl2ChConfMaxDelayVar         Unsigned32, 
            zxAnXdsl2ChConfInitPolicy          Xdsl2ChInitPolicy,
            
            zxAnXdsl2DIConfPrfRowStatus  RowStatus
      }


    zxAnXdsl2DelayInpConfPrfName  OBJECT-TYPE
        SYNTAX      DisplayString (SIZE(1..32))
        MAX-ACCESS  not-accessible
        STATUS      current
        DESCRIPTION
            "This object identifies a row in this table."
        ::= { zxAnXdsl2DelayInpConfPrfEntry 1 }
                  
    zxAnXdsl2ChConfMaxDelayDs  OBJECT-TYPE
       SYNTAX      Unsigned32(0..63)
       UNITS       "milliseconds"
       MAX-ACCESS  read-create
       STATUS      current
       DESCRIPTION
          "Maximum Interleave Delay on Downstream direction.  The
          maximum one-way interleaving delay introduced by the PMS-TC on
           Downstream direction.  The xTUs shall choose the S (factor)
           and D (depth) values such that the actual one-way interleaving
           delay (zxAnXdsl2Ch1StatusActDelay) is as close as possible to,
           but less than or equal to zxAnXdsl2Ch1ConfPrfMaxDelayDs.  The
           delay is coded in ms, with the value 0 indicating no delay
           bound is being imposed."
       REFERENCE    "ITU-T G.997.1, paragraph #7.3.2.2"
       ::= { zxAnXdsl2DelayInpConfPrfEntry 2 }
    
    zxAnXdsl2ChConfMaxDelayUs  OBJECT-TYPE
       SYNTAX      Unsigned32(0..63)
       UNITS       "milliseconds"
       MAX-ACCESS  read-create
       STATUS      current
       DESCRIPTION
          "Maximum Interleave Delay on Upstream direction.  The maximum
           one-way interleaving delay introduced by the PMS-TC on
           Upstream direction.  The xTUs shall choose the S (factor) and
           D (depth) values such that the actual one-way interleaving
           delay (zxAnXdsl2Ch1StatusActDelay) is as close as possible to,
           but less than or equal to zxAnXdsl2Ch1ConfPrfMaxDelayUs.  The
           delay is coded in ms, with the value 0 indicating no delay
           bound is being imposed."
       REFERENCE    "ITU-T G.997.1, paragraph #7.3.2.2"
       ::= { zxAnXdsl2DelayInpConfPrfEntry 3 }

    zxAnXdsl2ChConfMinProtectDs  OBJECT-TYPE
       SYNTAX      Xdsl2SymbolProtection
       UNITS       "symbols"
       MAX-ACCESS  read-create
       STATUS      current
       DESCRIPTION
          "Minimum Impulse Noise Protection on Downstream direction.
          The minimum impulse noise protection for the bearer channel,
           expressed in symbols.  The parameter can take the following
           values: noProtection (i.e., INP not required), halfSymbol
           (i.e., INP length is 1/2 symbol) and 1-16 symbols in steps
           of 1 symbol."
       REFERENCE    "ITU-T G.997.1, paragraph #7.3.2.3"
       DEFVAL       { noProtection }
       ::= { zxAnXdsl2DelayInpConfPrfEntry 4 }
    
    zxAnXdsl2ChConfMinProtectUs  OBJECT-TYPE
       SYNTAX      Xdsl2SymbolProtection
       UNITS       "symbols"
       MAX-ACCESS  read-create
       STATUS      current
       DESCRIPTION
          "Minimum Impulse Noise Protection on Upstream direction.  The
           minimum impulse noise protection for the bearer channel,
           expressed in symbols. "
       REFERENCE    "ITU-T G.997.1, paragraph #7.3.2.3"
       DEFVAL       { noProtection }
       ::= { zxAnXdsl2DelayInpConfPrfEntry 5 }
    
       
    zxAnXdsl2ChConfMinProtect8Ds  OBJECT-TYPE
       SYNTAX      Xdsl2SymbolProtection8
       UNITS       "symbols"
       MAX-ACCESS  read-create
       STATUS      current
       DESCRIPTION
          "(INPMIN8ds).
           This parameter specifies the minimum impulse noise protection
           for the bearer channel if it is transported over DMT symbols
           with a subcarrier spacing of 8.625 kHz. The impulse noise
           protection is expressed in DMT symbols with a subcarrier
           spacing of 8.625 kHz and can take any integer value from
           0 to 16, inclusive."
       REFERENCE    "ITU-T G.997.1, paragraph #7.3.2.4"
       DEFVAL       { noProtection }
       ::= { zxAnXdsl2DelayInpConfPrfEntry 6 }
    
    zxAnXdsl2ChConfMinProtect8Us  OBJECT-TYPE
       SYNTAX      Xdsl2SymbolProtection8
       UNITS       "symbols"
       MAX-ACCESS  read-create
       STATUS      current
       DESCRIPTION
          "(INPMIN8us).
           This parameter specifies the minimum impulse noise protection
           for the bearer channel if it is transported over DMT symbols
           with a subcarrier spacing of 8.625 kHz. The impulse noise
           protection is expressed in DMT symbols with a subcarrier
           spacing of 8.625 kHz and can take any integer value from
           0 to 16, inclusive."
       REFERENCE    "ITU-T G.997.1, paragraph #7.3.2.4"
       DEFVAL       { noProtection }
       ::= { zxAnXdsl2DelayInpConfPrfEntry 7 }
   

    zxAnXdsl2ChConfForceInpDs  OBJECT-TYPE
        SYNTAX      TruthValue
        MAX-ACCESS  read-create
        STATUS      current
        DESCRIPTION
            "Enable /disable force to use INP."
        ::= { zxAnXdsl2DelayInpConfPrfEntry 8 }      

    zxAnXdsl2ChConfForceInpUs  OBJECT-TYPE
        SYNTAX      TruthValue
        MAX-ACCESS  read-create
        STATUS      current
        DESCRIPTION
            "Enable /disable force to use INP."
        ::= { zxAnXdsl2DelayInpConfPrfEntry 9 }             
    
    zxAnXdsl2ChConfMaxDelayVar  OBJECT-TYPE
       SYNTAX      Unsigned32(1..255)
       UNITS       "0.1 milliseconds"
       MAX-ACCESS  read-create
       STATUS      current
       DESCRIPTION
          "Maximum delay variation (DVMAX).
           This optional VDSL2 specific parameter specifies the maximum
           value for the delay variation allowed in an OLR procedure.
           It is ranges from 1 to 254 units of 0.1 milliseconds
           (i.e., 0.1 to 25.4 milliseconds) with the special value
           255 which indicates that no delay variation bound is
           imposed."
       REFERENCE    "ITU-T G.997.1 Amendment 1, paragraph #7.3.2.9"
       DEFVAL       { 255 }
       ::= { zxAnXdsl2DelayInpConfPrfEntry 10 }

    zxAnXdsl2ChConfInitPolicy  OBJECT-TYPE
       SYNTAX      Xdsl2ChInitPolicy
       MAX-ACCESS  read-create
       STATUS      current
       DESCRIPTION
          "Channel Initialization Policy Selection (CIPOLICY).
          This optional parameter indicates which policy shall be applied
          to determine the transceiver configuration parameters at
          initialization. The valid values for CIPOLICY are policy0 and
          policy1. Those policies are defined in the respective
          Recommendations."
       REFERENCE    "ITU-T G.997.1 Amendment 1, paragraph #7.3.2.10"
       DEFVAL       { policy0 }
       ::= { zxAnXdsl2DelayInpConfPrfEntry 11 }
      
    zxAnXdsl2DIConfPrfRowStatus  OBJECT-TYPE
        SYNTAX      RowStatus
        MAX-ACCESS  read-create
        STATUS      current
        DESCRIPTION
           "This object is used to create a new row or to modify or
           delete an existing row in this table.
  
           A profile is activated by setting this object to 'active'.
           When 'active' is set, the system will validate the profile.
           Profile modification is prohibited while this object is set
           to 'active'.  "
        ::= { zxAnXdsl2DelayInpConfPrfEntry 80 }
    


------------------------------------------------------------------------------
-- zxAnXdsl2VirtualNoiseConfPrfTable
------------------------------------------------------------------------------
            
   zxAnXdsl2VirtualNoiseConfPrfTable  OBJECT-TYPE
        SYNTAX      SEQUENCE  OF  ZxAnXdsl2VirtualNoiseConfPrfEntry
        MAX-ACCESS  not-accessible
        STATUS      current
        DESCRIPTION
            "The Line Virtual Noise Profile Table."
        ::= { zxAnXdsl2LineProfile 17 }


   zxAnXdsl2VirtualNoiseConfPrfEntry  OBJECT-TYPE
        SYNTAX      ZxAnXdsl2VirtualNoiseConfPrfEntry
        MAX-ACCESS  not-accessible
        STATUS      current
        DESCRIPTION
         " A default profile with an index of 'VDEFVAL' will
          always exist and its parameters will be set to vendor-specific
          values, unless otherwise specified in this document"
        INDEX  { zxAnXdsl2VirtualNoiseConfPrfName }
        ::= { zxAnXdsl2VirtualNoiseConfPrfTable 1 }

   ZxAnXdsl2VirtualNoiseConfPrfEntry  ::=
        SEQUENCE {
            zxAnXdsl2VirtualNoiseConfPrfName            DisplayString,        
            zxAnXdsl2LConfTxRefVnDs                     OCTET STRING,
            zxAnXdsl2LConfTxRefVnUs                     OCTET STRING,
            
            zxAnXdsl2VNConfPrfRowStatus       RowStatus
        }
         
    zxAnXdsl2VirtualNoiseConfPrfName  OBJECT-TYPE
        SYNTAX      DisplayString (SIZE(1..32))
        MAX-ACCESS  not-accessible
        STATUS      current
        DESCRIPTION
            "This object identifies a row in this table."
        ::= { zxAnXdsl2VirtualNoiseConfPrfEntry 1 }


    zxAnXdsl2LConfTxRefVnDs  OBJECT-TYPE
        SYNTAX      OCTET STRING (SIZE(0..96)) 
        MAX-ACCESS  read-create
        STATUS      current
        DESCRIPTION
             "This configuration parameter defines the downstream transmitter 
        referred virtual noise (TXREFVNds). 
        The TXREFVNds shall be specified through a set of breakpoints. 
        Each breakpoint shall consist of a subcarrier index t, with a 
        sub-carrier spacing of 4.3125 kHz, and a noise PSD level (expressed 
        in dBm/Hz) at that subcarrier. The set of breakpoints can then be 
        represented as [(t1, PSD1), (t2, PSD2), ..., (tN, PSDN)]. 
        The subcarrier index shall be coded as an unsigned integer. 
        The noise level shall be coded as an 8-bit unsigned integer representing
        the noise level -40 dBm/Hz (coded as 0) to -140 dBm/Hz (coded as 200), 
        in steps of 0.5 dBm/Hz. Values from 201 to 255 are special values 
        indicating a noise level of 0 W/Hz. The maximum number of breakpoints 
        is 32."
        ::= { zxAnXdsl2VirtualNoiseConfPrfEntry 2 }


    zxAnXdsl2LConfTxRefVnUs  OBJECT-TYPE
        SYNTAX      OCTET STRING (SIZE(0..48)) 
        MAX-ACCESS  read-create
        STATUS      current
        DESCRIPTION
             "This configuration parameter defines the upstream transmitter 
             referred virtual noise (TXREFVNus). The TXREFVNus shall be 
             specified through a set of breakpoints. Each breakpoint shall 
             consist of a subcarrier index t, with a sub-carrier spacing of 
             4.3125 kHz, and a noise PSD level (expressed in dBm/Hz) at that 
             subcarrier. The set of breakpoints can then be represented as 
             [(t1, PSD1), (t2, PSD2), ..., (tN, PSDN)]. The subcarrier index 
             shall be coded as an unsigned integer. The noise level shall be 
             coded as an 8-bit unsigned integer representing the noise 
             level -40 dBm/Hz (coded as 0) to -140 dBm/Hz (coded as 200), 
             in steps of 0.5 dBm/Hz. Values from 201 to 255 are special values 
             indicating a noise level of 0 W/Hz. The maximum number of 
             breakpoints is 16."
        ::= { zxAnXdsl2VirtualNoiseConfPrfEntry 3 }
      

    zxAnXdsl2VNConfPrfRowStatus  OBJECT-TYPE
       SYNTAX      RowStatus
       MAX-ACCESS  read-create
       STATUS      current
       DESCRIPTION
           "This object is used to create a new row or to modify or
           delete an existing row in this table.
  
           A profile is activated by setting this object to 'active'.
           When 'active' is set, the system will validate the profile.
           Profile modification is prohibited while this object is set
           to 'active'.
           "    
       ::= { zxAnXdsl2VirtualNoiseConfPrfEntry 30 }
       
       
       
------------------------------------------------------------------------------
-- zxAnXdsl2RfiConfPrfTable
------------------------------------------------------------------------------
            
   zxAnXdsl2RfiConfPrfTable  OBJECT-TYPE
        SYNTAX      SEQUENCE  OF  ZxAnXdsl2RfiConfPrfEntry
        MAX-ACCESS  not-accessible
        STATUS      current
        DESCRIPTION
            "The Line RFI Profile Table."
        ::= { zxAnXdsl2LineProfile 18 }


   zxAnXdsl2RfiConfPrfEntry  OBJECT-TYPE
        SYNTAX      ZxAnXdsl2RfiConfPrfEntry
        MAX-ACCESS  not-accessible
        STATUS      current
        DESCRIPTION
         " A default profile with an index of 'VDEFVAL' will
          always exist and its parameters will be set to vendor-specific
          values, unless otherwise specified in this document"
        INDEX  { zxAnXdsl2LConfRfiPrfName }
        ::= { zxAnXdsl2RfiConfPrfTable 1 }

   ZxAnXdsl2RfiConfPrfEntry  ::=
        SEQUENCE {
            zxAnXdsl2LConfRfiPrfName            DisplayString,
            zxAnXdsl2LConfRfiBandsDs            Xdsl2RfiBands,
            
            zxAnXdsl2RfiConfPrfRowStatus        RowStatus         
        }
         
    zxAnXdsl2LConfRfiPrfName  OBJECT-TYPE
        SYNTAX      DisplayString (SIZE(1..32))
        MAX-ACCESS  not-accessible
        STATUS      current
        DESCRIPTION
            "This object identifies a row in this table."
        ::= { zxAnXdsl2RfiConfPrfEntry 1 }


    zxAnXdsl2LConfRfiBandsDs  OBJECT-TYPE
        SYNTAX      Xdsl2RfiBands
        MAX-ACCESS  read-create
        STATUS      current
        DESCRIPTION
            "RfiBands configured in the downstream."
        ::= { zxAnXdsl2RfiConfPrfEntry 2 }


    zxAnXdsl2RfiConfPrfRowStatus  OBJECT-TYPE
       SYNTAX      RowStatus
       MAX-ACCESS  read-create
       STATUS      current
       DESCRIPTION
           "This object is used to create a new row or to modify or
           delete an existing row in this table.
  
           A profile is activated by setting this object to 'active'.
           When 'active' is set, the system will validate the profile.
           Profile modification is prohibited while this object is set
           to 'active'.
           "    
       ::= { zxAnXdsl2RfiConfPrfEntry 30 }
       
       
-----------------------------------------------------------------------------
-- zxAnXdsl2ProfModeSpecTable 
-----------------------------------------------------------------------------

    zxAnXdsl2ProfModeSpecTable  OBJECT-TYPE
       SYNTAX      SEQUENCE  OF  ZxAnXdsl2ProfModeSpecEntry
       MAX-ACCESS  not-accessible
       STATUS      current
       DESCRIPTION
          "The table zxAnXdsl2ProfModeSpecTable extends the
          DSL line configuration profile by xDSL Mode Specific
          parameters.
          A row in this table that has an index of
          zxAnXdsl2LConfXdslMode == defMode(1), is called a
          'mandatory' row.
          A row in this table that has an index such that
          xdsl2LConfProfXdslMode is not equal to defMode(1),
          is called an 'optional' row.
          When a row in the zxAnXdsl2SpectrumConfPrfTable table
          (the parent row) is created, the SNMP agent will
          automatically create a 'mandatory' row in this table.
          When the parent row is deleted, the SNMP agent will
          automatically delete all associated rows in this table.
          Any attempt to delete the 'mandatory' row using the
          zxAnXdsl2ProfModeSpecRowStatus attribute will be
          rejected by the SNMP agent.
          The manager MAY create an 'optional' row in this table
          using the zxAnXdsl2ProfModeSpecRowStatus attribute if
          the parent row exists.
          The manager MAY delete an 'optional' row in this table
          using the zxAnXdsl2ProfModeSpecRowStatus attribute at
          any time.
          If the actual transmission mode of a DSL line does not
          match one of the 'optional' rows in this table, then
          the line will use the PSD configuration from the
          'mandatory' row.

          Entries in this table MUST be maintained in a
          persistent manner."
       ::= { zxAnXdsl2LineProfile 19 }

    zxAnXdsl2ProfModeSpecEntry  OBJECT-TYPE
       SYNTAX      ZxAnXdsl2ProfModeSpecEntry
       MAX-ACCESS  not-accessible
       STATUS      current
       DESCRIPTION
          "The table zxAnXdsl2ProfModeSpecTable extends the
          DSL line configuration profile by DSL Mode Specific
          parameters."
       INDEX  { zxAnXdsl2SpectrumConfPrfName, zxAnXdsl2LConfXdslMode }
       ::= { zxAnXdsl2ProfModeSpecTable 1 }

    ZxAnXdsl2ProfModeSpecEntry  ::=
       SEQUENCE {
            zxAnXdsl2LConfXdslMode              ZxAnXdsl2OperationModes,
            zxAnXdsl2LConfMaxNomPsdDs           Integer32,
            zxAnXdsl2LConfMaxNomPsdUs           Integer32,
            zxAnXdsl2LConfMaxNomAtpDs           Unsigned32,
            zxAnXdsl2LConfMaxNomAtpUs           Unsigned32,
            zxAnXdsl2LConfMaxAggRxPwrUs         Integer32,
            zxAnXdsl2LConfPsdMaskDs             Xdsl2PsdMaskDs,
            zxAnXdsl2LConfPsdMaskUs             Xdsl2PsdMaskUs,
            zxAnXdsl2LConfPsdMaskSelectUs       Xdsl2LinePsdMaskSelectUs,
            zxAnXdsl2LConfClassMask             Xdsl2LineClassMask,
            zxAnXdsl2LConfLimitMask             Xdsl2LineLimitMask,
            zxAnXdsl2LConfUs0Disable            Xdsl2LineUs0Disable,
            zxAnXdsl2ProfModeSpecRowStatus      RowStatus
            }

    zxAnXdsl2LConfXdslMode    OBJECT-TYPE
       SYNTAX      ZxAnXdsl2OperationModes
       MAX-ACCESS  not-accessible
       STATUS      current
       DESCRIPTION
          "The DSL Mode is a way of categorizing the various xDSL
           transmission modes into groups, each group (xDSL Mode) shares
           the same PSD configuration.
           There should be multiple entries in this table for a given
           line profile in case multiple bits are set in
           xdsl2LConfPrfXtuTransSysEna for that profile. "
       REFERENCE    "DSL Forum TR-129, paragraph #5.5"
       ::= { zxAnXdsl2ProfModeSpecEntry 1 }
   
     zxAnXdsl2LConfMaxNomPsdDs  OBJECT-TYPE
        SYNTAX      Integer32(-600..-300)
        UNITS       "0.1 dBm/Hz"
        MAX-ACCESS  read-create
        STATUS      current
        DESCRIPTION
           "(MAXNOMPSDds).
            The maximum nominal transmit PSD in the downstream
            direction during initialization and Showtime.  It ranges from
            -600 to -300 units of 0.1 dBm/Hz.  (physical values are -60 to
            -30 dBm/Hz).  "
        REFERENCE    "ITU-T G.997.1, paragraph #7.3.1.2.1"
        DEFVAL       { -300 }
       ::= { zxAnXdsl2ProfModeSpecEntry 2 }
     
     zxAnXdsl2LConfMaxNomPsdUs  OBJECT-TYPE
        SYNTAX      Integer32(-600..-300)
        UNITS       "0.1 dBm/Hz"
        MAX-ACCESS  read-create
        STATUS      current
        DESCRIPTION
           "(MAXNOMPSDus).
            The maximum nominal transmit PSD in the upstream direction
            during initialization and Showtime.  It ranges from -600 to
            -300 units of 0.1 dBm/Hz.  (physical values are -60 to
            -30 dBm/Hz).  "
        REFERENCE    "ITU-T G.997.1, paragraph #7.3.1.2.2"
        DEFVAL       { -300 }
        ::= { zxAnXdsl2ProfModeSpecEntry 3 }

        
     zxAnXdsl2LConfMaxNomAtpDs  OBJECT-TYPE
        SYNTAX      Unsigned32 (0..255)
        UNITS       "0.1 dBm"
        MAX-ACCESS  read-create
        STATUS      current
        DESCRIPTION
           "(MAXNOMATPds).
            The maximum nominal aggregate transmit power in the
            downstream direction during initialization and Showtime.  It
            ranges from 0 to 255 units of 0.1 dBm (physical values are 0
            to 25.5 dBm)."
        REFERENCE    "ITU-T G.997.1, paragraph #7.3.1.2.3"
        DEFVAL       { 255 }
        ::= { zxAnXdsl2ProfModeSpecEntry 4 }
     
     
     zxAnXdsl2LConfMaxNomAtpUs  OBJECT-TYPE
        SYNTAX      Unsigned32 (0..255)
        UNITS       "0.1 dBm"
        MAX-ACCESS  read-create
        STATUS      current
        DESCRIPTION
           "(MAXNOMATPus).
            The maximum nominal aggregate transmit power in the upstream
            direction during initialization and Showtime.  It ranges from
            0 to 255 units of 0.1 dBm (physical values are 0 to 25.5
            dBm)."
        REFERENCE    "ITU-T G.997.1, paragraph #7.3.1.2.4"
        DEFVAL       { 255 }
        ::= { zxAnXdsl2ProfModeSpecEntry 5 }
     
     
     zxAnXdsl2LConfMaxAggRxPwrUs  OBJECT-TYPE
        SYNTAX      Integer32(-255..255 | 2147483647)
        UNITS       "0.1 dBm"
        MAX-ACCESS  read-create
        STATUS      current
        DESCRIPTION
           "(MAXRXPWRus).
            The maximum upstream aggregate receive power over the relevant
            set of sub-carriers.  The xTU-C should verify that the
            upstream power cutback is such that this maximum aggregate
            receive power value is honored.  It ranges from -255 to 255
            units of 0.1 dBm (physical values are -25.5 to 25.5 dBm).
            A value of 0x7FFFFFFF (2147483647) means that there is no
            limit."
        REFERENCE    "ITU-T G.997.1, paragraph #7.3.1.2.5"
        DEFVAL       { 255 }
        ::= { zxAnXdsl2ProfModeSpecEntry 6 }

     zxAnXdsl2LConfPsdMaskDs   OBJECT-TYPE
        SYNTAX      Xdsl2PsdMaskDs
        MAX-ACCESS  read-create
        STATUS      current
        DESCRIPTION
          "(PSDMASKds).
           The downstream PSD mask applicable at the U-C2 reference
           point.
          This parameter is used only for G.992.5 and it may impose PSD
          restrictions (breakpoints) in addition to the Limit PSD mask
          defined in G.992.5.
          This is a string of 32 pairs of values in the following
          structure:
          Octets 0+1 - Index of 1st sub-carrier used in the context
                       of a first breakpoint.
     
          Octet 2    - The PSD reduction for the sub-carrier indicated in
                       octets 0 and 1.
          Octets 3-5 - Same, for a 2nd breakpoint.
          Octets 6-8 - Same, for a 3rd breakpoint.
          This architecture continues until octets 94-95, which are
          associated with a 32nd breakpoint.
          Each subcarrier index is an unsigned number in the range 1 and
          NSCds.  Each PSD reduction value is in the range 0 (0dBm/Hz) to
          255 (-127.5dBm/Hz) with steps of 0.5dBm/Hz.  Valid values are
          in the range 0 to 190 (0 to -95dBm/Hz).
          When the number of breakpoints is less than 32, all remaining
          octets are set to the value 0.  Note that the content of this
          object should be correlated with the sub-carriers mask and with
          the RFI setup. "
        REFERENCE    "ITU-T G.997.1, paragraph #7.3.1.2.9"
          ::= { zxAnXdsl2ProfModeSpecEntry 7 }
     
     zxAnXdsl2LConfPsdMaskUs   OBJECT-TYPE
        SYNTAX      Xdsl2PsdMaskUs
        MAX-ACCESS  read-create
        STATUS      current
        DESCRIPTION
          "(PSDMASKus).
           The upstream PSD mask applicable at the U-R2 reference
           point.
          This parameter is used only for G.992.5 and it may impose PSD
          restrictions (breakpoints) in addition to the Limit PSD mask
          defined in G.992.5.
          This is a string of 16 pairs of values in the following
          structure:
          Octets 0+1 - Index of 1st sub-carrier used in the context
                       of a first breakpoint.
          Octet 2    - The PSD reduction for the sub-carrier indicated in
                       octets 0 and 1.
          Octets 3-5 - Same, for a 2nd breakpoint.
          Octets 6-8 - Same, for a 3rd breakpoint.
          This architecture continues until octets 9-47, which are
          associated with a 16th breakpoint.
          Each subcarrier index is an unsigned number in the range 1 and
          NSCus.  Each PSD reduction value is in the range 0 (0dBm/Hz) to
          255 (-127.5dBm/Hz) with steps of 0.5dBm/Hz.  Valid values are
          in the range 0 to 190 (0 to -95dBm/Hz).
          When the number of breakpoints is less than 16, all remaining
          octets are set to the value 0.  Note that the content of this
          object should be correlated with the sub-carriers mask and with
          the RFI setup. "
        REFERENCE    "ITU-T G.997.1, paragraph #7.3.1.2.12"
          ::= { zxAnXdsl2ProfModeSpecEntry 8 }


     zxAnXdsl2LConfPsdMaskSelectUs  OBJECT-TYPE
        SYNTAX      Xdsl2LinePsdMaskSelectUs
        MAX-ACCESS  read-create
        STATUS      current
        DESCRIPTION
          "The selected upstream PSD mask.  This parameter is used only
           for annexes J and M of G.992.3 and G.992.5, and the same
           selection is used for all relevant enabled bits in
           zxAnXdsl2LConfXtuTransSysEna. "
        REFERENCE    "ITU-T G.997.1, paragraph #7.3.1.2.11"
        DEFVAL       { adlu56Eu56 }
         ::= { zxAnXdsl2ProfModeSpecEntry 9 }
         
         
    zxAnXdsl2LConfClassMask  OBJECT-TYPE
       SYNTAX      Xdsl2LineClassMask
       MAX-ACCESS  read-create
       STATUS      current
       DESCRIPTION
          "(CLASSMASK).
          In order to reduce the number of configuration
          possibilities, the limit Power Spectral Density masks
          (see LIMITMASK) are grouped in PSD mask classes.
          Each class is designed such that the PSD levels of each
          limit PSD mask of a specific class are equal in their
          respective passband above 276 kHz.
          This parameter is defined per VDSL2 Annex enabled in the
          xdsl2LConfPrfXtuTransSysEna object. It selects a single
          PSD mask class per Annex that is activated at the
          VTU-O."
       REFERENCE    "ITU-T G.997.1, paragraph #7.3.1.2.15"
       DEFVAL       { b998AdeM2x }
       ::= { zxAnXdsl2ProfModeSpecEntry 10 }
                      

    zxAnXdsl2LConfLimitMask  OBJECT-TYPE
       SYNTAX      Xdsl2LineLimitMask
       MAX-ACCESS  read-create
       STATUS      current
       DESCRIPTION
          "(LIMITMASK).
          This configuration parameter contains the G.993.2 limit
          PSD masks of the selected PSD mask class, enabled by the
          near-end xTU on this line for each class of profiles.
    
          This parameter is defined per VDSL2 Annex enabled in the
          xdsl2LConfProfXtuTransSysEna object.
          Through this parameter several limit PSD masks of the
          selected PSD mask class (xdsl2LConfProfClassMask) may be
          enabled. The enabling parameter is coded in a bitmap
          representation (0 if the associated mask is not allowed,
          1 if it is allowed)."
       REFERENCE    "ITU-T G.997.1 Amendment 1, paragraph #7.3.1.2.16"
        ::= { zxAnXdsl2ProfModeSpecEntry 11 }



    zxAnXdsl2LConfUs0Disable  OBJECT-TYPE
        SYNTAX      Xdsl2LineUs0Disable
        MAX-ACCESS  read-create
        STATUS      current
        DESCRIPTION
            " Enable or disable the use of US0."
        ::= { zxAnXdsl2ProfModeSpecEntry 12 }   
            
 
    zxAnXdsl2ProfModeSpecRowStatus  OBJECT-TYPE
       SYNTAX      RowStatus
       MAX-ACCESS  read-create
       STATUS      current
       DESCRIPTION
          "This object is used to create a new row or to modify or
          delete an existing row in this table.
    
          A profile is activated by setting this object to 'active'.
          When 'active' is set, the system will validate the profile.
    
          Before a profile can be deleted or taken out of service
          (by setting this object to 'destroy' or 'notInService'),
          it must be first unreferenced from all associated
          templates."
    
       ::= { zxAnXdsl2ProfModeSpecEntry 30 }


------------------------------------------------------------------------------
-- zxAnXdsl2ExtConfPrfTable
------------------------------------------------------------------------------
            
   zxAnXdsl2ExtConfPrfTable  OBJECT-TYPE
        SYNTAX      SEQUENCE  OF  ZxAnXdsl2ExtConfPrfEntry
        MAX-ACCESS  not-accessible
        STATUS      current
        DESCRIPTION
            "The Line Ext Profile Table."
        ::= { zxAnXdsl2LineProfile 20 }


   zxAnXdsl2ExtConfPrfEntry  OBJECT-TYPE
        SYNTAX      ZxAnXdsl2ExtConfPrfEntry
        MAX-ACCESS  not-accessible
        STATUS      current
        DESCRIPTION
         "The extend profile, a default profile with an index of 'VDEFVAL' will
          always exist and its parameters will be set to vendor-specific
          values, unless otherwise specified in this document"
        INDEX  { zxAnXdsl2LConfExtPrfName }
        ::= { zxAnXdsl2ExtConfPrfTable 1 }

   ZxAnXdsl2ExtConfPrfEntry  ::=
        SEQUENCE {
            zxAnXdsl2LConfExtPrfName            DisplayString,
            zxAnXdsl2LConfInpMinEtrUs           Unsigned32, 
            zxAnXdsl2LConfInpMinEtrDs           Unsigned32,    
            zxAnXdsl2LConfInpMaxEtrUs           Unsigned32, 
            zxAnXdsl2LConfInpMaxEtrDs           Unsigned32,                        
            zxAnXdsl2LConfInpMaxNetUs           Unsigned32, 
            zxAnXdsl2LConfInpMaxNetDs           Unsigned32, 
            zxAnXdsl2LConfInpShineRatioUs       INTEGER,
            zxAnXdsl2LConfInpShineRatioDs       INTEGER,                    
            zxAnXdsl2LConfInpMinReinUs          INTEGER,
            zxAnXdsl2LConfInpMinReinDs          INTEGER,
            zxAnXdsl2LConfInpIaReinFlagUs       INTEGER,     
            zxAnXdsl2LConfInpIaReinFlagDs       INTEGER,     
            zxAnXdsl2LConfInpMinDelayUs         INTEGER,
            zxAnXdsl2LConfInpMinDelayDs         INTEGER,           
            zxAnXdsl2LConfInpRetxModeUs         INTEGER,
            zxAnXdsl2LConfInpRetxModeDs         INTEGER,
            zxAnXdsl2LConfInpMaxDelayUs         Integer32,
            zxAnXdsl2LConfInpMaxDelayDs         Integer32,
            zxAnXdsl2LConfChanInitPolicyUs      Integer32,
            zxAnXdsl2LConfChanInitPolicyDs      Integer32,
            zxAnXdsl2LFextCancelNotReqBandDs    OCTET STRING,
            zxAnXdsl2LFextCancelNotReqBandUs    OCTET STRING,
            
            zxAnXdsl2LConfInpMinShineUs         Integer32,
            zxAnXdsl2LConfInpMinShineDs         Integer32,
            zxAnXdsl2LConfInpMin8ShineUs        Integer32,
            zxAnXdsl2LConfInpMin8ShineDs        Integer32,
            zxAnXdsl2LConfInpMin8ReinUs         Integer32,
            zxAnXdsl2LConfInpMin8ReinDs         Integer32,
            
            zxAnXdsl2ExtConfPrfRowStatus        RowStatus
        }
         
    zxAnXdsl2LConfExtPrfName  OBJECT-TYPE
        SYNTAX      DisplayString (SIZE(1..32))
        MAX-ACCESS  not-accessible
        STATUS      current
        DESCRIPTION
            "This object identifies a row in this table."
        ::= { zxAnXdsl2ExtConfPrfEntry 1 }
             
    zxAnXdsl2LConfInpMinEtrUs OBJECT-TYPE
      SYNTAX      Unsigned32(0..200000)
      UNITS       "kbps"
      MAX-ACCESS  read-create
      STATUS      current
      DESCRIPTION
         "GINP configuration parameters of upstream.
          Minimum allowed value for Expected throughput(ETR).
          to VDSL:range is 0-200000.
          to ADSL:range is 0-10240."
      ::= { zxAnXdsl2ExtConfPrfEntry 10 }      
      
    zxAnXdsl2LConfInpMinEtrDs OBJECT-TYPE
      SYNTAX      Unsigned32(0..200000)
      UNITS       "kbps"
      MAX-ACCESS  read-create
      STATUS      current
      DESCRIPTION
         "GINP configuration parameters of downstream.
          Minimum allowed value for Expected throughput(ETR).
          to VDSL:range is 0-200000.
          to ADSL:range is 0-131040."          
      ::= { zxAnXdsl2ExtConfPrfEntry 11 }  
      
    zxAnXdsl2LConfInpMaxEtrUs OBJECT-TYPE
      SYNTAX      Unsigned32(0..200000)
      UNITS       "kbps"
      MAX-ACCESS  read-create
      STATUS      current
      DESCRIPTION
         "GINP configuration parameters of upstream.
          Maximum allowed value for Expected throughput(ETR).
          to VDSL:range is 0-200000.
          to ADSL:range is 0-10240."           
      ::= { zxAnXdsl2ExtConfPrfEntry 12 } 
      
    zxAnXdsl2LConfInpMaxEtrDs OBJECT-TYPE
      SYNTAX      Unsigned32(0..200000)
      UNITS       "kbps"
      MAX-ACCESS  read-create
      STATUS      current
      DESCRIPTION
         "GINP configuration parameters of downstream.
          Maximum allowed value for Expected throughput(ETR).
          to VDSL:range is 0-200000.
          to ADSL:range is 0-131040."                 
      ::= { zxAnXdsl2ExtConfPrfEntry 13 } 
      
    zxAnXdsl2LConfInpMaxNetUs OBJECT-TYPE
      SYNTAX      Unsigned32(0..200000)
      UNITS       "kbps"
      MAX-ACCESS  read-create
      STATUS      current
      DESCRIPTION
         "GINP configuration parameters of upstream.
          Maximum net data rate over alpha1/beta1 interface .
          to VDSL:range is 0-200000.
          to ADSL:range is 0-10240."                 
      ::= { zxAnXdsl2ExtConfPrfEntry 14 } 
      
    zxAnXdsl2LConfInpMaxNetDs OBJECT-TYPE
      SYNTAX      Unsigned32(0..200000)
      UNITS       "bps"
      MAX-ACCESS  read-create
      STATUS      current
      DESCRIPTION
         "GINP configuration parameters of downstream.
          Maximum net data rate over alpha1/beta1 interface.
          to VDSL:range is 0-200000.
          to ADSL:range is 0-131040."                 
      ::= { zxAnXdsl2ExtConfPrfEntry 15 } 
    
    zxAnXdsl2LConfInpShineRatioUs OBJECT-TYPE
      SYNTAX      INTEGER(0..100)
      MAX-ACCESS  read-create
      STATUS      current
      DESCRIPTION      
         "GINP configuration parameters of upstream.
          The loss of rate in a 1 second interval expressed as a fraction of 
          NDR(Net data rate) due to a SHINE impulse noise environment expected
          by the operator to occur at a probability acceptable for the 
          services.
          It shall be represented as a 8-bit unsigned integer SHINEratio, with
          the value of SHINEratio defined as SHINEratio = (0.001* SHINEratio). 
          This data format supports a range from 0 to 0.1 with granularity of 
          0.001."
      DEFVAL       { 0 }
      ::= { zxAnXdsl2ExtConfPrfEntry 16 } 
       
    zxAnXdsl2LConfInpShineRatioDs OBJECT-TYPE
      SYNTAX      INTEGER(0..100)
      MAX-ACCESS  read-create
      STATUS      current
      DESCRIPTION
         "GINP configuration parameters of downstream.
          The loss of rate in a 1 second interval expressed as a fraction of 
          NDR(Net data rate) due to a SHINE impulse noise environment expected
          by the operator to occur at a probability acceptable for the 
          services.
          It shall be represented as a 8-bit unsigned integer SHINEratio, with
          the value of SHINEratio defined as SHINEratio = (0.001* SHINEratio). 
          This data format supports a range from 0 to 0.1 with granularity of 
          0.001."
      DEFVAL       { 0 }
      ::= { zxAnXdsl2ExtConfPrfEntry 17 }
    
    zxAnXdsl2LConfInpMinReinUs OBJECT-TYPE     
      SYNTAX      INTEGER(0..7)
      MAX-ACCESS  read-create
      STATUS      current
      DESCRIPTION
         "GINP configuration parameters of upstream.
          Minimum impulse protection against electrical repetitive impulse
          noise in DMT symbols.
          "
      DEFVAL       { 0 }
      ::= { zxAnXdsl2ExtConfPrfEntry 18 }
      
    zxAnXdsl2LConfInpMinReinDs OBJECT-TYPE     
      SYNTAX      INTEGER(0..7)
      MAX-ACCESS  read-create
      STATUS      current
      DESCRIPTION
         "GINP configuration parameters of downstream.
          Minimum impulse protection against electrical repetitive impulse
          noise in DMT symbols.
          "
      DEFVAL       { 0 }
      ::= { zxAnXdsl2ExtConfPrfEntry 19 }     
      
    zxAnXdsl2LConfInpIaReinFlagUs OBJECT-TYPE     
      SYNTAX      INTEGER {
          hz100(1),
          hz120(2)
      }
      MAX-ACCESS  read-create
      STATUS      current
      DESCRIPTION
         "GINP configuration parameters of upstream.
          Configuration flag indicating the inter-arrival of REIN. 
          "
      DEFVAL { hz100 }    
      ::= { zxAnXdsl2ExtConfPrfEntry 20 }    
      
    zxAnXdsl2LConfInpIaReinFlagDs OBJECT-TYPE     
      SYNTAX      INTEGER{
          hz100(1),
          hz120(2)
      }
      MAX-ACCESS  read-create
      STATUS      current
      DESCRIPTION
         "GINP configuration parameters of downstream.
          Configuration flag indicating the inter-arrival of REIN. 
          "
      DEFVAL { hz100 }    
      ::= { zxAnXdsl2ExtConfPrfEntry 21 }                

    zxAnXdsl2LConfInpMinDelayUs OBJECT-TYPE     
      SYNTAX      INTEGER(0..63)   
      UNITS       "ms"         
      MAX-ACCESS  read-create
      STATUS      current
      DESCRIPTION
         "GINP configuration parameters of upstream.
          Minimum delay in ms. 
          "
      DEFVAL       { 0 }
      ::= { zxAnXdsl2ExtConfPrfEntry 22 }     
      
    zxAnXdsl2LConfInpMinDelayDs OBJECT-TYPE     
      SYNTAX      INTEGER(0..63) 
      UNITS       "ms"                
      MAX-ACCESS  read-create
      STATUS      current
      DESCRIPTION
         "GINP configuration parameters of downstream.
          Minimum delay in ms. 
          "
      DEFVAL       { 0 }
      ::= { zxAnXdsl2ExtConfPrfEntry 23 }                                    
      
    zxAnXdsl2LConfInpRetxModeUs OBJECT-TYPE     
        SYNTAX      INTEGER{
            forbidden(1),
            preferred(2),
            forced(3),
            testMode(4)
        }              
        MAX-ACCESS  read-create
        STATUS      current
        DESCRIPTION
            "GINP configuration parameters of upstream used to control
             activation of retransmission during initialization.
             
             forbidden(1) - G.998.4 retransmission not allowed;
             preferred(2) - G.998.4 retransmission is preferred by the operator;
             forced(3)    - Force the use of the G.998.4 retransmission;
             testMode(4)  - Force the use of the G.998.4 retransmission in the 
                            test mode;
             "
        DEFVAL       { forbidden }
        REFERENCE    "ITU-T G.998.4, paragraph #11.1.13"
        ::= { zxAnXdsl2ExtConfPrfEntry 24 } 
      
    zxAnXdsl2LConfInpRetxModeDs OBJECT-TYPE     
        SYNTAX      INTEGER{
            forbidden(1),
            preferred(2),
            forced(3),
            testMode(4)
        }               
        MAX-ACCESS  read-create
        STATUS      current
        DESCRIPTION
            "GINP configuration parameters of upstream used to control
             activation of retransmission during initialization.
             
             forbidden(1) - G.998.4 retransmission not allowed;
             preferred(2) - G.998.4 retransmission is preferred by the operator;
             forced(3)    - Force the use of the G.998.4 retransmission;
             testMode(4)  - Force the use of the G.998.4 retransmission in the 
                            test mode;
             "
        DEFVAL       { forbidden }
        REFERENCE    "ITU-T G.998.4, paragraph #11.1.13"
        ::= { zxAnXdsl2ExtConfPrfEntry 25 }
      
    zxAnXdsl2LConfInpMaxDelayUs OBJECT-TYPE     
        SYNTAX      Integer32(0..63)   
        UNITS       "ms"         
        MAX-ACCESS  read-create
        STATUS      current
        DESCRIPTION
            "GINP configuration parameters of upstream.
             Maximum delay in milliseconds. 
             "
        DEFVAL      { 0 }
        REFERENCE    "ITU-T G.998.4, paragraph #8.1.6"
        ::= { zxAnXdsl2ExtConfPrfEntry 26 }     
      
    zxAnXdsl2LConfInpMaxDelayDs OBJECT-TYPE     
        SYNTAX      Integer32(0..63) 
        UNITS       "ms"                
        MAX-ACCESS  read-create
        STATUS      current
        DESCRIPTION
           "GINP configuration parameters of downstream.
            Maximum delay in milliseconds. 
            "
        DEFVAL       { 0 }
        REFERENCE    "ITU-T G.998.4, paragraph #8.1.6"
        ::= { zxAnXdsl2ExtConfPrfEntry 27 }
        
    zxAnXdsl2LConfChanInitPolicyUs OBJECT-TYPE     
        SYNTAX      Integer32(0..255)
        MAX-ACCESS  read-create
        STATUS      current
        DESCRIPTION
            "The channel initialisation policy of upstream used by the receiver
             to select the values of transceiver parameters.
             Support of Channel Initialization Policy 0 is mandatory. 
             The CIpolicyn parameter values other than 0 are reserved for use 
             by the ITU-T.
             "
        DEFVAL      { 0 }
        REFERENCE    "ITU-T G.998.4, paragraph #11.5"
        ::= { zxAnXdsl2ExtConfPrfEntry 28 }     
      
    zxAnXdsl2LConfChanInitPolicyDs OBJECT-TYPE     
        SYNTAX      Integer32(0..255)
        MAX-ACCESS  read-create
        STATUS      current
        DESCRIPTION
            "The channel initialisation policy of downstream used by the 
             receiver to select the values of transceiver parameters.
             Support of Channel Initialization Policy 0 is mandatory. 
             The CIpolicyn parameter values other than 0 are reserved for use 
             by the ITU-T.
             "
        DEFVAL      { 0 }
        REFERENCE    "ITU-T G.998.4, paragraph #11.5"
        ::= { zxAnXdsl2ExtConfPrfEntry 29 }
        
    zxAnXdsl2LFextCancelNotReqBandDs OBJECT-TYPE     
        SYNTAX      OCTET STRING(SIZE(0..32))
        MAX-ACCESS  read-create
        STATUS      current
        DESCRIPTION
            "This configuration parameter shall be an array of pairs of
             downstream sub-carrier indices. Each pair represents the start and 
             stop sub-carrier index of a frequency band in which FEXT 
             cancellation is not required. Up to 8 frequency bands may be 
             configured.
             The same configuration shall be applied for all lines in the 
             vectored group."
        REFERENCE    "ITU-T G.993.5, paragraph #11.1.2"
        ::= { zxAnXdsl2ExtConfPrfEntry 30 }
    
    zxAnXdsl2LFextCancelNotReqBandUs OBJECT-TYPE     
        SYNTAX      OCTET STRING(SIZE(0..32))
        MAX-ACCESS  read-create
        STATUS      current
        DESCRIPTION
            "This configuration parameter shall be an array of pairs of
             upstream sub-carrier indices. Each pair represents the start and 
             stop sub-carrier index of a frequency band in which FEXT 
             cancellation is not required. Up to 8 frequency bands may be 
             configured.
             The same configuration shall be applied for all lines in the 
             vectored group."
        REFERENCE    "ITU-T G.993.5, paragraph #11.1.2"
        ::= { zxAnXdsl2ExtConfPrfEntry 31 }
        
    zxAnXdsl2LConfInpMinShineUs OBJECT-TYPE     
        SYNTAX      Integer32(0..63)
        UNITS       "DMT symbol"
        MAX-ACCESS  read-create
        STATUS      current
        DESCRIPTION
            "GINP configuration parameters of upstream.
             The INPMIN_SHINE_RTX is a configuration parameter that, for the 
             case of subcarrier spacing of 4.3125kHz, is used to derive the 
             control parameter INP_min which specifies the minimum impulse 
             noise protection against SHINE.
             It is used in the Channel Initialization Policy and on-line 
             reconfiguration procedures.
             The downstream and upstream values of INPMIN_SHINE_RTX shall be 
             configured in the CO MIB.
             The value range from 0 to 63 DMT symbols of 4.3125 kHz in steps of 
             1 DMT.
             The control parameter INP_min shall be set to the same value as the
             configuration parameter INPMIN_SHINE_RTX."        
        REFERENCE    "ITU-T G.998.4, paragraph #11.1.6"
        ::= { zxAnXdsl2ExtConfPrfEntry 32 }
        
    zxAnXdsl2LConfInpMinShineDs OBJECT-TYPE     
        SYNTAX      Integer32(0..63)
        UNITS       "DMT symbol"
        MAX-ACCESS  read-create
        STATUS      current
        DESCRIPTION
            "GINP configuration parameters of upstream.
             The INPMIN_SHINE_RTX is a configuration parameter that, for the 
             case of subcarrier spacing of 4.3125kHz, is used to derive the 
             control parameter INP_min which specifies the minimum impulse 
             noise protection against SHINE.
             It is used in the Channel Initialization Policy and on-line 
             reconfiguration procedures.
             The downstream and upstream values of INPMIN_SHINE_RTX shall be 
             configured in the CO MIB.
             The value range from 0 to 63 DMT symbols of 4.3125 kHz in steps of 
             1 DMT.
             The control parameter INP_min shall be set to the same value as the
             configuration parameter INPMIN_SHINE_RTX."        
        REFERENCE    "ITU-T G.998.4, paragraph #11.1.6"
        ::= { zxAnXdsl2ExtConfPrfEntry 33 }
        
    zxAnXdsl2LConfInpMin8ShineUs OBJECT-TYPE     
        SYNTAX      Integer32(0..127)
        UNITS       "DMT symbol"
        MAX-ACCESS  read-create
        STATUS      current
        DESCRIPTION
            "GINP configuration parameters of upstream.
             The INPMIN8_SHINE_RTX is a configuration parameter that, for the 
             case of subcarrier spacing of 8.625kHz, is used to derive the 
             control parameter INP_min which specifies the minimum impulse 
             noise protection against SHINE.
             It is used in the Channel Initialization Policy and on-line 
             reconfiguration procedures.
             The downstream and upstream values of INPMIN8_SHINE_RTX shall be 
             configured in the CO MIB.
             The value range from 0 to 127 DMT symbols of 8.625 kHz in steps of 
             1 DMT.
             The control parameter INP_min shall be set to the same value as the
             configuration parameter INPMIN8_SHINE_RTX."        
        REFERENCE    "ITU-T G.998.4, paragraph #11.1.7"
        ::= { zxAnXdsl2ExtConfPrfEntry 34 }
        
    zxAnXdsl2LConfInpMin8ShineDs OBJECT-TYPE     
        SYNTAX      Integer32(0..127)
        UNITS       "DMT symbol"
        MAX-ACCESS  read-create
        STATUS      current
        DESCRIPTION
            "GINP configuration parameters of upstream.
             The INPMIN8_SHINE_RTX is a configuration parameter that, for the 
             case of subcarrier spacing of 8.625kHz, is used to derive the 
             control parameter INP_min which specifies the minimum impulse 
             noise protection against SHINE.
             It is used in the Channel Initialization Policy and on-line 
             reconfiguration procedures.
             The downstream and upstream values of INPMIN8_SHINE_RTX shall be 
             configured in the CO MIB.
             The value range from 0 to 127 DMT symbols of 8.625 kHz in steps of 
             1 DMT.
             The control parameter INP_min shall be set to the same value as the
             configuration parameter INPMIN8_SHINE_RTX."        
        REFERENCE    "ITU-T G.998.4, paragraph #11.1.7"
        ::= { zxAnXdsl2ExtConfPrfEntry 35 }
        
    zxAnXdsl2LConfInpMin8ReinUs OBJECT-TYPE     
        SYNTAX      Integer32(0..13)
        UNITS       "DMT symbol"
        MAX-ACCESS  read-create
        STATUS      current
        DESCRIPTION
            "GINP configuration parameters of upstream.
             The INPMIN8_REIN_RTX is a configuration parameter that, for the 
             case of subcarrier spacing of 8.625kHz, is used to derive the 
             control parameter INP_min which specifies the minimum impulse 
             noise protection against REIN.
             It is used in the Channel Initialization Policy and on-line 
             reconfiguration procedures.
             The downstream and upstream values of INPMIN8_SHINE_RTX shall be 
             configured in the CO MIB.
             The value range from 0 to 13 DMT symbols of 8.625 kHz in steps of 
             1 DMT.
             The control parameter INP_min shall be set to the same value as the
             configuration parameter INPMIN8_REIN_RTX."        
        REFERENCE    "ITU-T G.998.4, paragraph #11.1.10"
        ::= { zxAnXdsl2ExtConfPrfEntry 36 }
    
    zxAnXdsl2LConfInpMin8ReinDs OBJECT-TYPE     
        SYNTAX      Integer32(0..13)
        UNITS       "DMT symbol"
        MAX-ACCESS  read-create
        STATUS      current
        DESCRIPTION
            "GINP configuration parameters of upstream.
             The INPMIN8_REIN_RTX is a configuration parameter that, for the 
             case of subcarrier spacing of 8.625kHz, is used to derive the 
             control parameter INP_min which specifies the minimum impulse 
             noise protection against REIN.
             It is used in the Channel Initialization Policy and on-line 
             reconfiguration procedures.
             The downstream and upstream values of INPMIN8_SHINE_RTX shall be 
             configured in the CO MIB.
             The value range from 0 to 13 DMT symbols of 8.625 kHz in steps of 
             1 DMT.
             The control parameter INP_min shall be set to the same value as the
             configuration parameter INPMIN8_REIN_RTX."        
        REFERENCE    "ITU-T G.998.4, paragraph #11.1.10"
        ::= { zxAnXdsl2ExtConfPrfEntry 37 }
    
    zxAnXdsl2ExtConfPrfRowStatus  OBJECT-TYPE
        SYNTAX      RowStatus
        MAX-ACCESS  read-create
        STATUS      current
        DESCRIPTION
            "This object is used to create a new row or to modify or
            delete an existing row in this table.
        
            A profile is activated by setting this object to 'active'.
            When 'active' is set, the system will validate the profile.
            Profile modification is prohibited while this object is set
            to 'active'.
            "    
        ::= { zxAnXdsl2ExtConfPrfEntry 50 }    
              
-----------------------------------------------------------------------------
-- zxAnXdsl2SosConfPrfTable
-----------------------------------------------------------------------------

    zxAnXdsl2SosConfPrfTable  OBJECT-TYPE
        SYNTAX      SEQUENCE  OF  ZxAnXdsl2SosConfPrfEntry
        MAX-ACCESS  not-accessible
        STATUS      current
        DESCRIPTION
            "The Line SOS Profile Table."
        ::= { zxAnXdsl2LineProfile 21 }
    
    zxAnXdsl2SosConfPrfEntry  OBJECT-TYPE
        SYNTAX      ZxAnXdsl2SosConfPrfEntry
        MAX-ACCESS  not-accessible
        STATUS      current
        DESCRIPTION
            "Line SOS profile entry."
        INDEX  { zxAnXdsl2LConfSosPrfName }
        ::= { zxAnXdsl2SosConfPrfTable 1 }
         
    ZxAnXdsl2SosConfPrfEntry ::=
        SEQUENCE {
        zxAnXdsl2LConfSosPrfName            DisplayString,
        zxAnXdsl2LConfSosTimeWindowDs       Integer32,
        zxAnXdsl2LConfSosTimeWindowUs       Integer32,
        zxAnXdsl2LConfSosNTonesDs           Integer32,
        zxAnXdsl2LConfSosNTonesUs           Integer32,
        zxAnXdsl2LConfSosCrcDs              Integer32,
        zxAnXdsl2LConfSosCrcUs              Integer32,
        zxAnXdsl2LConfMaximumSosDs          Integer32,
        zxAnXdsl2LConfMaximumSosUs          Integer32,
        zxAnXdsl2LConfSosSnrmOffsetRocDs    Integer32,
        zxAnXdsl2LConfSosSnrmOffsetRocUs    Integer32,
        zxAnXdsl2LConfSosMinInpRocDs        Xdsl2SymbolProtection,
        zxAnXdsl2LConfSosMinInpRocUs        Xdsl2SymbolProtection,
        zxAnXdsl2LConfSosPrfRowStatus       RowStatus
        }
         
    zxAnXdsl2LConfSosPrfName  OBJECT-TYPE
        SYNTAX      DisplayString(SIZE(1..32))
        MAX-ACCESS  not-accessible
        STATUS      current
        DESCRIPTION
            "This object identifies a row in this table."
        ::= { zxAnXdsl2SosConfPrfEntry 1 }
         
    zxAnXdsl2LConfSosTimeWindowDs  OBJECT-TYPE
        SYNTAX      Integer32(0|64..16320)
        UNITS       "ms"
        MAX-ACCESS  read-create
        STATUS      current
        DESCRIPTION
            "The parameter SOS-TIME-ds is used in the specification of the
             receiver initiated SOS(see 13.4.3/G.993.2). If the value of this 
             parameter is not zero, the standard SOS triggering criteria are 
             enabled, and the value corresponds with duration of the time 
             window used in the standard SOS triggering criteria in the 
             downstream direction. See G.993.2 for detailed usage rules.
             The special value zero indicates that the standard SOS triggering 
             criteria are disabled, i.e., vendordiscretionary values may be 
             used instead of the values configured in the MIB for the following 
             parameters: SOS-NTONES-ds, SOS-CRC-ds, SOS-TIME-ds.
             This parameter applies in the downstream direction. The valid 
             range of non-zero values is from 64 ms to 16320 ms in steps of 64 
             ms."
        REFERENCE    
            "ITU-T G.997.1, paragraph #7.3.1.10.2
             ITU-T G.993.2, paragraph #13.4.3.1.1"
        DEFVAL       { 0 }
        ::= { zxAnXdsl2SosConfPrfEntry 2 }
         
    zxAnXdsl2LConfSosTimeWindowUs  OBJECT-TYPE
        SYNTAX      Integer32(0|64..16320)
        UNITS       "ms"
        MAX-ACCESS  read-create
        STATUS      current
        DESCRIPTION
            "The parameter SOS-TIME-us is used in the specification of the
             receiver initiated SOS (see 13.4.3/G.993.2). If the value of this 
             parameter is not zero, the standard SOS triggering criteria are 
             enabled, and the value corresponds with duration of the time 
             window used in the standard SOS triggering criteria in the 
             upstream direction. See G.993.2 for detailed usage rules.
             The special value zero indicates that the standard SOS triggering 
             criteria are disabled, i.e.,vendor-discretionary values may be 
             used instead of the values configured in the MIB for the following 
             parameters: SOS-NTONES-us, SOS-CRC-us, SOS-TIME-us.
             
             This parameter applies in the upstream direction. The valid range 
             of non-zero values is from 64 ms to 16320 ms in steps of 64 ms."
        REFERENCE    
            "ITU-T G.997.1, paragraph #7.3.1.10.2
             ITU-T G.993.2, paragraph #13.4.3.1.1"
        DEFVAL       { 0 }
        ::= { zxAnXdsl2SosConfPrfEntry 3 }
        
    zxAnXdsl2LConfSosNTonesDs  OBJECT-TYPE
        SYNTAX      Integer32(0..100)
        UNITS       "percentage"
        MAX-ACCESS  read-create
        STATUS      current
        DESCRIPTION
            "This parameter is defined as the minimum percentage of tones in the
             downstream MEDLEY SET that must be degraded in order to arm the 
             first sub-condition of the standard SOS triggering criteria
             (see 13.4.3.2/G.993.2) in the downstream direction. The parameter 
             SOS-NTONES-ds is defined as a percentage of tones. See G.993.2 for 
             detailed usage rules.
             
             The valid range of values is from 0 to 100 in steps of 1. A special 
             value of 0 indicates that SOS-NTONES-ds is not used in the decision 
             criteria."
        REFERENCE    
            "ITU-T G.997.1, paragraph #7.3.1.10.3
             ITU-T G.993.2, paragraph #13.4.3.1.2"
        ::= { zxAnXdsl2SosConfPrfEntry 4 }
        
    zxAnXdsl2LConfSosNTonesUs  OBJECT-TYPE
        SYNTAX      Integer32(0..100)
        UNITS       "percentage"
        MAX-ACCESS  read-create
        STATUS      current
        DESCRIPTION
            "The minimum percentage of tones in the upstream MEDLEY SET that
             must be degraded in order to arm the first sub-condition of the 
             standard SOS triggering criteria (see 13.4.3.2/G.993.2) in the 
             upstream direction. The parameter SOS-NTONES-us is defined as a 
             percentage of tones. See G.993.2 for detailed usage rules. 
             
             The valid range of values is from 0 to 100 in steps of 1. A special 
             value of 0 indicates that SOS-NTONES-ds is not used in the decision 
             criteria."
        REFERENCE    
            "ITU-T G.997.1, paragraph #7.3.1.10.4
             ITU-T G.993.2, paragraph #13.4.3.1.2"
        ::= { zxAnXdsl2SosConfPrfEntry 5 }
        
    zxAnXdsl2LConfSosCrcDs  OBJECT-TYPE
        SYNTAX      Integer32(1..65535)
        MAX-ACCESS  read-create
        STATUS      current
        DESCRIPTION
            "This parameter is defined as the minimum number of normalized CRC
             anomalies received in SOSTIME-ds seconds in order to arm the 
             second sub-condition of the standard SOS triggering criteria
             (see 13.4.3.2/G.993.2) in the downstream direction. See G.993.2 
             for detailed usage rules. 
             The valid range of SOS-CRC values is 0.02 to ((2^16)-1) X 0.02, in
             steps of 0.02."
        REFERENCE    
            "ITU-T G.997.1, paragraph #7.3.1.10.5
             ITU-T G.993.2, paragraph #13.4.3.1.3"
        ::= { zxAnXdsl2SosConfPrfEntry 6 }
        
    zxAnXdsl2LConfSosCrcUs  OBJECT-TYPE
        SYNTAX      Integer32(1..65535)
        MAX-ACCESS  read-create
        STATUS      current
        DESCRIPTION
            "This parameter is defined as the minimum number of normalized CRC
             anomalies received in SOSTIME-us seconds in order to arm the 
             second sub-condition of the standard SOS triggering criteria
             (see 13.4.3.2/G.993.2) in the upstream direction. See G.993.2 for 
             detailed usage rules. 
             The valid range of SOS-CRC values is 0.02 to ((2^16)-1) X 0.02, in
             steps of 0.02."
        REFERENCE    
            "ITU-T G.997.1, paragraph #7.3.1.10.6
             ITU-T G.993.2, paragraph #13.4.3.1.3"
        ::= { zxAnXdsl2SosConfPrfEntry 7 }
        
    zxAnXdsl2LConfMaximumSosDs  OBJECT-TYPE
        SYNTAX      Integer32(0..15)
        MAX-ACCESS  read-create
        STATUS      current
        DESCRIPTION
            "This parameter is used in G.993.2 de-activation
             (see 12.1.4/G.993.2). If the number of successful SOS procedures 
             in the downstream direction performed within a 120-second interval 
             exceeds MAX-SOS-ds, the modem shall transition to the L3 state. 
             See G.993.2 for detailed usage rules (see 12.1.4/G.993.2). 
             The valid range of values is 0 to 15. A special value of 0 
             indicates that there is no limit on the maximum allowed number of 
             SOS recoveries within this time interval."
        REFERENCE    
            "ITU-T G.997.1, paragraph #7.3.1.10.7
             ITU-T G.993.2, paragraph #12.1.4"
        ::= { zxAnXdsl2SosConfPrfEntry 8 }
        
    zxAnXdsl2LConfMaximumSosUs  OBJECT-TYPE
        SYNTAX      Integer32(0..15)
        MAX-ACCESS  read-create
        STATUS      current
        DESCRIPTION
            "This parameter is used in G.993.2 de-activation
             (see 12.1.4/G.993.2). If the number of successful SOS procedures 
             in the upstream direction performed within a 120-second interval 
             exceeds MAX-SOS-us, the modem shall transition to the L3 state. 
             See G.993.2 for detailed usage rules (see 12.1.4/G.993.2). 
             The valid range of values is 0 to 15. A special value of 0 
             indicates that there is no limit on the maximum allowed number of 
             SOS recoveries within this time interval."
        REFERENCE    
            "ITU-T G.997.1, paragraph #7.3.1.10.8
             ITU-T G.993.2, paragraph #12.1.4"
        ::= { zxAnXdsl2SosConfPrfEntry 9 }
        
    zxAnXdsl2LConfSosSnrmOffsetRocDs  OBJECT-TYPE
        SYNTAX      Integer32(0..310)
        UNITS       "0.1dB"
        MAX-ACCESS  read-create
        STATUS      current
        DESCRIPTION
            "The parameter is defined as the SNR margin offset for the ROC
             channel in the downstream direction. 
             The parameter is used in the specification of the channel 
             initialization policy (see 12.3.7.1/G.993.2).
             The valid range of SNR margin offset values is from 0 to 31 dB 
             with 0.1 dB steps."
        REFERENCE    
            "ITU-T G.997.1, paragraph #7.3.1.10.9
             ITU-T G.993.2, paragraph #12.3.7.1"
        ::= { zxAnXdsl2SosConfPrfEntry 10 }
    
    zxAnXdsl2LConfSosSnrmOffsetRocUs  OBJECT-TYPE
        SYNTAX      Integer32(0..310)
        UNITS       "0.1dB"
        MAX-ACCESS  read-create
        STATUS      current
        DESCRIPTION
            "The parameter is defined as the SNR margin offset for the ROC
             channel in the upstream direction.
             The parameter is used in the specification of the channel 
             initialization policy (see 12.3.7.1/G.993.2).
             The valid range of SNR margin offset values is from 0 to 31 dB 
             with 0.1 dB steps."
        REFERENCE    
            "ITU-T G.997.1, paragraph #7.3.1.10.10
             ITU-T G.993.2, paragraph #12.3.7.1"
        ::= { zxAnXdsl2SosConfPrfEntry 11 }
        
    zxAnXdsl2LConfSosMinInpRocDs  OBJECT-TYPE
        SYNTAX      Xdsl2SymbolProtection
        UNITS       "symbols"
        MAX-ACCESS  read-create
        STATUS      current
        DESCRIPTION
            "This parameter contains the minimum impulse noise protection to
             apply on the ROC in the downstream direction. 
             The minimum impulse noise protection is an integer ranging from 0 
             to 16."
        REFERENCE    
            "ITU-T G.997.1, paragraph #7.3.1.10.11"
        ::= { zxAnXdsl2SosConfPrfEntry 12 }
        
    zxAnXdsl2LConfSosMinInpRocUs  OBJECT-TYPE
        SYNTAX      Xdsl2SymbolProtection
        UNITS       "symbols"
        MAX-ACCESS  read-create
        STATUS      current
        DESCRIPTION
            "This parameter contains the minimum impulse noise protection to
             apply on the robust ROC in the upstream direction. 
             The minimum impulse noise protection is an integer ranging from 0 
             to 16."
        REFERENCE    
            "ITU-T G.997.1, paragraph #7.3.1.10.12"
        ::= { zxAnXdsl2SosConfPrfEntry 13 }
    
    zxAnXdsl2LConfSosPrfRowStatus    OBJECT-TYPE
        SYNTAX      RowStatus
        MAX-ACCESS  read-create
        STATUS      current
        DESCRIPTION
            "The status of this conceptual row.
            
            The supported actions of this conceptual row only include:
            'createAndGo' and 'destroy'.

            To create a row in this table, a manager must set this object to 
            createAndGo(4), and must comply with the multi-variables binding 
            rule described in zxAnXdsl2SosConfPrfEntry
    
            To delete a row in this table, a manager must set this object to 
            destroy(6). 
             
            To get this object, the agent always returns active(1)."
        ::= { zxAnXdsl2SosConfPrfEntry 50 }
        
-----------------------------------------------------------------------------
-- zxAnXdsl2InmConfPrfTable
-----------------------------------------------------------------------------
    
    zxAnXdsl2InmConfPrfTable  OBJECT-TYPE
        SYNTAX      SEQUENCE  OF  ZxAnXdsl2InmConfPrfEntry
        MAX-ACCESS  not-accessible
        STATUS      current
        DESCRIPTION
            "The Line INM Profile Table."
        ::= { zxAnXdsl2LineProfile 22 }
    
    zxAnXdsl2InmConfPrfEntry  OBJECT-TYPE
        SYNTAX      ZxAnXdsl2InmConfPrfEntry
        MAX-ACCESS  not-accessible
        STATUS      current
        DESCRIPTION
            "Line INM profile entry."
        INDEX  { zxAnXdsl2LConfInmPrfName }
        ::= { zxAnXdsl2InmConfPrfTable 1 }
         
    ZxAnXdsl2InmConfPrfEntry ::=
        SEQUENCE {
        zxAnXdsl2LConfInmPrfName            DisplayString,
        zxAnXdsl2LConfInmInpEqModeUs        Unsigned32,
        zxAnXdsl2LConfInmInpEqModeDs        Unsigned32,
        zxAnXdsl2LConfInmIatoUs             Unsigned32,
        zxAnXdsl2LConfInmIatoDs             Unsigned32,
        zxAnXdsl2LConfInmIatsUs             Unsigned32,
        zxAnXdsl2LConfInmIatsDs             Unsigned32,
        zxAnXdsl2LConfInmCcUs               Unsigned32,
        zxAnXdsl2LConfInmCcDs               Unsigned32,
        zxAnXdsl2LConfInmPrfRowStatus       RowStatus
        }
        
    zxAnXdsl2LConfInmPrfName  OBJECT-TYPE
        SYNTAX      DisplayString(SIZE(1..32))
        MAX-ACCESS  not-accessible
        STATUS      current
        DESCRIPTION
            "This object identifies a row in this table."
        ::= { zxAnXdsl2InmConfPrfEntry 1 }
        
    zxAnXdsl2LConfInmInpEqModeUs OBJECT-TYPE
        SYNTAX      Unsigned32(0..4)
        MAX-ACCESS  read-create
        STATUS      current
        DESCRIPTION
           "INM configuration parameters.
            This is the INM Equivalent INP Mode that the xTU receiver 
            shall use in the computation of the Equivalent INP, 
            as defined in the relevant ITU-T Recommendation.  
                     
            The valid values for INM_INPEQ_MODE are 0, 1, 2, 3, and 4."
        REFERENCE    "ITU-T G.997.1, paragraph #7.3.1.9.4"
        DEFVAL       { 0 }
        ::= { zxAnXdsl2InmConfPrfEntry 2 }      
      
    zxAnXdsl2LConfInmInpEqModeDs OBJECT-TYPE
        SYNTAX      Unsigned32(0..4)
        MAX-ACCESS  read-create
        STATUS      current
        DESCRIPTION
           "INM configuration parameters.
            This is the INM Equivalent INP Mode that the xTU receiver 
            shall use in the computation of the Equivalent INP, 
            as defined in the relevant ITU-T Recommendation.  
                     
            The valid values for INM_INPEQ_MODE are 0, 1, 2, 3, and 4."
        REFERENCE    "ITU-T G.997.1, paragraph #7.3.1.9.4"
        DEFVAL       { 0 }
        ::= { zxAnXdsl2InmConfPrfEntry 3 }        
                
    zxAnXdsl2LConfInmIatoUs OBJECT-TYPE
        SYNTAX      Unsigned32(3..511)
        UNITS       "1 DMT symbol"
        MAX-ACCESS  read-create
        STATUS      current
        DESCRIPTION
           "INM configuration parameters.
           This is the Inter Arrival Time Offset that the xTU receiver 
           shall use to determine in which bin of the Inter Arrival Time 
           histogram the IAT is reported. 
           
           The valid values for INMIATO ranges from 3 to 511 DMT symbols 
           in steps of 1 DMT symbol."
        REFERENCE    "ITU-T G.997.1, paragraph #7.3.1.9.1"
        DEFVAL       { 3 }
        ::= { zxAnXdsl2InmConfPrfEntry 4 }   
                      
    zxAnXdsl2LConfInmIatoDs OBJECT-TYPE
        SYNTAX      Unsigned32(3..511)
        UNITS       "1 DMT symbol"
        MAX-ACCESS  read-create
        STATUS      current
        DESCRIPTION
           "INM configuration parameters.
           This is the Inter Arrival Time Offset that the xTU receiver 
           shall use to determine in which bin of the Inter Arrival Time 
           histogram the IAT is reported. 
           
           The valid values for INMIATO ranges from 3 to 511 DMT symbols 
           in steps of 1 DMT symbol."
        REFERENCE    "ITU-T G.997.1, paragraph #7.3.1.9.1"
        DEFVAL       { 3 }
        ::= { zxAnXdsl2InmConfPrfEntry 5 }     

    zxAnXdsl2LConfInmIatsUs OBJECT-TYPE
        SYNTAX      Unsigned32(0..7)
        MAX-ACCESS  read-create
        STATUS      current
        DESCRIPTION
           "INM configuration parameters.
            This is the Inter Arrival Time Step that the xTU receiver 
            shall use to determine in which bin of the Inter Arrival 
            Time histogram the IAT is reported. 
            
            The valid values for INMIATS ranges from 0 to 7 in steps of 1."
        REFERENCE    "ITU-T G.997.1, paragraph #7.3.1.9.2"
        DEFVAL       { 0 }
        ::= { zxAnXdsl2InmConfPrfEntry 6 }  
          
    zxAnXdsl2LConfInmIatsDs OBJECT-TYPE
        SYNTAX      Unsigned32(0..7)
        MAX-ACCESS  read-create
        STATUS      current
        DESCRIPTION
           "INM configuration parameters.
            This is the Inter Arrival Time Step that the xTU receiver 
            shall use to determine in which bin of the Inter Arrival 
            Time histogram the IAT is reported. 
            
            The valid values for INMIATS ranges from 0 to 7 in steps of 1."
        REFERENCE    "ITU-T G.997.1, paragraph #7.3.1.9.2"
        DEFVAL       { 0 }
        ::= { zxAnXdsl2InmConfPrfEntry 7 }   
      
    zxAnXdsl2LConfInmCcUs OBJECT-TYPE
        SYNTAX      Unsigned32(0..64)
        UNITS       "1 DMT symbol"
        MAX-ACCESS  read-create
        STATUS      current
        DESCRIPTION
           "INM configuration parameters.
            This is the Cluster Continuation value that the xTU receiver
            shall use in the cluster indication process described in the 
            relevant ITU-T Recommendation. 
            
            The valid values for INMCC range from 0 to 64 DMT symbols 
            in steps of 1 DMT symbol."
        REFERENCE    "ITU-T G.997.1, paragraph #7.3.1.9.3"
        DEFVAL       { 0 }
        ::= { zxAnXdsl2InmConfPrfEntry 8 }      
      
    zxAnXdsl2LConfInmCcDs OBJECT-TYPE
        SYNTAX      Unsigned32(0..64)
        UNITS       "1 DMT symbol"
        MAX-ACCESS  read-create
        STATUS      current
        DESCRIPTION
           "INM configuration parameters.
            This is the Cluster Continuation value that the xTU receiver
            shall use in the cluster indication process described in the 
            relevant ITU-T Recommendation. 
            
            The valid values for INMCC range from 0 to 64 DMT symbols 
            in steps of 1 DMT symbol."
        REFERENCE    "ITU-T G.997.1, paragraph #7.3.1.9.3"
        DEFVAL       { 0 }
        ::= { zxAnXdsl2InmConfPrfEntry 9 }
    
    zxAnXdsl2LConfInmPrfRowStatus    OBJECT-TYPE
        SYNTAX      RowStatus
        MAX-ACCESS  read-create
        STATUS      current
        DESCRIPTION
            "The status of this conceptual row.
            
            The supported actions of this conceptual row only include:
            'createAndGo' and 'destroy'.

            To create a row in this table, a manager must set this object to 
            createAndGo(4), and must comply with the multi-variables binding 
            rule described in zxAnXdsl2InmConfPrfEntry
    
            To delete a row in this table, a manager must set this object to 
            destroy(6). 
             
            To get this object, the agent always returns active(1)."
        ::= { zxAnXdsl2InmConfPrfEntry 50 }
    
-----------------------------------------------------------------------------
-- zxAnXdsl2AlmThreshPrfTable
-----------------------------------------------------------------------------

    zxAnXdsl2AlmThreshPrfTable  OBJECT-TYPE
         SYNTAX      SEQUENCE  OF  ZxAnXdsl2AlmThreshPrfEntry
         MAX-ACCESS  not-accessible
         STATUS      current
         DESCRIPTION
          "The table zxAnXdsl2AlmThreshPrfTable contains DSL
          line PM thresholds profiles.
    
           Entries in this table MUST be maintained in a
           persistent manner."
         ::= { zxAnXdsl2AlarmProfile 1 }
    
    zxAnXdsl2AlmThreshPrfEntry  OBJECT-TYPE
         SYNTAX      ZxAnXdsl2AlmThreshPrfEntry
         MAX-ACCESS  not-accessible
         STATUS      current
         DESCRIPTION
          "The table zxAnXdsl2AlmThreshPrfTable contains DSL
          line PM thresholds profiles.
          A default profile with an index of 'VDEFVAL' will
          always exist and its parameters will be set to vendor
          specific values, unless otherwise specified in this
          document"
         INDEX  { zxAnXdsl2AlmThreshPrfName }
         ::= { zxAnXdsl2AlmThreshPrfTable 1 }
    
    ZxAnXdsl2AlmThreshPrfEntry ::=
        SEQUENCE {
        zxAnXdsl2AlmThreshPrfName         SnmpAdminString,
        zxAnXdsl2XtucThreshFecs           HCPerfIntervalThreshold,
        zxAnXdsl2XtucThreshEs             HCPerfIntervalThreshold,
        zxAnXdsl2XtucThreshSes            HCPerfIntervalThreshold,
        zxAnXdsl2XtucThreshLoss           HCPerfIntervalThreshold,
        zxAnXdsl2XtucThreshLofs           HCPerfIntervalThreshold,
        zxAnXdsl2XtucThreshLols           HCPerfIntervalThreshold,
        zxAnXdsl2XtucThreshLprs           HCPerfIntervalThreshold,
        zxAnXdsl2XtucThreshUas            HCPerfIntervalThreshold,
        zxAnXdsl2XtucThreshPtmCrcErrs     Unsigned32,
        zxAnXdsl2XtucThreshPtmCodViol     Unsigned32,
        zxAnXdsl2XturThreshFecs           HCPerfIntervalThreshold,
        zxAnXdsl2XturThreshEs             HCPerfIntervalThreshold,
        zxAnXdsl2XturThreshSes            HCPerfIntervalThreshold,
        zxAnXdsl2XturThreshLoss           HCPerfIntervalThreshold,
        zxAnXdsl2XturThreshLofs           HCPerfIntervalThreshold,
--        zxAnXdsl2XturThreshLols         HCPerfIntervalThreshold,
        zxAnXdsl2XturThreshLprs           HCPerfIntervalThreshold,
        zxAnXdsl2XturThreshUas            HCPerfIntervalThreshold,
        zxAnXdsl2XturThreshPtmCrcErrs     Unsigned32,
        zxAnXdsl2XturThreshPtmCodViol     Unsigned32,
        zxAnXdsl2ThreshFailedFullInt      Unsigned32,
        zxAnXdsl2ThreshFailedShrtInt      Unsigned32,
        zxAnXdsl2Ch1XtucThrshCodeViol     Unsigned32,
        zxAnXdsl2Ch1XtucThrshCorrected    Unsigned32,
        zxAnXdsl2Ch1XturThrshCodeViol     Unsigned32,
        zxAnXdsl2Ch1XturThrshCorrected    Unsigned32,
        zxAnXdsl2Ch2XtucThrshCodeViol     Unsigned32,
        zxAnXdsl2Ch2XtucThrshCorrected    Unsigned32,
        zxAnXdsl2Ch2XturThrshCodeViol     Unsigned32,
        zxAnXdsl2Ch2XturThrshCorrected    Unsigned32,
        zxAnXdsl2AlmThreshPrfRowStatus    RowStatus,
        zxAnXdsl2XtucLowDataRateTolerance INTEGER,                
        zxAnXdsl2XturLowDataRateTolerance INTEGER,   
        zxAnXdsl2XtucLowDataRateThresh    Integer32,       
        zxAnXdsl2XturLowDataRateThresh    Integer32,
        zxAnXdsl2XtucInitFailTrapEnable   BITS,
        zxAnXdsl2XturInitFailTrapEnable   BITS,
        zxAnXdsl2XtucThreshInpLeftr       INTEGER,         
        zxAnXdsl2XturThreshInpLeftr       INTEGER,
        zxAnXdsl2XtucEsLossRatioThresh    Integer32,
        zxAnXdsl2XturEsLossRatioThresh    Integer32,
        zxAnXdsl2XtucThreshInpLeftrs      HCPerfIntervalThreshold,
        zxAnXdsl2XturThreshInpLeftrs      HCPerfIntervalThreshold
        }

    zxAnXdsl2AlmThreshPrfName  OBJECT-TYPE
         SYNTAX      SnmpAdminString (SIZE(1..32))
         MAX-ACCESS  not-accessible
         STATUS      current
         DESCRIPTION
         "This object identifies a row in this table."
         ::= { zxAnXdsl2AlmThreshPrfEntry 1 }
    
    zxAnXdsl2XtucThreshFecs  OBJECT-TYPE
         SYNTAX      HCPerfIntervalThreshold
         UNITS       "seconds"
         MAX-ACCESS  read-create
         STATUS      current
         DESCRIPTION
         "A threshold for the xdsl2PMLCurr15MFecs counter,
         when xdsl2PMLCurrUnit is xtuc {1}.
         The value 0 means that no threshold is specified for the
         associated counter."
       REFERENCE    "ITU-T G.997.1, paragraph #7.3.1"
       DEFVAL       { 0 }
         ::= { zxAnXdsl2AlmThreshPrfEntry 2 }
    
    zxAnXdsl2XtucThreshEs  OBJECT-TYPE
         SYNTAX      HCPerfIntervalThreshold
         UNITS       "seconds"
         MAX-ACCESS  read-create
         STATUS      current
         DESCRIPTION
         "A threshold for the xdsl2PMLCurr15MEs counter,
         when xdsl2PMLCurrUnit is xtuc {1}.
         The value 0 means that no threshold is specified for the
         associated counter."
       REFERENCE    "ITU-T G.997.1, paragraph #7.3.1"
       DEFVAL       { 0 }
         ::= { zxAnXdsl2AlmThreshPrfEntry 3 }
    
    zxAnXdsl2XtucThreshSes  OBJECT-TYPE
         SYNTAX      HCPerfIntervalThreshold
         UNITS       "seconds"
         MAX-ACCESS  read-create
         STATUS      current
         DESCRIPTION
         "A threshold for the xdsl2PMLCurr15MSes counter,
         when xdsl2PMLCurrUnit is xtuc {1}.
         The value 0 means that no threshold is specified for the
         associated counter."
       REFERENCE    "ITU-T G.997.1, paragraph #7.3.1"
       DEFVAL       { 0 }
         ::= { zxAnXdsl2AlmThreshPrfEntry 4 }
    
    zxAnXdsl2XtucThreshLoss  OBJECT-TYPE
         SYNTAX      HCPerfIntervalThreshold
         UNITS       "seconds"
         MAX-ACCESS  read-create
         STATUS      current
         DESCRIPTION
         "A threshold for the zxAnXdsl2PMLCurr15MLoss counter,
         when xdsl2PMLCurrUnit is xtuc {1}.
         The value 0 means that no threshold is specified for the
         associated counter."
       REFERENCE    "ITU-T G.997.1, paragraph #7.3.1"
       DEFVAL       { 0 }
         ::= { zxAnXdsl2AlmThreshPrfEntry 5 }

    zxAnXdsl2XtucThreshLofs OBJECT-TYPE
        SYNTAX      HCPerfIntervalThreshold
        UNITS       "seconds"
        MAX-ACCESS  read-create
        STATUS      current
        DESCRIPTION
             "A threshold for the xdsl2PMLCurr15MLoss counter,
             when xdsl2PMLCurrUnit is xtuc {1}.
             The value 0 means that no threshold is specified for the
             associated counter."
       DEFVAL       { 0 }
        ::= { zxAnXdsl2AlmThreshPrfEntry 6}
    
    
    zxAnXdsl2XtucThreshLols  OBJECT-TYPE
        SYNTAX      HCPerfIntervalThreshold
        UNITS       "seconds"
        MAX-ACCESS  read-create
        STATUS      current
        DESCRIPTION
             "A threshold for the xdsl2PMLCurr15MLoss counter,
             when xdsl2PMLCurrUnit is xtuc {1}.
             The value 0 means that no threshold is specified for the
             associated counter."
       DEFVAL       { 0 }
        ::= { zxAnXdsl2AlmThreshPrfEntry 7}
    
    zxAnXdsl2XtucThreshLprs  OBJECT-TYPE
        SYNTAX      HCPerfIntervalThreshold
        UNITS       "seconds"
        MAX-ACCESS  read-create
        STATUS      current
        DESCRIPTION
             "A threshold for the xdsl2PMLCurr15MLoss counter,
             when xdsl2PMLCurrUnit is xtuc {1}.
             The value 0 means that no threshold is specified for the
             associated counter."
       DEFVAL       { 0 }
        ::= { zxAnXdsl2AlmThreshPrfEntry 8}
    
    
    zxAnXdsl2XtucThreshUas  OBJECT-TYPE
         SYNTAX      HCPerfIntervalThreshold
         UNITS       "seconds"
         MAX-ACCESS  read-create
         STATUS      current
         DESCRIPTION
         "A threshold for the zxAnXdsl2PMLCurr15MUas counter,
         when xdsl2PMLCurrUnit is xtuc {1}.
         The value 0 means that no threshold is specified for the
         associated counter."
       REFERENCE    "ITU-T G.997.1, paragraph #7.3.1"
       DEFVAL       { 0 }
         ::= { zxAnXdsl2AlmThreshPrfEntry 9 }


    zxAnXdsl2XtucThreshPtmCrcErrs  OBJECT-TYPE
        SYNTAX      Unsigned32
        MAX-ACCESS  read-create
        STATUS      current
        DESCRIPTION
             "A threshold for the zxAnXdsl2PMLCurr15MPtmCrcErrs counter,
             when xdsl2PMLCurrUnit is xtuc {1}.
             The value 0 means that no threshold is specified for the
             associated counter."
       DEFVAL       { 0 }
        ::= { zxAnXdsl2AlmThreshPrfEntry 10}
    

    zxAnXdsl2XtucThreshPtmCodViol  OBJECT-TYPE
        SYNTAX      Unsigned32
        MAX-ACCESS  read-create
        STATUS      current
        DESCRIPTION
             "A threshold for the zxAnXdsl2PMLCurr15MPtmCodViol counter,
             when xdsl2PMLCurrUnit is xtuc {1}.
             The value 0 means that no threshold is specified for the
             associated counter."
       DEFVAL       { 0 }
        ::= { zxAnXdsl2AlmThreshPrfEntry 11}

    
    zxAnXdsl2XturThreshFecs  OBJECT-TYPE
         SYNTAX      HCPerfIntervalThreshold
         UNITS       "seconds"
         MAX-ACCESS  read-create
         STATUS      current
         DESCRIPTION
         "A threshold for the xdsl2PMLCurr15MFecs counter,
         when xdsl2PMLCurrUnit is xtur {2}.
         The value 0 means that no threshold is specified for the
         associated counter."
       REFERENCE    "ITU-T G.997.1, paragraph #7.3.1"
       DEFVAL       { 0 }
         ::= { zxAnXdsl2AlmThreshPrfEntry 12 }
    
    zxAnXdsl2XturThreshEs  OBJECT-TYPE
         SYNTAX      HCPerfIntervalThreshold
         UNITS       "seconds"
         MAX-ACCESS  read-create
         STATUS      current
         DESCRIPTION
         "A threshold for the xdsl2PMLCurr15MEs counter,
         when xdsl2PMLCurrUnit is xtur {2}.
         The value 0 means that no threshold is specified for the
         associated counter."
       REFERENCE    "ITU-T G.997.1, paragraph #7.3.1"
       DEFVAL       { 0 }
         ::= { zxAnXdsl2AlmThreshPrfEntry 13 }
    
    
    zxAnXdsl2XturThreshSes  OBJECT-TYPE
         SYNTAX      HCPerfIntervalThreshold
         UNITS       "seconds"
         MAX-ACCESS  read-create
         STATUS      current
         DESCRIPTION
         "A threshold for the xdsl2PMLCurr15MSes counter,
         when xdsl2PMLCurrUnit is xtur {2}.
         The value 0 means that no threshold is specified for the
         associated counter."
       REFERENCE    "ITU-T G.997.1, paragraph #7.3.1"
       DEFVAL       { 0 }
         ::= { zxAnXdsl2AlmThreshPrfEntry 14 }
    
    zxAnXdsl2XturThreshLoss  OBJECT-TYPE
         SYNTAX      HCPerfIntervalThreshold
         UNITS       "seconds"
         MAX-ACCESS  read-create
         STATUS      current
         DESCRIPTION
         "A threshold for the xdsl2PMLCurr15MLoss counter,
         when xdsl2PMLCurrUnit is xtur {2}.
         The value 0 means that no threshold is specified for the
         associated counter."
       REFERENCE    "ITU-T G.997.1, paragraph #7.3.1"
       DEFVAL       { 0 }
         ::= { zxAnXdsl2AlmThreshPrfEntry 15 }


    zxAnXdsl2XturThreshLofs OBJECT-TYPE
        SYNTAX      HCPerfIntervalThreshold
        UNITS       "seconds"
        MAX-ACCESS  read-create
        STATUS      current
        DESCRIPTION
             "A threshold for the xdsl2PMLCurr15MLoss counter,
             when xdsl2PMLCurrUnit is xtur {2}.
             The value 0 means that no threshold is specified for the
             associated counter."
       DEFVAL       { 0 }
        ::= { zxAnXdsl2AlmThreshPrfEntry 16}
    
    
--    zxAnXdsl2XturThreshLols  OBJECT-TYPE
--        SYNTAX      HCPerfIntervalThreshold
--        UNITS       "seconds"
--        MAX-ACCESS  read-create
--        STATUS      current
--        DESCRIPTION
--             "A threshold for the xdsl2PMLCurr15MLoss counter,
--             when xdsl2PMLCurrUnit is xtur {2}.
--             The value 0 means that no threshold is specified for the
--             associated counter."
--       DEFVAL       { 0 }
--        ::= { zxAnXdsl2AlmThreshPrfEntry 17}
    
    zxAnXdsl2XturThreshLprs  OBJECT-TYPE
        SYNTAX      HCPerfIntervalThreshold
        UNITS       "seconds"
        MAX-ACCESS  read-create
        STATUS      current
        DESCRIPTION
             "A threshold for the xdsl2PMLCurr15MLoss counter,
             when xdsl2PMLCurrUnit is xtur {2}.
             The value 0 means that no threshold is specified for the
             associated counter."
       DEFVAL       { 0 }
        ::= { zxAnXdsl2AlmThreshPrfEntry 18}
    
    
    zxAnXdsl2XturThreshUas  OBJECT-TYPE
         SYNTAX      HCPerfIntervalThreshold
         UNITS       "seconds"
         MAX-ACCESS  read-create
         STATUS      current
         DESCRIPTION
         "A threshold for the xdsl2PMLCurr15MUas counter,
         when xdsl2PMLCurrUnit is xtur {2}.
         The value 0 means that no threshold is specified for the
         associated counter."
       REFERENCE    "ITU-T G.997.1, paragraph #7.3.1"
       DEFVAL       { 0 }
         ::= { zxAnXdsl2AlmThreshPrfEntry 19 }
    
    zxAnXdsl2XturThreshPtmCrcErrs  OBJECT-TYPE
        SYNTAX      Unsigned32
        MAX-ACCESS  read-create
        STATUS      current
        DESCRIPTION
             "A threshold for the zxAnXdsl2PMLCurr15MPtmCrcErrs counter,
             when xdsl2PMLCurrUnit is xtur {2}.
             The value 0 means that no threshold is specified for the
             associated counter."
       DEFVAL       { 0 }
        ::= { zxAnXdsl2AlmThreshPrfEntry 20}
    

    zxAnXdsl2XturThreshPtmCodViol  OBJECT-TYPE
        SYNTAX      Unsigned32
        MAX-ACCESS  read-create
        STATUS      current
        DESCRIPTION
             "A threshold for the zxAnXdsl2PMLCurr15MPtmCodViol counter,
             when xdsl2PMLCurrUnit is xtur {2}.
             The value 0 means that no threshold is specified for the
             associated counter."
       DEFVAL       { 0 }
        ::= { zxAnXdsl2AlmThreshPrfEntry 21}
        

    zxAnXdsl2ThreshFailedFullInt  OBJECT-TYPE
         SYNTAX      Unsigned32
         MAX-ACCESS  read-create
         STATUS      current
         DESCRIPTION
         "A threshold for the xdsl2PMLCurrInit15MfailedFullInits
         counter.
         The value 0 means that no threshold is specified for the
         associated counter."
       REFERENCE    "ITU-T G.997.1, paragraph #7.3.1"
       DEFVAL       { 0 }
         ::= { zxAnXdsl2AlmThreshPrfEntry 22 }
    
    zxAnXdsl2ThreshFailedShrtInt  OBJECT-TYPE
         SYNTAX      Unsigned32
         MAX-ACCESS  read-create
         STATUS      current
         DESCRIPTION
         "A threshold for the xdsl2PMLCurrInit15MFailedShortInits
         counter.
         The value 0 means that no threshold is specified for the
         associated counter."
       REFERENCE    "ITU-T G.997.1, paragraph #7.3.1"
       DEFVAL       { 0 }
         ::= { zxAnXdsl2AlmThreshPrfEntry 23 }
    
    zxAnXdsl2Ch1XtucThrshCodeViol OBJECT-TYPE
         SYNTAX      Unsigned32
         MAX-ACCESS  read-create
         STATUS      current
         DESCRIPTION
         "A threshold for the xdsl2PMChCurr15MCodingViolations
         counter, when xdsl2PMChCurrUnit is xtuc {1}.
         The value 0 means that no threshold is specified for the
         associated counter."
       REFERENCE    "ITU-T G.997.1, paragraph #7.3.2"
       DEFVAL       { 0 }
         ::= { zxAnXdsl2AlmThreshPrfEntry 24 }
    
    zxAnXdsl2Ch1XtucThrshCorrected  OBJECT-TYPE
         SYNTAX      Unsigned32
         MAX-ACCESS  read-create
         STATUS      current
         DESCRIPTION
         "A threshold for the xdsl2PMChCurr15MCorrectedBlocks
         counter, when xdsl2PMChCurrUnit is xtuc {1}.
         The value 0 means that no threshold is specified for the
         associated counter."
       REFERENCE    "ITU-T G.997.1, paragraph #7.3.2"
       DEFVAL       { 0 }
         ::= { zxAnXdsl2AlmThreshPrfEntry 25 }
    
    zxAnXdsl2Ch1XturThrshCodeViol  OBJECT-TYPE
         SYNTAX      Unsigned32
         MAX-ACCESS  read-create
         STATUS      current
         DESCRIPTION
         "A threshold for the xdsl2PMChCurr15MCodingViolations
         counter, when xdsl2PMChCurrUnit is xtur {2}.
         The value 0 means that no threshold is specified for the
         associated counter."
       REFERENCE    "ITU-T G.997.1, paragraph #7.3.2"
       DEFVAL       { 0 }
         ::= { zxAnXdsl2AlmThreshPrfEntry 26 }
    
    zxAnXdsl2Ch1XturThrshCorrected  OBJECT-TYPE
         SYNTAX      Unsigned32
         MAX-ACCESS  read-create
         STATUS      current
         DESCRIPTION
         "A threshold for the xdsl2PMChCurr15MCorrectedBlocks
         counter, when xdsl2PMChCurrUnit is xtur {2}.
         The value 0 means that no threshold is specified for the
         associated counter."
       REFERENCE    "ITU-T G.997.1, paragraph #7.3.2"
       DEFVAL       { 0 }
         ::= { zxAnXdsl2AlmThreshPrfEntry 27 }
    
    zxAnXdsl2Ch2XtucThrshCodeViol OBJECT-TYPE
         SYNTAX      Unsigned32
         MAX-ACCESS  read-create
         STATUS      current
         DESCRIPTION
         "A threshold for the xdsl2PMChCurr15MCodingViolations
         counter, when xdsl2PMChCurrUnit is xtuc {1}.
         The value 0 means that no threshold is specified for the
         associated counter."
       REFERENCE    "ITU-T G.997.1, paragraph #7.3.2"
       DEFVAL       { 0 }
         ::= { zxAnXdsl2AlmThreshPrfEntry 28 }
    
    zxAnXdsl2Ch2XtucThrshCorrected  OBJECT-TYPE
         SYNTAX      Unsigned32
         MAX-ACCESS  read-create
         STATUS      current
         DESCRIPTION
         "A threshold for the xdsl2PMChCurr15MCorrectedBlocks
         counter, when xdsl2PMChCurrUnit is xtuc {1}.
         The value 0 means that no threshold is specified for the
         associated counter."
       REFERENCE    "ITU-T G.997.1, paragraph #7.3.2"
       DEFVAL       { 0 }
         ::= { zxAnXdsl2AlmThreshPrfEntry 29 }
    
    zxAnXdsl2Ch2XturThrshCodeViol  OBJECT-TYPE
         SYNTAX      Unsigned32
         MAX-ACCESS  read-create
         STATUS      current
         DESCRIPTION
         "A threshold for the xdsl2PMChCurr15MCodingViolations
         counter, when xdsl2PMChCurrUnit is xtur {2}.
         The value 0 means that no threshold is specified for the
         associated counter."
       REFERENCE    "ITU-T G.997.1, paragraph #7.3.2"
       DEFVAL       { 0 }
         ::= { zxAnXdsl2AlmThreshPrfEntry 30 }
    
    zxAnXdsl2Ch2XturThrshCorrected  OBJECT-TYPE
         SYNTAX      Unsigned32
         MAX-ACCESS  read-create
         STATUS      current
         DESCRIPTION
         "A threshold for the xdsl2PMChCurr15MCorrectedBlocks
         counter, when xdsl2PMChCurrUnit is xtur {2}.
         The value 0 means that no threshold is specified for the
         associated counter."
       REFERENCE    "ITU-T G.997.1, paragraph #7.3.2"
       DEFVAL       { 0 }
         ::= { zxAnXdsl2AlmThreshPrfEntry 31 }

    zxAnXdsl2AlmThreshPrfRowStatus  OBJECT-TYPE
         SYNTAX      RowStatus
         MAX-ACCESS  read-create
         STATUS      current
         DESCRIPTION
          "This object is used to create a new row or to modify or
          delete an existing row in this table.
    
          A profile is activated by setting this object to 'active'.
          When 'active' is set, the system will validate the profile.
    
          Before a profile can be deleted or taken out of service
          (by setting this object to 'destroy' or 'notInService'),
          it must be first unreferenced from all associated
          templates."
         ::= { zxAnXdsl2AlmThreshPrfEntry 32 }    
       
    zxAnXdsl2XtucLowDataRateTolerance  OBJECT-TYPE
        SYNTAX      INTEGER(0..100)
        UNITS       "%"
        MAX-ACCESS  read-create
        STATUS      current
        DESCRIPTION
            " Tolerance between zxAnXdsl2ChConfMaxDataRateDs and
              xdsl2ChStatusActDataRate(xtuc).                   
              Calculation:
                           100*(zxAnXdsl2ChConfMaxDataRateDs - xdsl2ChStatusActDataRate(xtuc))
                Difference =-------------------------------------------------------------------
                                     zxAnXdsl2ChConfMaxDataRateDs
              If Difference  is larger than zxAnXdsl2XtucLowDataRateTolerance, 
              zxAnXdsl2LineXtucLowDataRateTrap will be sent.                 
              A value of `0' will disable the trap. "                  
        DEFVAL { 0 }
        ::= { zxAnXdsl2AlmThreshPrfEntry 33 } 
   
    zxAnXdsl2XturLowDataRateTolerance  OBJECT-TYPE
        SYNTAX      INTEGER(0..100)
        UNITS       "%"
        MAX-ACCESS  read-create
        STATUS      current
        DESCRIPTION
            " Tolerance between zxAnXdsl2ChConfMaxDataRateUs and
              xdsl2ChStatusActDataRate(xtur).                   
              Calculation:
                           100*(zxAnXdsl2ChConfMaxDataRateUs - xdsl2ChStatusActDataRate(xtur))
                Difference =-------------------------------------------------------------------
                                     zxAnXdsl2ChConfMaxDataRateUs
              If Difference  is larger than zxAnXdsl2XturLowDataRateTolerance, 
              zxAnXdsl2LineXturLowDataRateTrap will be sent.                 
              A value of `0' will disable the trap. "  
        DEFVAL { 0 }
        ::= { zxAnXdsl2AlmThreshPrfEntry 34 }
                     
    zxAnXdsl2XtucLowDataRateThresh  OBJECT-TYPE
        SYNTAX      Integer32
        UNITS       "kbps"
        MAX-ACCESS  read-create
        STATUS      current
        DESCRIPTION
            " Threshold of xtuc data rate. 
              If xdsl2ChStatusActDataRate(xtuc) is lower than zxAnXdsl2XtucLowDataRateThresh, 
              zxAnXdsl2LineXtucLowDataRateTrap will be sent.
              A value of `0' will disable the trap. "
        DEFVAL { 0 }
        ::= { zxAnXdsl2AlmThreshPrfEntry 35 }  
    
    zxAnXdsl2XturLowDataRateThresh  OBJECT-TYPE
        SYNTAX      Integer32
        UNITS       "kbps"
        MAX-ACCESS  read-create
        STATUS      current
        DESCRIPTION
            " Threshold of xtur data rate. 
              If xdsl2ChStatusActDataRate(xtur) is lower than zxAnXdsl2XturLowDataRateThresh, 
              zxAnXdsl2LineXturLowDataRateTrap will be sent.
              A value of `0' will disable the trap. "
        DEFVAL { 0 }
        ::= { zxAnXdsl2AlmThreshPrfEntry 36 }
    
    zxAnXdsl2XtucInitFailTrapEnable OBJECT-TYPE
        SYNTAX      BITS {
            unused1             (0),
            lossOfFraming       (1),
            lossOfSignal        (2),
            lossOfPower         (3),
            initFailure         (4),
            lossOfSignalQuality (5),
            lossOfLink          (6),
            lossOfSignalAlm     (7)
        }
        MAX-ACCESS  read-create
        STATUS      current
        DESCRIPTION
            "Enables and disables the InitFailureTrap on the xTU-C interface.
             
             unused1             (0) - This bit is no use to enable or disable
                                       the InitFailureTrap on the xTU-C 
                                       interface.

             lossOfFraming       (1) - Value 0 means disable the loss of frame 
                                       synchronization trap on the xTU-C
                                       interface.
                                    
             lossOfSignal        (2) - Value 0 means disable the loss of signal
                                       trap on the xTU-C interface.
                               
             lossOfPower         (3) - Value 0 means disable the loss of power 
                                       trap on the xTU-C interface.
                                              
             initFailure         (4) - Value 0 means disable the initialization
                                       failure trap on the xTU-C interface.
                              
             lossOfSignalQuality (5) - Value 0 means disable the loss of signal
                                       quality trap on the xTU-C interface.
                                       
             lossOfLink          (6) - Value 0 means disable the loss of link 
                                       quality trap on the xTU-C interface.
             
             lossOfSignalAlm     (7) - Value 0 means disable the loss of signal
                                       alarm on the xTU-C interface.
            "
        REFERENCE "Used by MAP"    
        ::= { zxAnXdsl2AlmThreshPrfEntry 37 }
    
    zxAnXdsl2XturInitFailTrapEnable OBJECT-TYPE
        SYNTAX      BITS{
            unused1             (0),
            lossOfFraming       (1),
            lossOfSignal        (2),
            lossOfPower         (3),
            unused2             (4),
            lossOfSignalQuality (5),
            unused3             (6),
            lossOfSignalAlm     (7),
            lossOfPowerAlm      (8)
        }
        MAX-ACCESS  read-create
        STATUS      current
        DESCRIPTION
            "Enables and disables the InitFailureTrap on the xTU-R interface.
            
             unused1             (0) - This bit is no use to enable or disable
                                       the InitFailureTrap on the xTU-R
                                       interface.
             
             lossOfFraming       (1) - Value 0 means disable the loss of frame 
                                       synchronization trap on the xTU-R
                                       interface.
                                    
             lossOfSignal        (2) - Value 0 means disable the loss of signal
                                       trap on the xTU-R interface.
             
             lossOfPower         (3) - Value 0 means disable the loss of power
                                       trap on the xTU-R interface.
             
             unused2             (4) - This bit is no use to enable or disable
                                       the InitFailureTrap on the xTU-R
                                       interface.
                         
             lossOfSignalQuality (5) - Value 0 means disable the loss of signal
                                       quality trap on the xTU-C interface.
             
             unused3             (6) - This bit is no use to enable or disable
                                       the InitFailureTrap on the xTU-R
                                       interface.
                                       
             lossOfSignalAlm     (7) - Value 0 means disable the loss of signal
                                       alarm on the xTU-R interface.
                                       
             lossOfPowerAlm      (8) - Value 0 means disable the loss of power
                                       alarm on the xTU-R interface.
            "
        REFERENCE "Used by MAP"
        ::= { zxAnXdsl2AlmThreshPrfEntry 38 }
      
    zxAnXdsl2XtucThreshInpLeftr OBJECT-TYPE     
        SYNTAX      INTEGER(0..100)
        MAX-ACCESS  read-create
        STATUS      current
        DESCRIPTION
            "The LEFTR_THRESH is a configuration parameter that is used to
             derive the control parameter leftr_thresh, which specifies the 
             fraction of NDR that shall be used as the threshold for declaring 
             leftr defects.
             The downstream and upstream values of LEFTR_THRESH shall be 
             configured in the CO-MIB.
             The valid range for LEFTR_THRESH is from 0.01 to 0.99 with a 
             granularity of 0.01 and a special value including that ETR shall 
             be used as the threshold for declaring leftr detects.
             The control parameter leftr_thresh shall be set to the same value 
             as the configuration parameter LEFTR_THRESH. The special value of 
             LEFTR_THRESH shall be mapped to leftr_thresh=0.
             The minimum valid threshold for declaring leftr defect is ETR/2.
             The receiver shall use ETR/2 in the case the threshold is 
             configured to a value less than ETR/2 by the operator.
             "
        DEFVAL       { 0 }
        ::= { zxAnXdsl2AlmThreshPrfEntry 39 }  
        
    zxAnXdsl2XturThreshInpLeftr OBJECT-TYPE
        SYNTAX      INTEGER(0..100)
        MAX-ACCESS  read-create
        STATUS      current
        DESCRIPTION
            "The LEFTR_THRESH is a configuration parameter that is used to
             derive the control parameter leftr_thresh, which specifies the 
             fraction of NDR that shall be used as the threshold for declaring 
             leftr defects.
             The downstream and upstream values of LEFTR_THRESH shall be 
             configured in the CO-MIB.
             The valid range for LEFTR_THRESH is from 0.01 to 0.99 with a 
             granularity of 0.01 and a special value including that ETR shall 
             be used as the threshold for declaring leftr detects.
             The control parameter leftr_thresh shall be set to the same value 
             as the configuration parameter LEFTR_THRESH. The special value of 
             LEFTR_THRESH shall be mapped to leftr_thresh=0.
             The minimum valid threshold for declaring leftr defect is ETR/2.
             The receiver shall use ETR/2 in the case the threshold is 
             configured to a value less than ETR/2 by the operator.   
            "
        DEFVAL       { 0 }
        ::= { zxAnXdsl2AlmThreshPrfEntry 40 }        
                     
    zxAnXdsl2XtucEsLossRatioThresh OBJECT-TYPE
        SYNTAX      Integer32(0..100)
        UNITS       "percent"
        MAX-ACCESS  read-create
        STATUS      current
        DESCRIPTION
            "XTU-C vectoring error sample loss ratio between
             zxAnXdsl2PMLCurr1DayTxEsPkts and zxAnXdsl2PMLCurr1DayRxEsPkts.
                              
             Calculation:
             Difference= 100 * (zxAnXdsl2PMLCurr1DayTxEsPkts - 
             zxAnXdsl2PMLCurr1DayRxEsPkts) / zxAnXdsl2PMLCurr1DayTxEsPkts

             If Difference is larger than zxAnXdsl2XtucEsLossRatioThresh, 
             zxAnXdsl2XtucEsLossOverThreshAlm will be sent.
             
             Value '0' means that the trap is disabled."
        DEFVAL { 0 }
        ::= { zxAnXdsl2AlmThreshPrfEntry 41 } 

    zxAnXdsl2XturEsLossRatioThresh OBJECT-TYPE
        SYNTAX      Integer32(0..100)
        UNITS       "percent"
        MAX-ACCESS  read-create
        STATUS      current
        DESCRIPTION
            "XTU-R error sample loss ratio between zxAnXdsl2PMLCurr1DayTxEsPkts
             and zxAnXdsl2PMLCurr1DayRxEsPkts.
              
             Calculation:
             Difference= 100 * (zxAnXdsl2PMLCurr1DayTxEsPkts - 
             zxAnXdsl2PMLCurr1DayRxEsPkts) / zxAnXdsl2PMLCurr1DayTxEsPkts
             
             If Difference is larger than zxAnXdsl2XturEsLossRatioThresh, 
             zxAnXdsl2XturEsLossOverThreshAlm will be sent.
                      
             Value '0' means that the trap is disabled."
        DEFVAL { 0 }
        ::= { zxAnXdsl2AlmThreshPrfEntry 42 }

    zxAnXdsl2XtucThreshInpLeftrs  OBJECT-TYPE
        SYNTAX      HCPerfIntervalThreshold
        UNITS       "seconds"
        MAX-ACCESS  read-create
        STATUS      current
        DESCRIPTION
            "A threshold for the zxAnXdsl2PMChCurr15MInpLeftrs counter,
             when xdsl2PMLCurrUnit is xtuc {1}.
             The value 0 means that no threshold is specified for the
             associated counter."
        DEFVAL { 0 }
        ::= { zxAnXdsl2AlmThreshPrfEntry 43 } 
         
    zxAnXdsl2XturThreshInpLeftrs  OBJECT-TYPE
        SYNTAX      HCPerfIntervalThreshold
        UNITS       "seconds"
        MAX-ACCESS  read-create
        STATUS      current
        DESCRIPTION
            "A threshold for the zxAnXdsl2PMChCurr15MInpLeftrs counter,
             when xdsl2PMLCurrUnit is xtur {2}.
             The value 0 means that no threshold is specified for the
             associated counter."
        DEFVAL { 0 }
        ::= { zxAnXdsl2AlmThreshPrfEntry 44 }
                             
------------------------------------------------------------------------------
-- zxAnXdsl2PMLineCurrTable
------------------------------------------------------------------------------

    zxAnXdsl2PMLineCurrTable  OBJECT-TYPE
        SYNTAX      SEQUENCE  OF  ZxAnXdsl2PMLineCurrEntry
        MAX-ACCESS  not-accessible
        STATUS      current
        DESCRIPTION
            "The table zxAnXdsl2PMLineCurrTable contains current Performance
             Monitoring results of DSL line. "
        ::= { zxAnXdsl2PMLine 1 }
    
    zxAnXdsl2PMLineCurrEntry  OBJECT-TYPE
        SYNTAX      ZxAnXdsl2PMLineCurrEntry
        MAX-ACCESS  not-accessible
        STATUS      current
        DESCRIPTION
            "The table zxAnXdsl2PMLineCurrTable contains current Performance
             Monitoring results of DSL line.
             The index of this table is an interface index where the
             interface has an ifType of vdsl2(xxx) and the termination
             unit."
        AUGMENTS  { xdsl2PMLineCurrEntry }
        ::= { zxAnXdsl2PMLineCurrTable 1 }
    
    ZxAnXdsl2PMLineCurrEntry  ::= SEQUENCE {
        zxAnXdsl2PMLCurr15MLofs                 Counter32,
        zxAnXdsl2PMLCurr15MLols                 Counter32,
        zxAnXdsl2PMLCurr15MLprs                 Counter32,
        zxAnXdsl2PMLCurr15MPtmCrcErrs           Counter32,
        zxAnXdsl2PMLCurr15MPtmCodViol           Counter32,        
        
        zxAnXdsl2PMLCurr1DayLofs                Counter32,
        zxAnXdsl2PMLCurr1DayLols                Counter32,
        zxAnXdsl2PMLCurr1DayLprs                Counter32,
        zxAnXdsl2PMLCurr1DayPtmCrcErrs          Counter32,
        zxAnXdsl2PMLCurr1DayPtmCodViol          Counter32,  
          
        zxAnXdsl2PMLCurr15MInmInpEq             OCTET STRING,
        zxAnXdsl2PMLCurr15MInmMe                Counter32,
        zxAnXdsl2PMLCurr15MInmIat               OCTET STRING,        
        zxAnXdsl2PMLCurr1DayInmInpEq            OCTET STRING,
        zxAnXdsl2PMLCurr1DayInmMe               Counter32,
        zxAnXdsl2PMLCurr1DayInmIat              OCTET STRING,        
        zxAnXdsl2PMLCurr15MSosSuccess           Counter32,        
        zxAnXdsl2PMLCurr1DaySosSuccess          Counter32,
        
        zxAnXdsl2PMLCurr15MTxEsPkts             Counter32,
        zxAnXdsl2PMLCurr15MRxEsPkts             Counter32,
        zxAnXdsl2PMLCurr1DayTxEsPkts            Counter32,
        zxAnXdsl2PMLCurr1DayRxEsPkts            Counter32
    }    
    
    zxAnXdsl2PMLCurr15MLofs  OBJECT-TYPE
        SYNTAX      Counter32
        UNITS       "seconds"
        MAX-ACCESS  read-only
        STATUS      current
        DESCRIPTION
           "Count of seconds during this interval that there was LOF ."
        REFERENCE    "ITU-T G.997.1, paragraph #7.2.1"
        ::= { zxAnXdsl2PMLineCurrEntry 1 }
           
    zxAnXdsl2PMLCurr15MLols  OBJECT-TYPE
        SYNTAX      Counter32
        UNITS       "seconds"
        MAX-ACCESS  read-only
        STATUS      current
        DESCRIPTION
           "Count of seconds during this interval that there was LOL."
        REFERENCE    "ITU-T G.997.1, paragraph #7.2.1"
        ::= { zxAnXdsl2PMLineCurrEntry 2 }   
    
    zxAnXdsl2PMLCurr15MLprs  OBJECT-TYPE
        SYNTAX      Counter32
        UNITS       "seconds"
        MAX-ACCESS  read-only
        STATUS      current
        DESCRIPTION
           "Count of seconds during this interval that there was LPR."
        REFERENCE    "ITU-T G.997.1, paragraph #7.2.1"
        ::= { zxAnXdsl2PMLineCurrEntry 3 }
    
    zxAnXdsl2PMLCurr15MPtmCrcErrs  OBJECT-TYPE
        SYNTAX      Counter32
        MAX-ACCESS  read-only
        STATUS      current
        DESCRIPTION
           "Count of the number of occurrences of Ptm Crc Errors during 
           this interval."
        REFERENCE    "ITU-T G.997.1, paragraph #7.2.5"
        ::= { zxAnXdsl2PMLineCurrEntry 4 }
    
    zxAnXdsl2PMLCurr15MPtmCodViol  OBJECT-TYPE
        SYNTAX      Counter32
        MAX-ACCESS  read-only
        STATUS      current
        DESCRIPTION
           "Count of the number of occurrences of Ptm coding violations  during 
           this interval."
        REFERENCE    "ITU-T G.997.1, paragraph #7.2.5"
        ::= { zxAnXdsl2PMLineCurrEntry 5 }           
       
    zxAnXdsl2PMLCurr1DayLofs  OBJECT-TYPE
        SYNTAX      Counter32
        UNITS       "seconds"
        MAX-ACCESS  read-only
        STATUS      current
        DESCRIPTION
           "Count of seconds during this interval that there was LOF."
        REFERENCE    "ITU-T G.997.1, paragraph #7.2.1"
        ::= { zxAnXdsl2PMLineCurrEntry 6 }
         
    zxAnXdsl2PMLCurr1DayLols  OBJECT-TYPE
        SYNTAX      Counter32
        UNITS       "seconds"
        MAX-ACCESS  read-only
        STATUS      current
        DESCRIPTION
           "Count of seconds during this interval that there was LOL."
        REFERENCE    "ITU-T G.997.1, paragraph #7.2.1"
        ::= { zxAnXdsl2PMLineCurrEntry 7 }
    
    zxAnXdsl2PMLCurr1DayLprs  OBJECT-TYPE
        SYNTAX      Counter32
        UNITS       "seconds"
        MAX-ACCESS  read-only
        STATUS      current
        DESCRIPTION
           "Count of seconds during this interval that there was LPR."
        REFERENCE    "ITU-T G.997.1, paragraph #7.2.1"
        ::= { zxAnXdsl2PMLineCurrEntry 8 }
           
    zxAnXdsl2PMLCurr1DayPtmCrcErrs  OBJECT-TYPE
        SYNTAX      Counter32
        MAX-ACCESS  read-only
        STATUS      current
        DESCRIPTION
           "Count of the number of occurrences of Ptm Crc Errors during 
           this interval."
        REFERENCE    "ITU-T G.997.1, paragraph #7.2.5"
        ::= { zxAnXdsl2PMLineCurrEntry 9 }
    
    zxAnXdsl2PMLCurr1DayPtmCodViol  OBJECT-TYPE
        SYNTAX      Counter32
        MAX-ACCESS  read-only
        STATUS      current
        DESCRIPTION
           "Count of the number of occurrences of Ptm coding violations  during 
           this interval."
        REFERENCE    "ITU-T G.997.1, paragraph #7.2.5"
        ::= { zxAnXdsl2PMLineCurrEntry 10 }                  
       
    zxAnXdsl2PMLCurr15MInmInpEq OBJECT-TYPE 
        SYNTAX      OCTET STRING (SIZE(0..68))
        MAX-ACCESS  read-only
        STATUS      current
        DESCRIPTION     
            "INM parameters.
            The integer sequence of INM INPEQ histogram 1..17. 
            Each parameter is a count of the INMAINPEQi anomalies occurring on 
            the line during the accumulation period.
            Each parameter is presented with 4 octets.
            Octets 0-3               -- INMAINPEQ1  
            Octets 4-7               -- INMAINPEQ2
            Octets 8-11              -- INMAINPEQ3
            ...
            Octets 64-67             -- INMAINPEQ17"
        REFERENCE    "ITU-T G.997.1, paragraph #7.2.1.4.1"
        ::=  {  zxAnXdsl2PMLineCurrEntry  11  }     
       
    zxAnXdsl2PMLCurr15MInmMe OBJECT-TYPE
        SYNTAX      Counter32
        MAX-ACCESS  read-only
        STATUS      current
        DESCRIPTION
           "INM parameters.
            This parameter is a count of the INMAME anomalies occurring on the 
            line during the accumulation period."
        REFERENCE    "ITU-T G.997.1, paragraph #7.2.1.4.2"
        ::= { zxAnXdsl2PMLineCurrEntry 12 }
       
    zxAnXdsl2PMLCurr15MInmIat OBJECT-TYPE
        SYNTAX      OCTET STRING (SIZE(0..32))
        MAX-ACCESS  read-only
        STATUS      current
        DESCRIPTION
           "INM parameters.
            This parameter is a count of the INMAIATi(0-7) anomalies occurring 
            on the line during the accumulation period.
            Each parameter is presented with 4 octets.
            Octets 0-3               -- INMAIAT0  
            Octets 4-7               -- INMAIAT1
            Octets 8-11              -- INMAIAT2
            ...
            Octets 28-31             -- INMAIAT7"
        REFERENCE    "ITU-T G.997.1, paragraph #7.2.1.4.3"
        ::= { zxAnXdsl2PMLineCurrEntry 13 }
              
    zxAnXdsl2PMLCurr1DayInmInpEq OBJECT-TYPE 
        SYNTAX      OCTET STRING (SIZE(0..68))
        MAX-ACCESS  read-only
        STATUS      current
        DESCRIPTION     
            "INM parameters.
            The integer sequence of INM INPEQ histogram 1..17.
            Each parameter is a count of the INMAINPEQi anomalies occurring on 
            the line during the accumulation period. 
            Each parameter is presented with 4 octets.
            Octets 0-3               -- INMAINPEQ1  
            Octets 4-7               -- INMAINPEQ2
            Octets 8-11              -- INMAINPEQ3
            ...
            Octets 64-67             -- INMAINPEQ17"
        REFERENCE    "ITU-T G.997.1, paragraph #7.2.1.4.1"
        ::= { zxAnXdsl2PMLineCurrEntry 14 }

    zxAnXdsl2PMLCurr1DayInmMe OBJECT-TYPE
        SYNTAX      Counter32
        MAX-ACCESS  read-only
        STATUS      current
        DESCRIPTION
           "INM parameters.
            This parameter is a count of the INMAME anomalies occurring on the 
            line during the accumulation period."
        REFERENCE    "ITU-T G.997.1, paragraph #7.2.1.4.2"
        ::= { zxAnXdsl2PMLineCurrEntry 15 }

    zxAnXdsl2PMLCurr1DayInmIat OBJECT-TYPE
        SYNTAX      OCTET STRING (SIZE(0..32))
        MAX-ACCESS  read-only
        STATUS      current
        DESCRIPTION
           "INM parameters.
            This parameter is a count of the INMAIATi(0-7) anomalies occurring 
            on the line during the accumulation period.
            Each parameter is presented with 4 octets.
            Octets 0-3               -- INMAIAT0  
            Octets 4-7               -- INMAIAT1
            Octets 8-11              -- INMAIAT2
            ...
            Octets 28-31             -- INMAIAT7"
        REFERENCE    "ITU-T G.997.1, paragraph #7.2.1.4.3"
        ::= { zxAnXdsl2PMLineCurrEntry 16 }

    zxAnXdsl2PMLCurr15MSosSuccess OBJECT-TYPE
        SYNTAX      Counter32
        MAX-ACCESS  read-only
        STATUS      current
        DESCRIPTION
            "This parameter is a count of the total number of successful SOS
             procedures initiated on the line during the accumulation period. 
             Parameter procedures shall be as defined in 7.2.7."
        REFERENCE    "ITU-T G.997.1, paragraph #7.2.1.6.1"
        ::= { zxAnXdsl2PMLineCurrEntry 17 }

    zxAnXdsl2PMLCurr1DaySosSuccess OBJECT-TYPE
        SYNTAX      Counter32
        MAX-ACCESS  read-only
        STATUS      current
        DESCRIPTION
            "This parameter is a count of the total number of successful SOS
             procedures initiated on the line during the accumulation period. 
             Parameter procedures shall be as defined in 7.2.7."
        REFERENCE    "ITU-T G.997.1, paragraph #7.2.1.6.1"
        ::= { zxAnXdsl2PMLineCurrEntry 18 }
        
    zxAnXdsl2PMLCurr15MTxEsPkts OBJECT-TYPE
        SYNTAX      Counter32
        MAX-ACCESS  read-only
        STATUS      current
        DESCRIPTION
            "Transmitted erorr sample packets during 15 minutes."        
        ::= { zxAnXdsl2PMLineCurrEntry 27 }
        
    zxAnXdsl2PMLCurr15MRxEsPkts OBJECT-TYPE
        SYNTAX      Counter32
        MAX-ACCESS  read-only
        STATUS      current
        DESCRIPTION
            "Received erorr sample packets during 15 minutes."        
        ::= { zxAnXdsl2PMLineCurrEntry 28 }
        
    zxAnXdsl2PMLCurr1DayTxEsPkts OBJECT-TYPE
        SYNTAX      Counter32
        MAX-ACCESS  read-only
        STATUS      current
        DESCRIPTION
            "Transmitted erorr sample packets during 1 day."        
        ::= { zxAnXdsl2PMLineCurrEntry 29 }
        
    zxAnXdsl2PMLCurr1DayRxEsPkts OBJECT-TYPE
        SYNTAX      Counter32
        MAX-ACCESS  read-only
        STATUS      current
        DESCRIPTION
            "Received erorr sample packets during 1 day."        
        ::= { zxAnXdsl2PMLineCurrEntry 30 }
       
------------------------------------------------------------------------------
-- zxAnXdsl2PMLineHist15MinTable
------------------------------------------------------------------------------

    zxAnXdsl2PMLineHist15MinTable  OBJECT-TYPE
       SYNTAX      SEQUENCE  OF  ZxAnXdsl2PMLineHist15MinEntry
       MAX-ACCESS  not-accessible
       STATUS      current
       DESCRIPTION
          "The table zxAnXdsl2PMLineHist15MinTable contains history Performance 
           Monitoring results for 15min of DSL line. "
       ::= { zxAnXdsl2PMLine 2 }
    
    zxAnXdsl2PMLineHist15MinEntry  OBJECT-TYPE
       SYNTAX      ZxAnXdsl2PMLineHist15MinEntry
       MAX-ACCESS  not-accessible
       STATUS      current
       DESCRIPTION
          "The table zxAnXdsl2PMLineHist15MinTable contains history Performance  
           Monitoring results for 15min of DSL line.
           The index of this table is an interface index where the
           interface has an ifType of vdsl2(xxx) and the termination
           unit."
       AUGMENTS  { xdsl2PMLineHist15MinEntry }
       ::= { zxAnXdsl2PMLineHist15MinTable 1 }
    
    ZxAnXdsl2PMLineHist15MinEntry  ::=
        SEQUENCE {
        zxAnXdsl2PMLHist15MMonitoredTime        Unsigned32,
        zxAnXdsl2PMLHist15MLofs                 Counter32,
        zxAnXdsl2PMLHist15MLols                 Counter32,
        zxAnXdsl2PMLHist15MLprs                 Counter32,
        zxAnXdsl2PMLHist15MPtmCrcErrs           Counter32,
        zxAnXdsl2PMLHist15MPtmCodViol           Counter32,
        zxAnXdsl2PMLHist15MValidInterval        TruthValue,  

        zxAnXdsl2PMLHist15MInmInpEq             OCTET STRING,
        zxAnXdsl2PMLHist15MInmMe                Counter32,
        zxAnXdsl2PMLHist15MInmIat               OCTET STRING,
        zxAnXdsl2PMLHist15MSosSuccess           Counter32,
          
        zxAnXdsl2PMLHist15MTxEsPkts             Counter32,
        zxAnXdsl2PMLHist15MRxEsPkts             Counter32
       }
      
    zxAnXdsl2PMLHist15MMonitoredTime  OBJECT-TYPE
        SYNTAX      Unsigned32
        UNITS       "seconds"
        MAX-ACCESS  read-only
        STATUS      current
        DESCRIPTION
           "Total seconds monitored in this interval."
        ::= { zxAnXdsl2PMLineHist15MinEntry 1 }
    
    zxAnXdsl2PMLHist15MLofs  OBJECT-TYPE
        SYNTAX      Counter32
        UNITS       "seconds"
        MAX-ACCESS  read-only
        STATUS      current
        DESCRIPTION
           "Count of seconds during this interval that there was LOF ."
        REFERENCE    "ITU-T G.997.1, paragraph #7.2.1"
        ::= { zxAnXdsl2PMLineHist15MinEntry 2 }
    
    zxAnXdsl2PMLHist15MLols  OBJECT-TYPE
        SYNTAX      Counter32
        UNITS       "seconds"
        MAX-ACCESS  read-only
        STATUS      current
        DESCRIPTION
           "Count of seconds during this interval that there was LOL."
        REFERENCE    "ITU-T G.997.1, paragraph #7.2.1"
        ::= { zxAnXdsl2PMLineHist15MinEntry 3 }    
    
    zxAnXdsl2PMLHist15MLprs  OBJECT-TYPE
        SYNTAX      Counter32
        UNITS       "seconds"
        MAX-ACCESS  read-only
        STATUS      current
        DESCRIPTION
           "Count of seconds during this interval that there was LPR."
        REFERENCE    "ITU-T G.997.1, paragraph #7.2.1"
        ::= { zxAnXdsl2PMLineHist15MinEntry 4 }
           
    zxAnXdsl2PMLHist15MPtmCrcErrs  OBJECT-TYPE
        SYNTAX      Counter32
        MAX-ACCESS  read-only
        STATUS      current
        DESCRIPTION
           "Count of the number of occurrences of Ptm Crc Errors during 
           this interval."
        REFERENCE    "ITU-T G.997.1, paragraph #7.2.5"
        ::= { zxAnXdsl2PMLineHist15MinEntry 5 }
    
    zxAnXdsl2PMLHist15MPtmCodViol  OBJECT-TYPE
        SYNTAX      Counter32
        MAX-ACCESS  read-only
        STATUS      current
        DESCRIPTION
           "Count of the number of occurrences of Ptm coding violations  during 
           this interval."
        REFERENCE    "ITU-T G.997.1, paragraph #7.2.5"
        ::= { zxAnXdsl2PMLineHist15MinEntry 6 }    

    zxAnXdsl2PMLHist15MValidInterval  OBJECT-TYPE
        SYNTAX      TruthValue
        MAX-ACCESS  read-only
        STATUS      current
        DESCRIPTION
           "This variable indicates if the data for this interval is
            valid."
        ::= { zxAnXdsl2PMLineHist15MinEntry 7 }         
              
    zxAnXdsl2PMLHist15MInmInpEq  OBJECT-TYPE 
        SYNTAX      OCTET STRING (SIZE(0..68))
        MAX-ACCESS  read-only
        STATUS      current
        DESCRIPTION     
            "INM parameters.
            The integer sequence of INM INPEQ histogram 1..17.
            Each parameter is a count of the INMAINPEQi anomalies occurring on 
            the line during the accumulation period. 
            Each parameter is presented with 4 octets.
            Octets 0-3               -- INMAINPEQ1  
            Octets 4-7               -- INMAINPEQ2
            Octets 8-11              -- INMAINPEQ3
            ...
            Octets 64-67             -- INMAINPEQ17"
        REFERENCE    "ITU-T G.997.1, paragraph #7.2.1.4.1"
        ::=  {  zxAnXdsl2PMLineHist15MinEntry  8  }     

    zxAnXdsl2PMLHist15MInmMe  OBJECT-TYPE
        SYNTAX      Counter32
        MAX-ACCESS  read-only
        STATUS      current
        DESCRIPTION
           "INM parameters.
            This parameter is a count of the INMAME anomalies occurring on the
            line during the accumulation period."
        REFERENCE    "ITU-T G.997.1, paragraph #7.2.1.4.2"
        ::= { zxAnXdsl2PMLineHist15MinEntry 9 }
       
    zxAnXdsl2PMLHist15MInmIat  OBJECT-TYPE
        SYNTAX      OCTET STRING (SIZE(0..32))
        MAX-ACCESS  read-only
        STATUS      current
        DESCRIPTION
           "INM parameters.
            This parameter is a count of the INMAIATi(0-7) anomalies occurring 
            on the line during the accumulation period.
            Each parameter is presented with 4 octets.
            Octets 0-3               -- INMAIAT0  
            Octets 4-7               -- INMAIAT1
            Octets 8-11              -- INMAIAT2
            ...
            Octets 28-31             -- INMAIAT7"
        REFERENCE    "ITU-T G.997.1, paragraph #7.2.1.4.3"
        ::= { zxAnXdsl2PMLineHist15MinEntry 10 }
    
    zxAnXdsl2PMLHist15MSosSuccess  OBJECT-TYPE
        SYNTAX      Counter32
        MAX-ACCESS  read-only
        STATUS      current
        DESCRIPTION
            "This parameter is a count of the total number of successful SOS
             procedures initiated on the line during the accumulation period. 
             Parameter procedures shall be as defined in 7.2.7."
        REFERENCE    "ITU-T G.997.1, paragraph #7.2.1.6.1"
        ::= { zxAnXdsl2PMLineHist15MinEntry 11 }

    zxAnXdsl2PMLHist15MTxEsPkts   OBJECT-TYPE
        SYNTAX      Counter32
        MAX-ACCESS  read-only
        STATUS      current
        DESCRIPTION
            "Transmitted error sample packets during 15 minutes."
        ::= { zxAnXdsl2PMLineHist15MinEntry 16 }
     
    zxAnXdsl2PMLHist15MRxEsPkts   OBJECT-TYPE
        SYNTAX      Counter32
        MAX-ACCESS  read-only
        STATUS      current
        DESCRIPTION
            "Received error sample packets during 15 minutes."
        ::= { zxAnXdsl2PMLineHist15MinEntry 17 }

------------------------------------------------------------------------------
-- zxAnXdsl2PMLineHist1DayTable
------------------------------------------------------------------------------

    zxAnXdsl2PMLineHist1DayTable  OBJECT-TYPE
       SYNTAX      SEQUENCE  OF  ZxAnXdsl2PMLineHist1DayEntry
       MAX-ACCESS  not-accessible
       STATUS      current
       DESCRIPTION
          "The table zxAnXdsl2PMLineHist1DayTable contains history Performance 
           Monitoring results for 1 Day of DSL line. "
       ::= { zxAnXdsl2PMLine 3 }
    
    zxAnXdsl2PMLineHist1DayEntry  OBJECT-TYPE
       SYNTAX      ZxAnXdsl2PMLineHist1DayEntry
       MAX-ACCESS  not-accessible
       STATUS      current
       DESCRIPTION
          "The table zxAnXdsl2PMLineHist1DayTable contains history Performance  
           Monitoring results for 1Day of DSL line.
           The index of this table is an interface index where the
           interface has an ifType of vdsl2(xxx) and the termination
           unit."
       AUGMENTS  { xdsl2PMLineHist1DayEntry }
       ::= { zxAnXdsl2PMLineHist1DayTable 1 }
    
    ZxAnXdsl2PMLineHist1DayEntry  ::=
       SEQUENCE {
          zxAnXdsl2PMLHist1DayMonitoredTime        Unsigned32,
          zxAnXdsl2PMLHist1DayLofs                 Counter32,
          zxAnXdsl2PMLHist1DayLols                 Counter32,
          zxAnXdsl2PMLHist1DayLprs                 Counter32,
          zxAnXdsl2PMLHist1DayPtmCrcErrs           Counter32,
          zxAnXdsl2PMLHist1DayPtmCodViol           Counter32,
          zxAnXdsl2PMLHist1DayValidInterval        TruthValue,                    
                  
          zxAnXdsl2PMLHist1DayInmInpEq             OCTET STRING,
          zxAnXdsl2PMLHist1DayInmMe                Counter32,
          zxAnXdsl2PMLHist1DayInmIat               OCTET STRING,          
          zxAnXdsl2PMLHist1DaySosSuccess           Counter32,
          
          zxAnXdsl2PMLHist1DayEsPkts               Counter32,
          zxAnXdsl2PMLHist1DayEsPkts               Counter32
       }
      
    zxAnXdsl2PMLHist1DayMonitoredTime  OBJECT-TYPE
        SYNTAX      Unsigned32
        UNITS       "seconds"
        MAX-ACCESS  read-only
        STATUS      current
        DESCRIPTION
           "Total seconds monitored in this interval."
        ::= { zxAnXdsl2PMLineHist1DayEntry 1 }
    
    zxAnXdsl2PMLHist1DayLofs  OBJECT-TYPE
        SYNTAX      Counter32
        UNITS       "seconds"
        MAX-ACCESS  read-only
        STATUS      current
        DESCRIPTION
           "Count of seconds during this interval that there was LOF ."
        REFERENCE    "ITU-T G.997.1, paragraph #7.2.1"
        ::= { zxAnXdsl2PMLineHist1DayEntry 2 }
    
    zxAnXdsl2PMLHist1DayLols  OBJECT-TYPE
        SYNTAX      Counter32
        UNITS       "seconds"
        MAX-ACCESS  read-only
        STATUS      current
        DESCRIPTION
           "Count of seconds during this interval that there was LOL."
        REFERENCE    "ITU-T G.997.1, paragraph #7.2.1"
        ::= { zxAnXdsl2PMLineHist1DayEntry 3 }    
    
    zxAnXdsl2PMLHist1DayLprs  OBJECT-TYPE
        SYNTAX      Counter32
        UNITS       "seconds"
        MAX-ACCESS  read-only
        STATUS      current
        DESCRIPTION
           "Count of seconds during this interval that there was LPR."
        REFERENCE    "ITU-T G.997.1, paragraph #7.2.1"
        ::= { zxAnXdsl2PMLineHist1DayEntry 4 }
           
    zxAnXdsl2PMLHist1DayPtmCrcErrs  OBJECT-TYPE
        SYNTAX      Counter32
        MAX-ACCESS  read-only
        STATUS      current
        DESCRIPTION
           "Count of the number of occurrences of Ptm Crc Errors during 
           this interval."
        REFERENCE    "ITU-T G.997.1, paragraph #7.2.5"
        ::= { zxAnXdsl2PMLineHist1DayEntry 5 }
    
    zxAnXdsl2PMLHist1DayPtmCodViol  OBJECT-TYPE
        SYNTAX      Counter32
        MAX-ACCESS  read-only
        STATUS      current
        DESCRIPTION
           "Count of the number of occurrences of Ptm coding violations  during 
           this interval."
        REFERENCE    "ITU-T G.997.1, paragraph #7.2.5"
        ::= { zxAnXdsl2PMLineHist1DayEntry 6 }    

    zxAnXdsl2PMLHist1DayValidInterval  OBJECT-TYPE
        SYNTAX      TruthValue
        MAX-ACCESS  read-only
        STATUS      current
        DESCRIPTION
           "This variable indicates if the data for this interval is
            valid."
        ::= { zxAnXdsl2PMLineHist1DayEntry 7 }
              
    zxAnXdsl2PMLHist1DayInmInpEq OBJECT-TYPE 
        SYNTAX      OCTET STRING (SIZE(0..68))
        MAX-ACCESS  read-only
        STATUS      current
        DESCRIPTION     
            "INM parameters.
            The integer sequence of INM INPEQ histogram 1..17.
            Each parameter is a count of the INMAINPEQi anomalies occurring on 
            the line during the accumulation period. 
            Each parameter is presented with 4 octets.
            Octets 0-3               -- INMAINPEQ1  
            Octets 4-7               -- INMAINPEQ2
            Octets 8-11              -- INMAINPEQ3
            ...
            Octets 64-67             -- INMAINPEQ17"
        REFERENCE    "ITU-T G.997.1, paragraph #7.2.1.4.1"
        ::=  {  zxAnXdsl2PMLineHist1DayEntry  8  }     
       
    zxAnXdsl2PMLHist1DayInmMe OBJECT-TYPE
        SYNTAX      Counter32
        MAX-ACCESS  read-only
        STATUS      current
        DESCRIPTION
           "INM parameters.
            This parameter is a count of the INMAME anomalies occurring on the 
            line during the accumulation period."
        REFERENCE    "ITU-T G.997.1, paragraph #7.2.1.4.2"
        ::= { zxAnXdsl2PMLineHist1DayEntry 9 }
       
    zxAnXdsl2PMLHist1DayInmIat OBJECT-TYPE
        SYNTAX      OCTET STRING (SIZE(0..32))
        MAX-ACCESS  read-only
        STATUS      current
        DESCRIPTION
           "INM parameters.
            This parameter is a count of the INMAIATi(0-7) anomalies occurring 
            on the line during the accumulation period.
            Each parameter is presented with 4 octets.
            Octets 0-3               -- INMAIAT0  
            Octets 4-7               -- INMAIAT1
            Octets 8-11              -- INMAIAT2
            ...
            Octets 28-31             -- INMAIAT7"
        REFERENCE    "ITU-T G.997.1, paragraph #7.2.1.4.3"
        ::= { zxAnXdsl2PMLineHist1DayEntry 10 }

    zxAnXdsl2PMLHist1DaySosSuccess OBJECT-TYPE
        SYNTAX      Counter32
        MAX-ACCESS  read-only
        STATUS      current
        DESCRIPTION
            "This parameter is a count of the total number of successful SOS
             procedures initiated on the line during the accumulation period. 
             Parameter procedures shall be as defined in 7.2.7."
        REFERENCE    "ITU-T G.997.1, paragraph #7.2.1.6.1"
        ::= { zxAnXdsl2PMLineHist1DayEntry 11 }
        
    zxAnXdsl2PMLHist1DayTxEsPkts OBJECT-TYPE
        SYNTAX      Counter32
        MAX-ACCESS  read-only
        STATUS      current
        DESCRIPTION
            "Transmitted error sample packets during 1 day."
        ::= { zxAnXdsl2PMLineHist1DayEntry 16 }
        
    zxAnXdsl2PMLHist1DayRxEsPkts OBJECT-TYPE
        SYNTAX      Counter32
        MAX-ACCESS  read-only
        STATUS      current
        DESCRIPTION
            "Received error sample packets during 1 day."
        ::= { zxAnXdsl2PMLineHist1DayEntry 17 }

------------------------------------------------------------------------------
-- zxAnXdsl2PMChCurrTable
------------------------------------------------------------------------------

    zxAnXdsl2PMChCurrTable  OBJECT-TYPE
       SYNTAX      SEQUENCE  OF  ZxAnXdsl2PMChCurrEntry
       MAX-ACCESS  not-accessible
       STATUS      current
       DESCRIPTION
          "The table zxAnXdsl2PMChCurrTable contains current Performance
           Monitoring results of DSL Channel. "
       ::= { zxAnXdsl2PMChannel 1 }
    
    zxAnXdsl2PMChCurrEntry  OBJECT-TYPE
       SYNTAX      ZxAnXdsl2PMChCurrEntry
       MAX-ACCESS  not-accessible
       STATUS      current
       DESCRIPTION
          "The table zxAnXdsl2PMChCurrTable contains current Performance
           Monitoring results of DSL Channel.
           The index of this table is an interface index where the
           interface has an ifType of vdsl2(xxx) and the termination
           unit."
       AUGMENTS  { xdsl2PMChCurrEntry }
       ::= { zxAnXdsl2PMChCurrTable 1 }
    
    ZxAnXdsl2PMChCurrEntry  ::=
       SEQUENCE {
          zxAnXdsl2PMChCurr15MRtxDtu                 Counter32,
          zxAnXdsl2PMChCurr15MRtxCDtu                Counter32,
          zxAnXdsl2PMChCurr15MRtxUcDtu               Counter32,   
          
          zxAnXdsl2PMChCurr15MInpLeftrs              Counter32,
          zxAnXdsl2PMChCurr15MInpEfb                 Counter32,
          zxAnXdsl2PMChCurr15MInpMinEftr             Counter32,          
                                    
          zxAnXdsl2PMChCurr1DayRtxDtu                Counter32,
          zxAnXdsl2PMChCurr1DayRtxCDtu               Counter32,
          zxAnXdsl2PMChCurr1DayRtxUcDtu              Counter32,  
          
          zxAnXdsl2PMChCurr1DayInpLeftrs             Counter32,
          zxAnXdsl2PMChCurr1DayInpEfb                Counter32,
          zxAnXdsl2PMChCurr1DayInpMinEftr            Counter32,          
                  
          zxAnXdsl2PMChCurrTransmittedBlks           Counter32,
          zxAnXdsl2PMChCurrOverflowBlks              Counter32,
          zxAnXdsl2PMChCurrErroredBlks               Counter32
       }    
    
    zxAnXdsl2PMChCurr15MRtxDtu  OBJECT-TYPE
        SYNTAX      Counter32
        MAX-ACCESS  read-only
        STATUS      current
        DESCRIPTION
            "this is a counter that is incremented each time a DTU has been
             retransmitted by the transmitter in the current 15 minute 
             interval. Multiple retransmission of the same DTU is counted 
             as many times as it has been retransmitted.
             "         
        ::= { zxAnXdsl2PMChCurrEntry 1 }
           
    zxAnXdsl2PMChCurr15MRtxCDtu  OBJECT-TYPE
        SYNTAX      Counter32
        MAX-ACCESS  read-only
        STATUS      current
        DESCRIPTION
            "This is a counter that is incremented each time a DTU has been 
             detected in error and has been successfully corrected by a 
             retransmission in the current 15 minute interval"
        ::= { zxAnXdsl2PMChCurrEntry 2 }   
    
    zxAnXdsl2PMChCurr15MRtxUcDtu  OBJECT-TYPE
        SYNTAX      Counter32
        MAX-ACCESS  read-only
        STATUS      current
        DESCRIPTION
            "This is a counter that is incremented each time a DTU is detected
             in error and has not been corrected by a retransmission in the 
             current 15 minute interval."
        ::= { zxAnXdsl2PMChCurrEntry 3 }
        
    zxAnXdsl2PMChCurr15MInpLeftrs  OBJECT-TYPE
        SYNTAX      Counter32
        UNITS       "seconds"
        MAX-ACCESS  read-only
        STATUS      current
        DESCRIPTION
            "This is a counter of seconds with a 'leftr' defect present.
             It is a 32-bit wrap-around counter. The counter shall be reset at 
             power-on. The counters shall not be reset with a link state 
             transition and shall not be reset when read."
        REFERENCE   "ITU-T G.998.4, paragraph #11.4.1"
        ::= { zxAnXdsl2PMChCurrEntry 4 }
        
    zxAnXdsl2PMChCurr15MInpEfb  OBJECT-TYPE
        SYNTAX      Counter32
        UNITS       "bits"
        MAX-ACCESS  read-only
        STATUS      current
        DESCRIPTION
            "This is a counter counting the number of error-free bits passed 
             over the beta1-reference point, deivided by 2^16. Error-free bits 
             are bits originating from DTU's that have been detected to contain 
             on error at the moment of crossing the beta1-reference point.
             It is a 32-bit wrap-around counter. The counter shall be reset at 
             power-on. The counters shall not be reset with a link state 
             transition and shall not be reset when read."
        REFERENCE   "ITU-T G.998.4, paragraph #11.4.2"
        ::= { zxAnXdsl2PMChCurrEntry 5 }
        
    zxAnXdsl2PMChCurr15MInpMinEftr  OBJECT-TYPE
        SYNTAX      Counter32
        UNITS       "kbps"
        MAX-ACCESS  read-only
        STATUS      current
        DESCRIPTION
            "The performance monitoring parameter minimum error-free
             throughput(EFTR_min) is defined as the minimum of the EFTR 
             observed since the last reading of the EFTR_min via an EOC command 
             over the U-interface.
             The EFTR_min shall be measured in Showtime by the receiver.
             The valid values are all integers from 0 to the maximum of the 
             valid values of the maximum net data rate specified in the 
             associated Recommendation values.
             The performance monitoring parameter EFTR_min shall be represented 
             as a 32-bit unsigned integer expressing the value of EFTR_min in 
             kbps This data format supports a granularity of 1 kbps.
             The previous value of EFTR_min shall be reported in the EOC if no 
             EFTR measurement has been done since the last reading of EFTR_min."
        REFERENCE   "ITU-T G.998.4, paragraph #11.4.3"
        ::= { zxAnXdsl2PMChCurrEntry 6 }
              
    zxAnXdsl2PMChCurr1DayRtxDtu  OBJECT-TYPE
        SYNTAX      Counter32
        MAX-ACCESS  read-only
        STATUS      current
        DESCRIPTION
            "This is a counter that is incremented each time a DTU has been 
             retransmitted by the transmitter in the current day interval. 
             Multiple retransmission of the same DTU is counted as many times 
             as it has been retransmitted.
             "
        ::= { zxAnXdsl2PMChCurrEntry 51 }
           
    zxAnXdsl2PMChCurr1DayRtxCDtu  OBJECT-TYPE
        SYNTAX      Counter32
        MAX-ACCESS  read-only
        STATUS      current
        DESCRIPTION
            "This is a counter that is incremented each time a DTU has been 
             detected in error and has been successfully corrected by a 
             retransmission in the current day interval"
        ::= { zxAnXdsl2PMChCurrEntry 52 }   
    
    zxAnXdsl2PMChCurr1DayRtxUcDtu  OBJECT-TYPE
        SYNTAX      Counter32
        MAX-ACCESS  read-only
        STATUS      current
        DESCRIPTION
            "This is a counter that is incremented each time a DTU is detected
             in error and has not been corrected by a retransmission."
        ::= { zxAnXdsl2PMChCurrEntry 53 }
        
    zxAnXdsl2PMChCurr1DayInpLeftrs  OBJECT-TYPE
        SYNTAX      Counter32
        UNITS       "seconds"
        MAX-ACCESS  read-only
        STATUS      current
        DESCRIPTION
            "This is a counter of seconds with a 'leftr' defect present.
             It is a 32-bit wrap-around counter. The counter shall be reset at 
             power-on. The counters shall not be reset with a link state 
             transition and shall not be reset when read."
        REFERENCE   "ITU-T G.998.4, paragraph #11.4.1"
        ::= { zxAnXdsl2PMChCurrEntry 54 }
        
    zxAnXdsl2PMChCurr1DayInpEfb  OBJECT-TYPE
        SYNTAX      Counter32
        UNITS       "bits"
        MAX-ACCESS  read-only
        STATUS      current
        DESCRIPTION
            "This is a counter counting the number of error-free bits passed 
             over the beta1-reference point, deivided by 2^16. Error-free bits 
             are bits originating from DTU's that have been detected to contain 
             on error at the moment of crossing the beta1-reference point.
             It is a 32-bit wrap-around counter. The counter shall be reset at 
             power-on. The counters shall not be reset with a link state 
             transition and shall not be reset when read."
        REFERENCE   "ITU-T G.998.4, paragraph #11.4.2"
        ::= { zxAnXdsl2PMChCurrEntry 55 }
        
    zxAnXdsl2PMChCurr1DayInpMinEftr  OBJECT-TYPE
        SYNTAX      Counter32
        UNITS       "kbps"
        MAX-ACCESS  read-only
        STATUS      current
        DESCRIPTION
            "The performance monitoring parameter minimum error-free
             throughput(EFTR_min) is defined as the minimum of the EFTR 
             observed since the last reading of the EFTR_min via an EOC command 
             over the U-interface.
             The EFTR_min shall be measured in Showtime by the receiver.
             The valid values are all integers from 0 to the maximum of the 
             valid values of the maximum net data rate specified in the 
             associated Recommendation values.
             The performance monitoring parameter EFTR_min shall be represented 
             as a 32-bit unsigned integer expressing the value of EFTR_min in 
             kbps This data format supports a granularity of 1 kbps.
             The previous value of EFTR_min shall be reported in the EOC if no 
             EFTR measurement has been done since the last reading of EFTR_min."
        REFERENCE   "ITU-T G.998.4, paragraph #11.4.3"
        ::= { zxAnXdsl2PMChCurrEntry 56 }
       
    zxAnXdsl2PMChCurrTransmittedBlks  OBJECT-TYPE
       SYNTAX      Counter32
       MAX-ACCESS  read-only
       STATUS      current
       DESCRIPTION
          "Count of blocks transmitted since last reset. 
           This parameter represents ATM cells for ATM mode, and 
           PTM packets for PTM mode.          
          "
       ::= { zxAnXdsl2PMChCurrEntry 101 }   
       
    zxAnXdsl2PMChCurrOverflowBlks  OBJECT-TYPE
       SYNTAX      Counter32
       MAX-ACCESS  read-only
       STATUS      current
       DESCRIPTION
          "Count of overflow blocks since last reset.
           This parameter represents ATM cells for ATM mode, and 
           PTM packets for PTM mode.          
          "
       ::= { zxAnXdsl2PMChCurrEntry 102 }   
       
    zxAnXdsl2PMChCurrErroredBlks  OBJECT-TYPE
       SYNTAX      Counter32
       MAX-ACCESS  read-only
       STATUS      current
       DESCRIPTION
          "Count of errored blocks since last reset.
           This parameter represents ATM cells for ATM mode, and 
           PTM packets for PTM mode.          
          "
       ::= { zxAnXdsl2PMChCurrEntry 103 }

------------------------------------------------------------------------------
-- zxAnXdsl2PMChHist15MinTable
------------------------------------------------------------------------------

    zxAnXdsl2PMChHist15MinTable  OBJECT-TYPE
       SYNTAX      SEQUENCE  OF  ZxAnXdsl2PMChHist15MinEntry
       MAX-ACCESS  not-accessible
       STATUS      current
       DESCRIPTION
          "The table zxAnXdsl2PMChHist15MinTable contains history Performance 
           Monitoring results for 15min of DSL channel. "
       ::= { zxAnXdsl2PMChannel 2 }
    
    zxAnXdsl2PMChHist15MinEntry  OBJECT-TYPE
       SYNTAX      ZxAnXdsl2PMChHist15MinEntry
       MAX-ACCESS  not-accessible
       STATUS      current
       DESCRIPTION
          "The table zxAnXdsl2PMChHist15MinTable contains history Performance  
           Monitoring results for 15min of DSL channel.
           The index of this table is an interface index where the
           interface has an ifType of vdsl2(xxx) and the termination
           unit."
       AUGMENTS  { xdsl2PMChHist15MinEntry }
       ::= { zxAnXdsl2PMChHist15MinTable 1 }
    
    ZxAnXdsl2PMChHist15MinEntry  ::=
       SEQUENCE {
          zxAnXdsl2PMChHist15MRtxDtu                  Counter32,
          zxAnXdsl2PMChHist15MRtxCDtu                 Counter32,
          zxAnXdsl2PMChHist15MRtxUcDtu                Counter32,
          
          zxAnXdsl2PMChHist15MInpLeftrs               Counter32,
          zxAnXdsl2PMChHist15MInpEfb                  Counter32,
          zxAnXdsl2PMChHist15MInpMinEftr              Counter32
       }
         
    zxAnXdsl2PMChHist15MRtxDtu  OBJECT-TYPE
        SYNTAX      Counter32
        MAX-ACCESS  read-only
        STATUS      current
        DESCRIPTION
            "This is a counter that is incremented each time a DTU has been 
             retransmitted by the transmitter during this interval. Multiple
             retransmission of the same DTU is counted as many times as it has
             been retransmitted.
             "
       ::= { zxAnXdsl2PMChHist15MinEntry 1 }
           
    zxAnXdsl2PMChHist15MRtxCDtu  OBJECT-TYPE
        SYNTAX      Counter32
        MAX-ACCESS  read-only
        STATUS      current
        DESCRIPTION
            "This is a counter that is incremented each time a DTU has been 
             detected in error and has been successfully corrected by a 
             retransmission during this interval."       
        ::= { zxAnXdsl2PMChHist15MinEntry 2 }   
    
    zxAnXdsl2PMChHist15MRtxUcDtu OBJECT-TYPE
        SYNTAX      Counter32
        MAX-ACCESS  read-only
        STATUS      current
        DESCRIPTION
            "This is a counter that is incremented each time a DTU is detected
             in error and has not been corrected by a retransmission. during 
             this interval."
        ::= { zxAnXdsl2PMChHist15MinEntry 3 }   
       
    zxAnXdsl2PMChHist15MInpLeftrs  OBJECT-TYPE
        SYNTAX      Counter32
        UNITS       "seconds"
        MAX-ACCESS  read-only
        STATUS      current
        DESCRIPTION
            "This is a counter of seconds with a 'leftr' defect present.
             It is a 32-bit wrap-around counter. The counter shall be reset at 
             power-on. The counters shall not be reset with a link state 
             transition and shall not be reset when read."
        REFERENCE   "ITU-T G.998.4, paragraph #11.4.1"
        ::= { zxAnXdsl2PMChHist15MinEntry 4 }
        
    zxAnXdsl2PMChHist15MInpEfb  OBJECT-TYPE
        SYNTAX      Counter32
        UNITS       "bits"
        MAX-ACCESS  read-only
        STATUS      current
        DESCRIPTION
            "This is a counter counting the number of error-free bits passed 
             over the beta1-reference point, deivided by 2^16. Error-free bits 
             are bits originating from DTU's that have been detected to contain 
             on error at the moment of crossing the beta1-reference point.
             It is a 32-bit wrap-around counter. The counter shall be reset at 
             power-on. The counters shall not be reset with a link state 
             transition and shall not be reset when read."
        REFERENCE   "ITU-T G.998.4, paragraph #11.4.2"
        ::= { zxAnXdsl2PMChHist15MinEntry 5 }
        
    zxAnXdsl2PMChHist15MInpMinEftr  OBJECT-TYPE
        SYNTAX      Counter32
        UNITS       "kpbs"
        MAX-ACCESS  read-only
        STATUS      current
        DESCRIPTION
            "The performance monitoring parameter minimum error-free
             throughput(EFTR_min) is defined as the minimum of the EFTR 
             observed since the last reading of the EFTR_min via an EOC command 
             over the U-interface.
             The EFTR_min shall be measured in Showtime by the receiver.
             The valid values are all integers from 0 to the maximum of the 
             valid values of the maximum net data rate specified in the 
             associated Recommendation values.
             The performance monitoring parameter EFTR_min shall be represented 
             as a 32-bit unsigned integer expressing the value of EFTR_min in 
             kbps This data format supports a granularity of 1 kbps.
             The previous value of EFTR_min shall be reported in the EOC if no 
             EFTR measurement has been done since the last reading of EFTR_min."
        REFERENCE   "ITU-T G.998.4, paragraph #11.4.3"
        ::= { zxAnXdsl2PMChHist15MinEntry 6 }
       
------------------------------------------------------------------------------
-- zxAnXdsl2PMChHist1DayTable
------------------------------------------------------------------------------

    zxAnXdsl2PMChHist1DayTable  OBJECT-TYPE
       SYNTAX      SEQUENCE  OF  ZxAnXdsl2PMChHist1DayEntry
       MAX-ACCESS  not-accessible
       STATUS      current
       DESCRIPTION
          "The table zxAnXdsl2PMChHist1DayTable contains history Performance 
           Monitoring results for 1 Day of DSL channel. "
       ::= { zxAnXdsl2PMChannel 3 }
    
    zxAnXdsl2PMChHist1DayEntry  OBJECT-TYPE
       SYNTAX      ZxAnXdsl2PMChHist1DayEntry
       MAX-ACCESS  not-accessible
       STATUS      current
       DESCRIPTION
          "The table zxAnXdsl2PMChHist1DayTable contains history Performance  
           Monitoring results for 1Day of DSL channel.
           The index of this table is an interface index where the
           interface has an ifType of vdsl2(xxx) and the termination
           unit."
       AUGMENTS  { xdsl2PMChHist1DEntry }
       ::= { zxAnXdsl2PMChHist1DayTable 1 }
    
    ZxAnXdsl2PMChHist1DayEntry  ::=
       SEQUENCE {                    
          zxAnXdsl2PMChHist1DayRtxDtu         Counter32,
          zxAnXdsl2PMChHist1DayRtxCDtu        Counter32,
          zxAnXdsl2PMChHist1DayRtxUcDtu       Counter32,
          
          zxAnXdsl2PMChHist1DayInpLeftrs      Counter32,
          zxAnXdsl2PMChHist1DayInpEfb         Counter32,
          zxAnXdsl2PMChHist1DayInpMinEftr     Counter32
       }

    zxAnXdsl2PMChHist1DayRtxDtu  OBJECT-TYPE
        SYNTAX      Counter32
        MAX-ACCESS  read-only
        STATUS      current
        DESCRIPTION
            "This is a counter that is incremented each time a DTU has been 
             retransmitted by the transmitter during this interval. Multiple 
             retransmission of the same DTU is counted as many times as it 
             has been retransmitted."
        ::= { zxAnXdsl2PMChHist1DayEntry 1 }
           
    zxAnXdsl2PMChHist1DayRtxCDtu  OBJECT-TYPE
        SYNTAX      Counter32
        MAX-ACCESS  read-only
        STATUS      current
        DESCRIPTION
            "This is a counter that is incremented each time a DTU has been 
             detected in error and has been successfully corrected by a 
             retransmission during this interval."       
        ::= { zxAnXdsl2PMChHist1DayEntry 2 }   
    
    zxAnXdsl2PMChHist1DayRtxUcDtu  OBJECT-TYPE
        SYNTAX      Counter32
        MAX-ACCESS  read-only
        STATUS      current
        DESCRIPTION
            "This is a counter that is incremented each time a DTU is detected
             in error and has not been corrected by a retransmission during 
             this interval."
        ::= { zxAnXdsl2PMChHist1DayEntry 3 }
        
    zxAnXdsl2PMChHist1DayInpLeftrs  OBJECT-TYPE
        SYNTAX      Counter32
        UNITS       "seconds"
        MAX-ACCESS  read-only
        STATUS      current
        DESCRIPTION
            "This is a counter of seconds with a 'leftr' defect present.
             It is a 32-bit wrap-around counter. The counter shall be reset at 
             power-on. The counters shall not be reset with a link state 
             transition and shall not be reset when read."
        REFERENCE   "ITU-T G.998.4, paragraph #11.4.1"
        ::= { zxAnXdsl2PMChHist1DayEntry 4 }
        
    zxAnXdsl2PMChHist1DayInpEfb  OBJECT-TYPE
        SYNTAX      Counter32
        UNITS       "bits"
        MAX-ACCESS  read-only
        STATUS      current
        DESCRIPTION
            "This is a counter counting the number of error-free bits passed 
             over the beta1-reference point, deivided by 2^16. Error-free bits 
             are bits originating from DTU's that have been detected to contain 
             on error at the moment of crossing the beta1-reference point.
             It is a 32-bit wrap-around counter. The counter shall be reset at 
             power-on. The counters shall not be reset with a link state 
             transition and shall not be reset when read."
        REFERENCE   "ITU-T G.998.4, paragraph #11.4.2"
        ::= { zxAnXdsl2PMChHist1DayEntry 5 }
        
    zxAnXdsl2PMChHist1DayInpMinEftr  OBJECT-TYPE
        SYNTAX      Counter32
        UNITS       "kbps"
        MAX-ACCESS  read-only
        STATUS      current
        DESCRIPTION
            "The performance monitoring parameter minimum error-free
             throughput(EFTR_min) is defined as the minimum of the EFTR 
             observed since the last reading of the EFTR_min via an EOC command 
             over the U-interface.
             The EFTR_min shall be measured in Showtime by the receiver.
             The valid values are all integers from 0 to the maximum of the 
             valid values of the maximum net data rate specified in the 
             associated Recommendation values.
             The performance monitoring parameter EFTR_min shall be represented 
             as a 32-bit unsigned integer expressing the value of EFTR_min in 
             kbps This data format supports a granularity of 1 kbps.
             The previous value of EFTR_min shall be reported in the EOC if no 
             EFTR measurement has been done since the last reading of EFTR_min."
        REFERENCE   "ITU-T G.998.4, paragraph #11.4.3"
        ::= { zxAnXdsl2PMChHist1DayEntry 6 }

--------------------------------------------------------------------------------
-- zxAnXdsl2SeltConfTable
--------------------------------------------------------------------------------

    zxAnXdsl2SeltConfTable  OBJECT-TYPE
       SYNTAX      SEQUENCE  OF  ZxAnXdsl2SeltConfEntry
       MAX-ACCESS  not-accessible
       STATUS      current
       DESCRIPTION
          "The table zxAnXdsl2SeltConfTable contains configuration parameters
           for SELT test. "
       ::= { zxAnXdsl2LineTest 1 }
    
    zxAnXdsl2SeltConfEntry  OBJECT-TYPE
       SYNTAX      ZxAnXdsl2SeltConfEntry
       MAX-ACCESS  not-accessible
       STATUS      current
       DESCRIPTION
          "The entry of zxAnXdsl2SeltConfTable."
       INDEX  { ifIndex }
       ::= { zxAnXdsl2SeltConfTable 1 }
    
    ZxAnXdsl2SeltConfEntry  ::=
       SEQUENCE {
          zxAnXdsl2LnSeltCmndConfLdsf              Xdsl2LineLdsf,
          zxAnXdsl2SeltUerMmd                      Unsigned32,   
          zxAnXdsl2SeltQlnMmd                      Unsigned32,      
          zxAnXdsl2SeltCece                        TruthValue,      
          zxAnXdsl2SeltCapSignalPsdDs              OCTET STRING,     
          zxAnXdsl2SeltCapSignalPsdUs              OCTET STRING,     
          zxAnXdsl2SeltCapNoisePsdDs               OCTET STRING,     
          zxAnXdsl2SeltCapNoisePsdUs               OCTET STRING,     
          zxAnXdsl2SeltCapTargetSnrmDs             Unsigned32,      
          zxAnXdsl2SeltCapTargetSnrmUs             Unsigned32,
          zxAnXdsl2SeltUerMeasureEnableC           Integer32,
          zxAnXdsl2SeltQlnMeasureEnableC           Integer32,
          zxAnXdsl2SeltCalibrateCmd                Xdsl2LineLdsf,
          zxAnXdsl2SeltRawDataCmd                  Xdsl2LineLdsf,
          zxAnXdsl2SeltQuickTestEnable             INTEGER
       }         
           
    zxAnXdsl2LnSeltCmndConfLdsf  OBJECT-TYPE
        SYNTAX      Xdsl2LineLdsf
        MAX-ACCESS  read-write
        STATUS      current
        DESCRIPTION
           "Command:Loop diagnostics mode forced (LDSF).  Defines whether the
            line should be forced into the loop diagnostics mode by the
            near-end xTU on this line or only be responsive to loop
            diagnostics initiated by the far-end xTU.
     
            This object MUST be maintained in a persistent manner.
            However, in case the operator forces loop diagnostics mode
            then the access node should reset the object (inhibit) when
            loop diagnostics mode procedures are completed."
        REFERENCE    "ITU-T G.997.1, paragraph #7.3.1.1.8"
        DEFVAL       { inhibit }
        ::= { zxAnXdsl2SeltConfEntry 1 }
                   
    zxAnXdsl2SeltUerMmd  OBJECT-TYPE
        SYNTAX      Unsigned32(5..240)        
        UNITS       "seconds"        
        MAX-ACCESS  read-write
        STATUS      current
        DESCRIPTION
           "SELT UER Maximum Measurement Duration.
            This parameter is the maximum allowed time for SELT Uncalibrated 
            Echo Response measurement, between the time of the start command 
            written by the SELT-PMD-ME, and the time the result is available 
            for read operation by SELT-PMD-ME."       
        ::= { zxAnXdsl2SeltConfEntry 2 }   
                    
    zxAnXdsl2SeltQlnMmd  OBJECT-TYPE
        SYNTAX      Unsigned32(1..240)        
        UNITS       "seconds"        
        MAX-ACCESS  read-write
        STATUS      current
        DESCRIPTION
           "SELT Quiet Line Noise Maximum Measurement Duration.
            This parameter is the maximum allowed time for SELT quiet line 
            noise measurement, between the time of the start command 
            written by the SELT-PMD-ME, and the time the result is 
            available for read operation by SELT-PMD-ME."
        ::= { zxAnXdsl2SeltConfEntry 3 }
                    
     zxAnXdsl2SeltCece  OBJECT-TYPE
        SYNTAX      TruthValue      
        MAX-ACCESS  read-write
        STATUS      current
        DESCRIPTION
        "Capacity Estimate Calculation Enabling.
         This parameter specifies if the SELT-P function shall perform the 
         Downstream capacity and Upstream capacity estimation, if supported."
        ::= { zxAnXdsl2SeltConfEntry 4 }
        
    zxAnXdsl2SeltCapSignalPsdDs  OBJECT-TYPE
        SYNTAX      OCTET STRING (SIZE(0..192))      
        MAX-ACCESS  read-write
        STATUS      current
        DESCRIPTION
           "Capacity Estimate Signal PSD Downstream.
            This configuration parameter defines the PSD template of the  
            transmit signal to be used in capacity estimate evaluation. 
            
            The parameter shall be a set of breakpoints that are represented 
            by [(t1, PSD1), (t2, PSD2), ..., (tN, PSDN)], each breakpoint 
            occupies 4 octets and consist of a frequency index tn(2 bytes) and 
            a signal PSD level(2 bytes).
            
            The range of valid values for index tn is 0 to 8191, and the range
            of valid values for PSD is 300 to 2000(units of -0.1dBm/Hz).
            
            The maximum number of breakpoints is 48."
        ::= { zxAnXdsl2SeltConfEntry 5 }
        
    zxAnXdsl2SeltCapSignalPsdUs  OBJECT-TYPE
        SYNTAX      OCTET STRING (SIZE(0..192))      
        MAX-ACCESS  read-write
        STATUS      current
        DESCRIPTION
           "Capacity Estimate Signal PSD Upstream.
            This configuration parameter defines the PSD template of the  
            transmit signal to be used in capacity estimate evaluation. 
            
            The parameter shall be a set of breakpoints that are represented 
            by [(t1, PSD1), (t2, PSD2), ..., (tN, PSDN)], each breakpoint 
            occupies 4 octets and consist of a frequency index tn(2 bytes) and 
            a signal PSD level(2 bytes).
            
            The range of valid values for index tn is 0 to 8191, and the range
            of valid values for PSD is 300 to 2000(units of -0.1dBm/Hz).
            
            The maximum number of breakpoints is 48."
        ::= { zxAnXdsl2SeltConfEntry 6 }
        
    zxAnXdsl2SeltCapNoisePsdDs  OBJECT-TYPE
        SYNTAX      OCTET STRING (SIZE(0..512))      
        MAX-ACCESS  read-write
        STATUS      current
        DESCRIPTION
           "Capacity Estimate Noise PSD Downstream.
            This configuration parameter defines the PSD template of the  
            transmit signal to be used in capacity estimate evaluation. 
            
            The parameter shall be a set of breakpoints that are represented 
            by [(t1, PSD1), (t2, PSD2), ..., (tN, PSDN)], each breakpoint 
            occupies 4 octets and consist of a frequency index tn(2 bytes) and 
            a signal PSD level(2 bytes).
            
            The range of valid values for index tn is 0 to 8191, and the range
            of valid values for PSD is 300 to 2000(units of -0.1dBm/Hz).
            
            The maximum number of breakpoints is 128."     
        ::= { zxAnXdsl2SeltConfEntry 7 }
        
    zxAnXdsl2SeltCapNoisePsdUs  OBJECT-TYPE
        SYNTAX      OCTET STRING (SIZE(0..512))      
        MAX-ACCESS  read-write
        STATUS      current
        DESCRIPTION
           "Capacity Estimate Noise PSD Upstream.
            This configuration parameter defines the PSD template of the  
            transmit signal to be used in capacity estimate evaluation. 
            
            The parameter shall be a set of breakpoints that are represented 
            by [(t1, PSD1), (t2, PSD2), ..., (tN, PSDN)], each breakpoint 
            occupies 4 octets and consist of a frequency index tn(2 bytes) and 
            a signal PSD level(2 bytes).
            
            The range of valid values for index tn is 0 to 8191, and the range
            of valid values for PSD is 300 to 2000(units of -0.1dBm/Hz).
            
            The maximum number of breakpoints is 128."     
        ::= { zxAnXdsl2SeltConfEntry 8 }        
            
    zxAnXdsl2SeltCapTargetSnrmDs  OBJECT-TYPE   
        SYNTAX      Unsigned32(0..310)       
        UNITS       "0.1dB"            
        MAX-ACCESS  read-write
        STATUS      current
        DESCRIPTION
           "Capacity Estimate Target Noise Margin Downstream.
            This is the Noise Margin to be used in capacity estimate evaluation,
            relative to a BER requirement of 1E-7."
        ::= { zxAnXdsl2SeltConfEntry 9 }
            
    zxAnXdsl2SeltCapTargetSnrmUs  OBJECT-TYPE   
        SYNTAX      Unsigned32(0..310)       
        UNITS       "0.1dB"            
        MAX-ACCESS  read-write
        STATUS      current
        DESCRIPTION
           "Capacity Estimate Target Noise Margin Upstream.
            This is the Noise Margin to be used in capacity estimate evaluation,
            relative to a BER requirement of 1E-7."
        ::= { zxAnXdsl2SeltConfEntry 10 }
  
   zxAnXdsl2SeltUerMeasureEnableC  OBJECT-TYPE
        SYNTAX      Integer32
        MAX-ACCESS  read-write
        STATUS      current
        DESCRIPTION
           "This parameter is a binary variable, where '1' triggers the CO 
            SELT PMD to start a UER measurement."
        REFERENCE    "ITU-T G.996.2, paragraph #A2.3.1"
        ::= { zxAnXdsl2SeltConfEntry 11 }
        
    zxAnXdsl2SeltQlnMeasureEnableC  OBJECT-TYPE
        SYNTAX      Integer32
        MAX-ACCESS  read-write
        STATUS      current
        DESCRIPTION
           "This parameter is a binary variable, where '1' triggers the CO 
            SELT PMD to start a QLN measurement."
        REFERENCE    "ITU-T G.996.2, paragraph #A2.3.2"
        ::= { zxAnXdsl2SeltConfEntry 12 }                 
     
    zxAnXdsl2SeltCalibrateCmd  OBJECT-TYPE
        SYNTAX      Xdsl2LineLdsf
        MAX-ACCESS  read-write
        STATUS      current
        DESCRIPTION
            "Execute this command to calibrate the parameter that is used to
             calculate the SELT result.
             When execute this command before SELT, the test result will be 
             more accurate."
        DEFVAL      { inhibit }
        ::= { zxAnXdsl2SeltConfEntry 13 } 
        
    zxAnXdsl2SeltRawDataCmd  OBJECT-TYPE
        SYNTAX      Xdsl2LineLdsf
        MAX-ACCESS  read-write
        STATUS      current
        DESCRIPTION
            "Defines whether the line should be forced into SELT raw data
             test mode."
        DEFVAL      { inhibit }
        ::= { zxAnXdsl2SeltConfEntry 14 }
        
    zxAnXdsl2SeltQuickTestEnable  OBJECT-TYPE
        SYNTAX      INTEGER
        {
            enabled(1),
            disabled(2)
        }
        MAX-ACCESS  read-write
        STATUS      current
        DESCRIPTION
            "Enable/disable the quick SELT test.
             enabled(1) - Start the SELT test with quick mode.
             disabled(2) - Start the SELT test with normal mode."
        DEFVAL  { disabled }
        ::= { zxAnXdsl2SeltConfEntry 15 }

--------------------------------------------------------------------------------
-- zxAnXdsl2SeltLineStatusTable
--------------------------------------------------------------------------------

    zxAnXdsl2SeltLineStatusTable  OBJECT-TYPE
       SYNTAX      SEQUENCE  OF  ZxAnXdsl2SeltLineStatusEntry
       MAX-ACCESS  not-accessible
       STATUS      current
       DESCRIPTION
          "The table zxAnXdsl2SeltLineStatusTable contains line status result 
          of SELT test. "
       ::= { zxAnXdsl2LineTest 2 }
    
    zxAnXdsl2SeltLineStatusEntry  OBJECT-TYPE
       SYNTAX      ZxAnXdsl2SeltLineStatusEntry
       MAX-ACCESS  not-accessible
       STATUS      current
       DESCRIPTION
          "The entry of zxAnXdsl2SeltLineStatusTable."
       INDEX  { ifIndex }
       ::= { zxAnXdsl2SeltLineStatusTable 1 }
    
    ZxAnXdsl2SeltLineStatusEntry  ::=
       SEQUENCE {          
          zxAnXdsl2SeltLoopTermStatus              INTEGER,                    
          zxAnXdsl2SeltLoopLength                  Unsigned32,      
          zxAnXdsl2SeltLoopTopology                OCTET STRING, 
          zxAnXdsl2SeltSplitterMissing             TruthValue,                 
          zxAnXdsl2SeltLineAtten                   OCTET STRING,
          zxAnXdsl2SeltCapacityDs                  Unsigned32,      
          zxAnXdsl2SeltCapacityUs                  Unsigned32,     
          zxAnXdsl2SeltUerScale                    Unsigned32,                 
          zxAnXdsl2SeltCerScale                    Unsigned32,
          zxAnXdsl2SeltTestStatus                  INTEGER,
          zxAnXdsl2SeltCapabilities                BITS,
          zxAnXdsl2SeltChipsetType                 INTEGER
       }         
           
    zxAnXdsl2SeltLoopTermStatus  OBJECT-TYPE        
        SYNTAX      INTEGER {
             open(1),
             short(2),
             poweredOnCPE(3),
             unknown(4)
        }
        MAX-ACCESS  read-only
        STATUS      current
        DESCRIPTION
           "Loop Termination Indicator is a state indication of the 
            loop termination."
        ::= { zxAnXdsl2SeltLineStatusEntry 1 }      
        
    zxAnXdsl2SeltLoopLength  OBJECT-TYPE        
        SYNTAX      Unsigned32(0..16383)
        MAX-ACCESS  read-only
        STATUS      current
        DESCRIPTION
           "This parameter is the physical length (in meters) of the loop
            between the U-C and the U-R interface.
            The loop length shall be measured with a granularity of 1 m, 
            with valid range of 0 to 16383 m."
        ::= { zxAnXdsl2SeltLineStatusEntry 2 }
        
    zxAnXdsl2SeltLoopTopology  OBJECT-TYPE        
        SYNTAX      OCTET STRING (SIZE(0..80))
        MAX-ACCESS  read-only
        STATUS      current
        DESCRIPTION
           "The Loop Topology without cable-type identification is consists of 
           a list of segments that are represented by (len1,gauge1,term1,bt1),
           (len2,gauge2,term2,bt2)...(lenN,gaugen,termn,btN).                
           
           Each segment occupies 5 octets in the following structure:
           Octets 0&1 -- Loop Segment Length
           Octets 2   -- Loop Segment Gauge.                            
           Octets 3   -- Loop Segment Termination Type.   
           Octets 4   -- Loop Segment Bridged Tap Indicator.     
           
           The range of valid values for length is 0 to 16383.
           The valid value for gauge is 1(PE04),2(PE05),3(Unknown).
           The valid value for termination type is 1(open),2(short),3(balanced),
           4(unknown).
           The valid value for indicator is 1(bridged tap, branching) or 
           2(not a bridged tap, in series).
           
           The maximum number of segments is 16."
        ::= { zxAnXdsl2SeltLineStatusEntry 3 }
        
    zxAnXdsl2SeltSplitterMissing  OBJECT-TYPE        
        SYNTAX      TruthValue
        MAX-ACCESS  read-only
        STATUS      current
        DESCRIPTION
           "This parameter is a indication of a missing or incorrectly 
           installed splitter or micro-filter at the U-R reference point.
           
           The value of true means missing splitter or micro-filter."
        ::= { zxAnXdsl2SeltLineStatusEntry 4 }        
        
    zxAnXdsl2SeltLineAtten  OBJECT-TYPE     
        SYNTAX      OCTET STRING (SIZE(0..16384))
        MAX-ACCESS  read-only
        STATUS      current
        DESCRIPTION
           "The line attenuation TFlog(f) is the logarithmic power transfer
            function of the line as a function of frequency when both the 
            near-end and far-end line terminations have the following values: 
            Source impedance = purely resistive equal to 100 Ohm.
            Termination impedance = purely resistive equal to 100 Ohm.
            
            The function TFlog(f) consists of an array of values TFlog(i X Df),
            with Df = 4.3125 kHz independent of the sub-carrier spacing used 
            for the XDSL DMT modulation.
            
            This parameter shall be a set of breakpoints that are represented 
            by [(t1, TFlog1), (t2, TFlog2), ..., (tN, TFlogN, each breakpoint 
            occupies 4 octets and consist of a index tn(2 bytes) and a TFlog 
            value(2 bytes).            
            
            The range of valid values for the index i is 0 to 8191. 
            The range of valid values for TFlog(i X Df) is from 60 down to
            -962(units of 0.1 dB), so those two bytes are signed value. 
            
            0x0FFFFF is used to indicate that no measurement could be done
            for this subcarrier because the attenuation is out of range 
            that can be represented."
        ::= { zxAnXdsl2SeltLineStatusEntry 5 }        
        
    zxAnXdsl2SeltCapacityDs  OBJECT-TYPE        
        SYNTAX      Unsigned32(0..200000)
        UNITS       "kbps"   
        MAX-ACCESS  read-only
        STATUS      current
        DESCRIPTION
           "This parameter represents a best-effort estimate of the achievable
            downstream data rate (in kbit/s) on the loop under test."
        ::= { zxAnXdsl2SeltLineStatusEntry 6 }
        
    zxAnXdsl2SeltCapacityUs  OBJECT-TYPE        
        SYNTAX      Unsigned32(0..200000)
        UNITS       "kbps"   
        MAX-ACCESS  read-only
        STATUS      current
        DESCRIPTION
           "This parameter represents a best-effort estimate of the achievable
            upstream data rate (in kbit/s) on the loop under test."
        ::= { zxAnXdsl2SeltLineStatusEntry 7 }
        
    zxAnXdsl2SeltUerScale  OBJECT-TYPE        
        SYNTAX      Unsigned32
        MAX-ACCESS  read-only
        STATUS      current
        DESCRIPTION
           "The scale factor for SELT Uncalibrated Echo Response, it shall be
            coded as a 32 bit unsigned integer."
        ::= { zxAnXdsl2SeltLineStatusEntry 8 }
        
    zxAnXdsl2SeltCerScale  OBJECT-TYPE        
        SYNTAX      Unsigned32
        MAX-ACCESS  read-only
        STATUS      deprecated
        DESCRIPTION
           "The scale factor for SELT Calibrated Echo Response, it shall be
            coded as a 32 bit unsigned integer."
        ::= { zxAnXdsl2SeltLineStatusEntry 9 }
   
    zxAnXdsl2SeltTestStatus  OBJECT-TYPE
        SYNTAX      INTEGER
        {
            none(1),
            success(2),
            inProgress(3),
            unsupported(4),
            cannotRun(5),
            aborted(6),
            failed(7),
            illegalMode(8),
            noResources(9),
            online(10),
            parallelOverLimit(11),
            showtime(12)
        }
        MAX-ACCESS  read-only
        STATUS      current
        DESCRIPTION
            "Possible failure reasons associated with performing Single Ended
             Loop Test (SELT) on a DSL line.
             Possible values are:
             none          (1) - The default value in case LDSF was never
                                 requested for the associated line.
             success       (2) - The recent command completed
                                 successfully.
             inProgress    (3) - The Loop Diagnostics process is in
                                 progress.
             unsupported   (4) - The NE or the line card doesn't support
                                 LDSF.
             cannotRun     (5) - The NE cannot initiate the command, due
                                 to a non specific reason.
             aborted       (6) - The Loop Diagnostics process aborted.
             failed        (7) - The Loop Diagnostics process failed.
             illegalMode   (8) - The NE cannot initiate the command, due
                                 to the specific mode of the relevant
                                 line.
             noResources   (9) - The NE cannot initiate the command, due
                                 to lack of internal memory resources.
             online        (10)- The CPE is online but not in showtime status.
             parallelOverLimit (11)- The number of parallel tests has reached 
                                 the upper limit.
             showtime      (12)- The CPE is in showtime status."
        ::= { zxAnXdsl2SeltLineStatusEntry 10 } 
        
    zxAnXdsl2SeltCapabilities  OBJECT-TYPE     
        SYNTAX      BITS
        {
            supportRawDataTest(0),
            supportCalibrate(1)
        }
        MAX-ACCESS  read-only
        STATUS      current
        DESCRIPTION
            "The management capabilities of VDSL card.
             bit 0: value 1 means support zxAnXdsl2SeltRawDataCmd.
             bit 1: value 1 means support zxAnXdsl2SeltCalibrateCmd."
        ::= { zxAnXdsl2SeltLineStatusEntry 11 }
    
    zxAnXdsl2SeltChipsetType  OBJECT-TYPE
        SYNTAX      INTEGER
        {
            lantiq(1),
            bcm(2)
        }
        MAX-ACCESS  read-only
        STATUS      current
        DESCRIPTION
            "Chipset type.
             Possible values are:
             lantiq    (1) - Use LANTIQ chipset.
             bcm       (2) - Use BCM chipset."
        ::= { zxAnXdsl2SeltLineStatusEntry 12 }
        
--------------------------------------------------------------------------------
-- zxAnXdsl2SeltSCStatusTable
--------------------------------------------------------------------------------

    zxAnXdsl2SeltSCStatusTable  OBJECT-TYPE
       SYNTAX      SEQUENCE  OF  ZxAnXdsl2SeltSCStatusEntry
       MAX-ACCESS  not-accessible
       STATUS      current
       DESCRIPTION
          "The table zxAnXdsl2SeltSCStatusTable contains subcarrier status
           result of SELT test. "
       ::= { zxAnXdsl2LineTest 3 }
    
    zxAnXdsl2SeltSCStatusEntry  OBJECT-TYPE
       SYNTAX      ZxAnXdsl2SeltSCStatusEntry
       MAX-ACCESS  not-accessible
       STATUS      current
       DESCRIPTION
          "The entry of zxAnXdsl2SeltSCStatusTable."
       INDEX  { ifIndex, xdsl2SCStatusDirection, xdsl2SCStatusSegment }
       ::= { zxAnXdsl2SeltSCStatusTable 1 }
    
    ZxAnXdsl2SeltSCStatusEntry  ::=
       SEQUENCE {                    
          zxAnXdsl2SeltUerReal              OCTET STRING,
          zxAnXdsl2SeltUerImg               OCTET STRING,
          zxAnXdsl2SeltVuer                 OCTET STRING,
          zxAnXdsl2SeltQln                  OCTET STRING,
          zxAnXdsl2SeltCerReal              OCTET STRING,
          zxAnXdsl2SeltCerImg               OCTET STRING
       }         
           
    zxAnXdsl2SeltUerReal  OBJECT-TYPE        
        SYNTAX      OCTET STRING (SIZE(0..2048))
        MAX-ACCESS  read-only
        STATUS      current
        DESCRIPTION
           "The Uncalibrated Echo Response UER(i* UER_G*Df), shall be 
           represented in linear format by a scale factor and a normalized
           complex number a(i)+j*b(i), where i is a frequency index i ranging
           from 0 to NSC-1 and where Df = 4.3125kHz and (NSC-1) X UER_G X Df 
           is the highest frequency supported by the SELT-PMD functionality.
           
           This parameter is the real part(a) value, and each four bytes has 
           a value of -2^31 to 2^31-1 for one real part(a) value."     
        ::= { zxAnXdsl2SeltSCStatusEntry 1 }              

    zxAnXdsl2SeltUerImg  OBJECT-TYPE        
        SYNTAX      OCTET STRING (SIZE(0..2048))
        MAX-ACCESS  read-only
        STATUS      current
        DESCRIPTION
           "The Uncalibrated Echo Response UER(i* UER_G*Df), shall be 
           represented in linear format by a scale factor and a normalized
           complex number a(i)+j*b(i), where i is a frequency index i ranging
           from 0 to NSC-1 and where Df = 4.3125kHz and (NSC-1) X UER_G X Df 
           is the highest frequency supported by the SELT-PMD functionality.
           
           This parameter is the image part(b) value, and each four bytes has 
           a value of -2^31 to 2^31 for one image part(b) value."     
        ::= { zxAnXdsl2SeltSCStatusEntry 2 }          
          
    zxAnXdsl2SeltVuer  OBJECT-TYPE        
        SYNTAX      OCTET STRING (SIZE(0..512))
        MAX-ACCESS  read-only
        STATUS      current
        DESCRIPTION
           "SELT Variance of Uncalibrated Echo Response.
           
           The REL_VAR_UER(f) provides the relative variance of the 
           uncalibrated echo response by the SELT-PMD function  for each
           frequency i X UER_G X Df where i ranges from 0 to NSC - 1 with
           and where Df = 4.3125kHz  and (NSC-1) X UER_G X Df is the highest
           frequency supported by the SELT-PMD functionality.           
           
           The relative variance of the uncalibrated echo response 
           REL_VAR_UER(iX UER_G XDf)shall be represented as an 8-bit unsigned 
           integer v(i), where i is the subcarrier index i = 0 to NSC - 1. 
           The value of  REL_VAR_UER(iX UER_G XDf) shall be defined as 
           REL_VAR_UER(iX UER_G XDf) = +3 - v(i)/2  dB. 
           
           This parameter is the v(i) value and each byte is an 8-bit unsigned
           integer in the range 0 to 254."     
        ::= { zxAnXdsl2SeltSCStatusEntry 3 }     
        
    zxAnXdsl2SeltQln  OBJECT-TYPE        
        SYNTAX      OCTET STRING (SIZE(0..512))
        MAX-ACCESS  read-only
        STATUS      current
        DESCRIPTION
           "The SELT Quiet Line noise provides the quiet line noise PSD as 
           measured by the SELT-PMD function (see #A.1.1.2) for each 
           sub-carrier frequency  i X SELTQLN_G X Df where i ranges from 
           0 to NSC - 1 with and where  Df = 4.3125kHz  and 
           (NSC-1) X SELTQLN_G X Df is the highest frequency supported by 
           the SELT-PMD functionality.           
                                 
           The SELT quiet line noise SELTQLN(i X SELTQLN_G X Df) shall be 
           represented as an 8 bit unsigned integer n(i), where i is the 
           subcarrier index i = 0 to NSC - 1. 
           
           The value of SELTQLN(i X SELTQLN_G X Df ) shall be defined as 
           SELTQLN(i X SELTQLN_G X Df ) = -23 - (n(i)/2) dBm/Hz."     
        ::= { zxAnXdsl2SeltSCStatusEntry 4 }     
        
    zxAnXdsl2SeltCerReal  OBJECT-TYPE        
        SYNTAX      OCTET STRING (SIZE(0..1024))
        MAX-ACCESS  read-only
        STATUS      deprecated
        DESCRIPTION
           "The Calibrated Echo Response UER(i* UER_G*Df), shall be 
           represented in linear format by a scale factor and a normalized
           complex number a(i)+j*b(i), where i is a frequency index i ranging
           from 0 to NSC-1 and where Df = 4.3125kHz and (NSC-1) X UER_G X Df 
           is the highest frequency supported by the SELT-PMD functionality.
           
           This parameter is the real part(a) value, and each two bytes has 
           a value of -2^15+1 to 2^15-1 for one real part(a) value."     
        ::= { zxAnXdsl2SeltSCStatusEntry 5 }              

    zxAnXdsl2SeltCerImg  OBJECT-TYPE        
        SYNTAX      OCTET STRING (SIZE(0..1024))
        MAX-ACCESS  read-only
        STATUS      deprecated
        DESCRIPTION
           "The Calibrated Echo Response UER(i* UER_G*Df), shall be 
           represented in linear format by a scale factor and a normalized
           complex number a(i)+j*b(i), where i is a frequency index i ranging
           from 0 to NSC-1 and where Df = 4.3125kHz and (NSC-1) X UER_G X Df 
           is the highest frequency supported by the SELT-PMD functionality.
           
           This parameter is the image part(b) value, and each two bytes has 
           a value of -2^15+1 to 2^15-1 for one image part(b) value."     
        ::= { zxAnXdsl2SeltSCStatusEntry 6 }                 
                
--------------------------------------------------------------------------------
-- zxAnXdsl2MeltConfTable
--------------------------------------------------------------------------------

    zxAnXdsl2MeltConfTable  OBJECT-TYPE
       SYNTAX      SEQUENCE  OF  ZxAnXdsl2MeltConfEntry
       MAX-ACCESS  not-accessible
       STATUS      current
       DESCRIPTION
          "The metallic line testing configuration table.
           This table describes specifications for metallic line testing (MELT) 
           configuration."
       ::= { zxAnXdsl2LineTest 4 }
       
    zxAnXdsl2MeltConfEntry  OBJECT-TYPE
       SYNTAX      ZxAnXdsl2MeltConfEntry
       MAX-ACCESS  not-accessible
       STATUS      current
       DESCRIPTION
          "The metallic line testing configuration entry."
       INDEX  { ifIndex }
       ::= { zxAnXdsl2MeltConfTable 1 }
    
    ZxAnXdsl2MeltConfEntry  ::=
       SEQUENCE {
          zxAnXdsl2MeltCmndConfLdsf         INTEGER,
          zxAnXdsl2MeltPeakMetallicVtr      Integer32,
          zxAnXdsl2MeltMaxFarendConductVtr  Integer32,
          zxAnXdsl2MeltMinFarendConductVtr  Integer32,
          zxAnXdsl2MeltPairIdToneCmd        INTEGER,
          zxAnXdsl2MeltPairIdToneFreq       Integer32,
          zxAnXdsl2MeltWettingCurrentCmd    INTEGER
       }
       
    zxAnXdsl2MeltCmndConfLdsf  OBJECT-TYPE
        SYNTAX      INTEGER
            {
                all         (1), 
                resistance  (2),
                capacitance (3),
                voltage     (4),
                current     (5),
                frequency   (6),
                admittance  (7),
                ppa         (8)
            }
        MAX-ACCESS  read-write
        STATUS      current
        DESCRIPTION
           "This object indicates which kind of measurements is to be done."
        DEFVAL { all }
        ::= { zxAnXdsl2MeltConfEntry 1 }
        
    zxAnXdsl2MeltPeakMetallicVtr  OBJECT-TYPE
        SYNTAX      Integer32(0..100)
        UNITS       "V"
        MAX-ACCESS  read-write
        STATUS      current
        DESCRIPTION
           "Peak metallic voltage between tip and ring."
        ::= { zxAnXdsl2MeltConfEntry 2 }
        
    zxAnXdsl2MeltMaxFarendConductVtr  OBJECT-TYPE
        SYNTAX      Integer32(0..500)
        UNITS       "0.1 V"
        MAX-ACCESS  read-write
        STATUS      current
        DESCRIPTION
           "Maximum far-end signature conduction voltage."
        ::= { zxAnXdsl2MeltConfEntry 3 }
        
    zxAnXdsl2MeltMinFarendConductVtr  OBJECT-TYPE
        SYNTAX      Integer32(0..500)
        UNITS       "0.1 V"
        MAX-ACCESS  read-write
        STATUS      current
        DESCRIPTION
           "Minimum far-end signature conduction voltage."
        ::= { zxAnXdsl2MeltConfEntry 4 }
        
    zxAnXdsl2MeltPairIdToneCmd  OBJECT-TYPE
        SYNTAX      INTEGER
        {
            start(1),
            stop(2)
        }
        MAX-ACCESS  read-write
        STATUS      current
        DESCRIPTION
            "Start/stop the pair identification tone generation."
        ::= { zxAnXdsl2MeltConfEntry 5 }
    
    zxAnXdsl2MeltPairIdToneFreq  OBJECT-TYPE
        SYNTAX      Integer32(300..3400)
        UNITS       "Hz"
        MAX-ACCESS  read-write
        STATUS      current
        DESCRIPTION
            "This parameter sets up frequency of the pair identification tone"
        REFERENCE   "ITU-T G.996.2 #E.2.1.4"
        ::= { zxAnXdsl2MeltConfEntry 6 }
        
    zxAnXdsl2MeltWettingCurrentCmd  OBJECT-TYPE
        SYNTAX      INTEGER
        {
            start(1),
            stop(2)
        }
        MAX-ACCESS  read-write
        STATUS      current
        DESCRIPTION
            "Start/stop a wetting current to prevent contact oxidation on the
             subscriber line."
        ::= { zxAnXdsl2MeltConfEntry 7 }

--------------------------------------------------------------------------------
-- zxAnXdsl2MeltStatusTable
--------------------------------------------------------------------------------

    zxAnXdsl2MeltStatusTable  OBJECT-TYPE
       SYNTAX      SEQUENCE  OF  ZxAnXdsl2MeltStatusEntry
       MAX-ACCESS  not-accessible
       STATUS      current
       DESCRIPTION
          "The metallic line testing status table.
           This table describes specifications for metallic line testing (MELT) 
           status."
       ::= { zxAnXdsl2LineTest 5 }
       
    zxAnXdsl2MeltStatusEntry  OBJECT-TYPE
       SYNTAX      ZxAnXdsl2MeltStatusEntry
       MAX-ACCESS  not-accessible
       STATUS      current
       DESCRIPTION
          "The metallic line testing status entry.
           Mib format: zxAnXdsl2Melt[Ac/Dc][A/R/C/V/F/G/B][tg/rg/tr/rt]."
       INDEX  { ifIndex }
       ::= { zxAnXdsl2MeltStatusTable 1 }
    
    ZxAnXdsl2MeltStatusEntry  ::=
       SEQUENCE {
          zxAnXdsl2MeltLdsfResult           Xdsl2LdsfResult,
          zxAnXdsl2MeltDcAtg                Integer32,
          zxAnXdsl2MeltDcArg                Integer32,
          zxAnXdsl2MeltAcAtg                Integer32,
          zxAnXdsl2MeltAcArg                Integer32,
          zxAnXdsl2MeltDcRtr                Integer32,
          zxAnXdsl2MeltDcRrt                Integer32,
          zxAnXdsl2MeltDcRtg                Integer32,
          zxAnXdsl2MeltDcRrg                Integer32,
          zxAnXdsl2MeltCtr                  Integer32,
          zxAnXdsl2MeltCtg                  Integer32,
          zxAnXdsl2MeltCrg                  Integer32,
          zxAnXdsl2MeltDcVtr                Integer32,
          zxAnXdsl2MeltDcVtg                Integer32,
          zxAnXdsl2MeltDcVrg                Integer32,
          zxAnXdsl2MeltAcVtr                Integer32,
          zxAnXdsl2MeltAcVtg                Integer32,
          zxAnXdsl2MeltAcVrg                Integer32,
          zxAnXdsl2MeltAcFtr                Integer32,
          zxAnXdsl2MeltAcFtg                Integer32,
          zxAnXdsl2MeltAcFrg                Integer32,
          zxAnXdsl2MeltGtr                  Integer32,
          zxAnXdsl2MeltBtr                  Integer32,
          zxAnXdsl2MeltGtg                  Integer32,
          zxAnXdsl2MeltBtg                  Integer32,
          zxAnXdsl2MeltGrg                  Integer32,
          zxAnXdsl2MeltBrg                  Integer32,
          zxAnXdsl2MeltPpaResistance        Integer32
       }
        
    zxAnXdsl2MeltLdsfResult         OBJECT-TYPE
        SYNTAX      Xdsl2LdsfResult
        MAX-ACCESS  read-only
        STATUS      current
        DESCRIPTION
           "The status of the recent occasion the loop diagnostics mode
            forced (LDSF) was issued for the associated line.  Possible
            values are:
               none        (1) - The default value in case LDSF was never
                                 requested for the associated line.
               success     (2) - The recent command completed
                                 successfully.
               inProgress  (3) - The Loop Diagnostics process is in
                                 progress.
               unsupported (4) - The NE or the line card doesn't support
                                 LDSF.
               cannotRun   (5) - The NE cannot initiate the command, due
                                 to a non specific reason.
               aborted     (6) - The Loop Diagnostics process aborted.
               failed      (7) - The Loop Diagnostics process failed.
               illegalMode (8) - The NE cannot initiate the command, due
                                 to the specific mode of the relevant
                                 line.
               adminUp     (9) - The NE cannot initiate the command, as
                                 the relevant line is administratively
                                 'Up'.
               tableFull   (10)- The NE cannot initiate the command, due
                                 to reaching the maximum number of rows
                                 in the results table.
               noResources (11)- The NE cannot initiate the command, due
                                 to lack of internal memory resources."
        DEFVAL       { none }
        ::= { zxAnXdsl2MeltStatusEntry 1 }
        
    zxAnXdsl2MeltDcAtg  OBJECT-TYPE
        SYNTAX      Integer32
        UNITS       "0.1 uA"
        MAX-ACCESS  read-only
        STATUS      current
        DESCRIPTION
           "DC current between tip and ground."
        ::= { zxAnXdsl2MeltStatusEntry 2 }
        
    zxAnXdsl2MeltDcArg  OBJECT-TYPE
        SYNTAX      Integer32
        UNITS       "0.1 uA"
        MAX-ACCESS  read-only
        STATUS      current
        DESCRIPTION
           "DC current between ring and ground."
        ::= { zxAnXdsl2MeltStatusEntry 3 }
        
    zxAnXdsl2MeltAcAtg  OBJECT-TYPE
        SYNTAX      Integer32
        UNITS       "0.1 uA"
        MAX-ACCESS  read-only
        STATUS      current
        DESCRIPTION
           "AC current between tip and ground."
        ::= { zxAnXdsl2MeltStatusEntry 4 }
        
    zxAnXdsl2MeltAcArg  OBJECT-TYPE
        SYNTAX      Integer32
        UNITS       "0.1 uA"
        MAX-ACCESS  read-only
        STATUS      current
        DESCRIPTION
           "AC current between ring and ground."
        ::= { zxAnXdsl2MeltStatusEntry 5 }
    
    zxAnXdsl2MeltDcRtr  OBJECT-TYPE
        SYNTAX      Integer32
        UNITS       "ohm"
        MAX-ACCESS  read-only
        STATUS      current
        DESCRIPTION
           "DC resistance between tip and ring."
        ::= { zxAnXdsl2MeltStatusEntry 6 }
        
    zxAnXdsl2MeltDcRrt  OBJECT-TYPE
        SYNTAX      Integer32
        UNITS       "ohm"
        MAX-ACCESS  read-only
        STATUS      current
        DESCRIPTION
           "DC resistance between ring and tip."
        ::= { zxAnXdsl2MeltStatusEntry 7 }
        
    zxAnXdsl2MeltDcRtg  OBJECT-TYPE
        SYNTAX      Integer32
        UNITS       "ohm"
        MAX-ACCESS  read-only
        STATUS      current
        DESCRIPTION
           "DC resistance between tip and ground."
        ::= { zxAnXdsl2MeltStatusEntry 8 }
        
    zxAnXdsl2MeltDcRrg  OBJECT-TYPE
        SYNTAX      Integer32
        UNITS       "ohm"
        MAX-ACCESS  read-only
        STATUS      current
        DESCRIPTION
           "DC resistance between ring and ground."
        ::= { zxAnXdsl2MeltStatusEntry 9 }
        
    zxAnXdsl2MeltCtr  OBJECT-TYPE
        SYNTAX      Integer32
        UNITS       "0.1 nF"
        MAX-ACCESS  read-only
        STATUS      current
        DESCRIPTION
           "Capacitance between tip and ring."
        ::= { zxAnXdsl2MeltStatusEntry 10 }
        
    zxAnXdsl2MeltCtg  OBJECT-TYPE
        SYNTAX      Integer32
        UNITS       "0.1 nF"
        MAX-ACCESS  read-only
        STATUS      current
        DESCRIPTION
           "Capacitance between tip and ground."
        ::= { zxAnXdsl2MeltStatusEntry 11 }
        
    zxAnXdsl2MeltCrg  OBJECT-TYPE
        SYNTAX      Integer32
        UNITS       "0.1 nF"
        MAX-ACCESS  read-only
        STATUS      current
        DESCRIPTION
           "Capacitance between ring and ground."
        ::= { zxAnXdsl2MeltStatusEntry 12 }
        
    zxAnXdsl2MeltDcVtr  OBJECT-TYPE
        SYNTAX      Integer32
        UNITS       "100 mV"
        MAX-ACCESS  read-only
        STATUS      current
        DESCRIPTION
           "Foreign DC voltage between tip and ring."
        ::= { zxAnXdsl2MeltStatusEntry 13 }
        
    zxAnXdsl2MeltDcVtg  OBJECT-TYPE
        SYNTAX      Integer32
        UNITS       "100 mV"
        MAX-ACCESS  read-only
        STATUS      current
        DESCRIPTION
           "Foreign DC voltage between tip and ground."
        ::= { zxAnXdsl2MeltStatusEntry 14 }
        
    zxAnXdsl2MeltDcVrg  OBJECT-TYPE
        SYNTAX      Integer32
        UNITS       "100 mV"
        MAX-ACCESS  read-only
        STATUS      current
        DESCRIPTION
           "Foreign DC voltage between ring and ground."
        ::= { zxAnXdsl2MeltStatusEntry 15 }
        
    zxAnXdsl2MeltAcVtr  OBJECT-TYPE
        SYNTAX      Integer32
        UNITS       "100 mV"
        MAX-ACCESS  read-only
        STATUS      current
        DESCRIPTION
           "Foreign AC root mean square (RMS) voltage between tip and ring."
        ::= { zxAnXdsl2MeltStatusEntry 16 }
        
    zxAnXdsl2MeltAcVtg  OBJECT-TYPE
        SYNTAX      Integer32
        UNITS       "100 mV"
        MAX-ACCESS  read-only
        STATUS      current
        DESCRIPTION
           "Foreign AC root mean square (RMS) voltage between tip and ground."
        ::= { zxAnXdsl2MeltStatusEntry 17 }
        
    zxAnXdsl2MeltAcVrg  OBJECT-TYPE
        SYNTAX      Integer32
        UNITS       "100 mV"
        MAX-ACCESS  read-only
        STATUS      current
        DESCRIPTION
           "Foreign AC root mean square (RMS) voltage between ring and ground."
        ::= { zxAnXdsl2MeltStatusEntry 18 }
        
    zxAnXdsl2MeltAcFtr  OBJECT-TYPE
        SYNTAX      Integer32
        UNITS       "0.1 Hz"
        MAX-ACCESS  read-only
        STATUS      current
        DESCRIPTION
           "Foreign AC voltage frequency between tip and ring."
        ::= { zxAnXdsl2MeltStatusEntry 19 }
        
    zxAnXdsl2MeltAcFtg  OBJECT-TYPE
        SYNTAX      Integer32
        UNITS       "0.1 Hz"
        MAX-ACCESS  read-only
        STATUS      current
        DESCRIPTION
           "Foreign AC voltage frequency between tip and ground."
        ::= { zxAnXdsl2MeltStatusEntry 20 }
        
    zxAnXdsl2MeltAcFrg  OBJECT-TYPE
        SYNTAX      Integer32
        UNITS       "0.1 Hz"
        MAX-ACCESS  read-only
        STATUS      current
        DESCRIPTION
           "Foreign AC voltage frequency between ring and ground."
        ::= { zxAnXdsl2MeltStatusEntry 21 }
        
    zxAnXdsl2MeltGtr  OBJECT-TYPE
        SYNTAX      Integer32
        UNITS       "0.1 microseconds"
        MAX-ACCESS  read-only
        STATUS      current
        DESCRIPTION
           "Conductance between tip and ring."
        ::= { zxAnXdsl2MeltStatusEntry 22 }
        
    zxAnXdsl2MeltBtr  OBJECT-TYPE
        SYNTAX      Integer32
        UNITS       "0.1 microseconds"
        MAX-ACCESS  read-only
        STATUS      current
        DESCRIPTION
           "Susceptance between tip and ring."
        ::= { zxAnXdsl2MeltStatusEntry 23 }
        
    zxAnXdsl2MeltGtg  OBJECT-TYPE
        SYNTAX      Integer32
        UNITS       "0.1 microseconds"
        MAX-ACCESS  read-only
        STATUS      current
        DESCRIPTION
           "Conductance between tip and ground."
        ::= { zxAnXdsl2MeltStatusEntry 24 }
        
    zxAnXdsl2MeltBtg  OBJECT-TYPE
        SYNTAX      Integer32
        UNITS       "0.1 microseconds"
        MAX-ACCESS  read-only
        STATUS      current
        DESCRIPTION
           "Susceptance between tip and ground."
        ::= { zxAnXdsl2MeltStatusEntry 25 }
        
    zxAnXdsl2MeltGrg  OBJECT-TYPE
        SYNTAX      Integer32
        UNITS       "0.1 microseconds"
        MAX-ACCESS  read-only
        STATUS      current
        DESCRIPTION
           "Conductance between ring and ground."
        ::= { zxAnXdsl2MeltStatusEntry 26 }
        
    zxAnXdsl2MeltBrg  OBJECT-TYPE
        SYNTAX      Integer32
        UNITS       "0.1 microseconds"
        MAX-ACCESS  read-only
        STATUS      current
        DESCRIPTION
           "Susceptance between ring and ground."
        ::= { zxAnXdsl2MeltStatusEntry 27 }
        
    zxAnXdsl2MeltPpaResistance  OBJECT-TYPE
        SYNTAX      Integer32
        UNITS       "ohm"
        MAX-ACCESS  read-only
        STATUS      current
        DESCRIPTION
           "This object contains the resistance of a detectd PPA(Passive Test
            Termination).
            0xFFFFFFFF means that is unsupported."
        ::= { zxAnXdsl2MeltStatusEntry 28 }

--------------------------------------------------------------------------------
-- zxAnXdsl2SeltRawDataTable
--------------------------------------------------------------------------------

    zxAnXdsl2SeltRawDataTable  OBJECT-TYPE
        SYNTAX      SEQUENCE  OF  ZxAnXdsl2SeltRawDataEntry
        MAX-ACCESS  not-accessible
        STATUS      current
        DESCRIPTION
           "This table describes the result of SELT raw data test."
        ::= { zxAnXdsl2LineTest 6 }
       
    zxAnXdsl2SeltRawDataEntry  OBJECT-TYPE
        SYNTAX      ZxAnXdsl2SeltRawDataEntry
        MAX-ACCESS  not-accessible
        STATUS      current
        DESCRIPTION
           "The SELT raw data entry."
        INDEX  { ifIndex,zxAnXdsl2RawDataSegment }
        ::= { zxAnXdsl2SeltRawDataTable 1 }
    
    ZxAnXdsl2SeltRawDataEntry  ::=
        SEQUENCE {
           zxAnXdsl2RawDataSegment     Integer32,
           zxAnXdsl2SeltRawData        OCTET STRING
        }
       
    zxAnXdsl2RawDataSegment  OBJECT-TYPE
        SYNTAX      Integer32
        MAX-ACCESS  not-accessible
        STATUS      current
        DESCRIPTION
            "An index for the array of raw data SELT result."
        ::= { zxAnXdsl2SeltRawDataEntry 1 }
    
    zxAnXdsl2SeltRawData  OBJECT-TYPE
        SYNTAX      OCTET STRING (SIZE(0..1024))
        MAX-ACCESS  read-only
        STATUS      current
        DESCRIPTION
            "The raw data test result shall be stored and reported 
             to the management entity for the further calculation 
             and analysis. ALL the datas were divided into several 
             1KB packet and transmited a packet at a time."
        ::= { zxAnXdsl2SeltRawDataEntry 2 }
        
--------------------------------------------------------------------------------
-- zxAnXdsl2FextCoefficientTable
--------------------------------------------------------------------------------
    
    zxAnXdsl2VectoringGlobalObjects  
        OBJECT IDENTIFIER  ::= {zxAnXdsl2Vectoring 1}    
        
    zxAnXdsl2VectorTrackingEnable  OBJECT-TYPE 
        SYNTAX      INTEGER
            {
                enabled(1),
                disabled(2)
            }
        MAX-ACCESS  read-write
        STATUS      current
        DESCRIPTION
            "Enable/disable vectoring tracking.
             enabled(1) - Update the channel matrix automatically.
             disabled(2)- Update the channel matrix when link is up or down.
            "
        DEFVAL  { enabled }
        ::=  {  zxAnXdsl2VectoringGlobalObjects  1  }
    
    zxAnXdsl2FextCoefficientTable  OBJECT-TYPE
        SYNTAX      SEQUENCE  OF  ZxAnXdsl2FextCoefficientEntry
        MAX-ACCESS  not-accessible
        STATUS      current
        DESCRIPTION
            "The FEXT coefficient table."
        ::= { zxAnXdsl2Vectoring 2 }
       
    zxAnXdsl2FextCoefficientEntry  OBJECT-TYPE
        SYNTAX      ZxAnXdsl2FextCoefficientEntry
        MAX-ACCESS  not-accessible
        STATUS      current
        DESCRIPTION
            "The FEXT coefficient entry."
        INDEX  
        { 
            zxAnXdsl2FextSrcIfIndex,
            zxAnXdsl2FextDstIfIndex
        }
        ::= { zxAnXdsl2FextCoefficientTable 1 }
    
    ZxAnXdsl2FextCoefficientEntry  ::=
        SEQUENCE {
            zxAnXdsl2FextSrcIfIndex         ZxAnIfindex,
            zxAnXdsl2FextDstIfIndex         ZxAnIfindex,
            zxAnXdsl2FextCoefficientDs      OCTET STRING,
            zxAnXdsl2FextCoefficientUs      OCTET STRING
        }
    
    zxAnXdsl2FextSrcIfIndex  OBJECT-TYPE
        SYNTAX      ZxAnIfindex
        MAX-ACCESS  not-accessible
        STATUS      current
        DESCRIPTION
            "An index for a FEXT source port."
        ::= { zxAnXdsl2FextCoefficientEntry 1 }
    
    zxAnXdsl2FextDstIfIndex  OBJECT-TYPE
        SYNTAX      ZxAnIfindex
        MAX-ACCESS  not-accessible
        STATUS      current
        DESCRIPTION
            "An index for a FEXT destination port."
        ::= { zxAnXdsl2FextCoefficientEntry 2 }
    
    zxAnXdsl2FextCoefficientDs  OBJECT-TYPE
        SYNTAX      OCTET STRING(SIZE(0..1024))
        MAX-ACCESS  read-only
        STATUS      current
        DESCRIPTION
            "The downstream FEXT coupling coefficient shall be stored and
             reported to the management entity upon request at least for all 
             pairs of line indices(i, j) in the vectored group and sub-carrier 
             indices n = k X G for which FEXT from line j into line i is 
             estimated or cancelled over a frequency band containing the 
             subcarrier index n. In this description, G is the sub-carrier 
             group size for reporting the FEXT coupling and is restricted to 
             powers of two less than or equal to 8 and k = 0 up to a maximum 
             number of sub-carrier groups of 511."
        REFERENCE    "ITU-T G.993.5, paragraph #11.2.1.2"
        ::= { zxAnXdsl2FextCoefficientEntry 3 }    
    
    zxAnXdsl2FextCoefficientUs  OBJECT-TYPE
        SYNTAX      OCTET STRING(SIZE(0..512))
        MAX-ACCESS  read-only
        STATUS      current
        DESCRIPTION
            "The upstream FEXT coupling coefficient."
        REFERENCE    "ITU-T G.993.5, paragraph #11.2.1.3"
        ::= { zxAnXdsl2FextCoefficientEntry 4 } 
        
    zxAnXdsl2VectoringCardTable  OBJECT-TYPE
        SYNTAX      SEQUENCE  OF  ZxAnXdsl2VectoringCardEntry
        MAX-ACCESS  not-accessible
        STATUS      current
        DESCRIPTION
            "The vectoring card table."
        ::= { zxAnXdsl2Vectoring 3 }
       
    zxAnXdsl2VectoringCardEntry  OBJECT-TYPE
        SYNTAX      ZxAnXdsl2VectoringCardEntry
        MAX-ACCESS  not-accessible
        STATUS      current
        DESCRIPTION
            "The vectoring card table entry."
        INDEX  
        { 
            zxAnXdsl2VectoringRack,
            zxAnXdsl2VectoringShelf,
            zxAnXdsl2VectoringSlot
        }
        ::= { zxAnXdsl2VectoringCardTable 1 }
        
    ZxAnXdsl2VectoringCardEntry  ::=
        SEQUENCE {
            zxAnXdsl2VectoringRack           Integer32,
            zxAnXdsl2VectoringShelf          Integer32,
            zxAnXdsl2VectoringSlot           Integer32,
            zxAnXdsl2VectoringConfigClear    INTEGER,
            zxAxXdsl2VectoringHwPathStatus   INTEGER
        }
        
    zxAnXdsl2VectoringRack  OBJECT-TYPE
        SYNTAX      Integer32
        MAX-ACCESS  not-accessible
        STATUS      current
        DESCRIPTION
            "Rack No.."
        ::= { zxAnXdsl2VectoringCardEntry 1 }
    
    zxAnXdsl2VectoringShelf  OBJECT-TYPE
        SYNTAX      Integer32
        MAX-ACCESS  not-accessible
        STATUS      current
        DESCRIPTION
            "Shelf No.."
        ::= { zxAnXdsl2VectoringCardEntry 2 }
    
    zxAnXdsl2VectoringSlot  OBJECT-TYPE
        SYNTAX      Integer32
        MAX-ACCESS  not-accessible
        STATUS      current
        DESCRIPTION
            "Card No.."
        ::= { zxAnXdsl2VectoringCardEntry 3 }
        
    zxAnXdsl2VectoringConfigClear  OBJECT-TYPE
        SYNTAX      INTEGER
        {
            clear(1)
        }
        MAX-ACCESS  read-write
        STATUS      current
        DESCRIPTION
            "Set value to '1' to clear the card vectoring configuration before
             plugging out the card."
        ::= { zxAnXdsl2VectoringCardEntry 4 }
        
    zxAxXdsl2VectoringHwPathStatus  OBJECT-TYPE
        SYNTAX      INTEGER
        {
            normal(1),
            fault(2)
        }
        MAX-ACCESS  accessible-for-notify
        STATUS      current
        DESCRIPTION
            "Vectoring hardward path status."
        ::= { zxAnXdsl2VectoringCardEntry 5 }

--------------------------------------------------------------------------------
-- zxAnXdsl2VectoringCrosstalkTable   
--------------------------------------------------------------------------------
    
    zxAnXdsl2VectoringCrosstalkTable  OBJECT-TYPE
        SYNTAX      SEQUENCE  OF  ZxAnXdsl2VectoringCrosstalkEntry
        MAX-ACCESS  not-accessible
        STATUS      current
        DESCRIPTION
            "The vectoring crosstalk table."
        ::= { zxAnXdsl2Vectoring 4 }
 
    zxAnXdsl2VectoringCrosstalkEntry  OBJECT-TYPE
        SYNTAX      ZxAnXdsl2VectoringCrosstalkEntry
        MAX-ACCESS  not-accessible
        STATUS      current
        DESCRIPTION
            "The vectoring crosstalk entry."
        INDEX  
        { 
            ifIndex
        }
        ::= { zxAnXdsl2VectoringCrosstalkTable 1 }
        
    ZxAnXdsl2VectoringCrosstalkEntry  ::=
        SEQUENCE {
            zxAnXdsl2CrosstalkWeightsDs               OCTET STRING,
            zxAnXdsl2CrosstalkWeightsUs               OCTET STRING
        }

    zxAnXdsl2CrosstalkWeightsDs  OBJECT-TYPE
        SYNTAX      OCTET STRING(SIZE(0..768))
        MAX-ACCESS  read-only
        STATUS      current
        DESCRIPTION
            "It indicates the downstream crosstalk weight list of up to 
            M*N<=384 ports as following structure, each crosstalk weight is 
            present with two octets, and 'FF' is set if octet is not in use.
            Octets 1-2*M                  -- 1 to M port of slot 1
            Octets (2*M+1)- 4*M           -- 1 to M port of slot 2
            Octets (4*M + 1) - 6*M        -- 1 to M port of slot 3
            ........
            Octets (2*(N-1)*M + 1) - 2*N*M  -- 1 to M port of slot N
            Note: M means maximum port number of card, 
                  N means maximum card number of vectoring group."
        ::= { zxAnXdsl2VectoringCrosstalkEntry 1 }
        
    zxAnXdsl2CrosstalkWeightsUs  OBJECT-TYPE
        SYNTAX      OCTET STRING(SIZE(0..768))
        MAX-ACCESS  read-only
        STATUS      current
        DESCRIPTION
            "It indicates the upstream crosstalk weight list of up to 
            M*N<=384 ports as following structure, each crosstalk weight is 
            present with two octets, and 'FF' is set if octet is not in use.
            Octets 1-2*M                  -- 1 to M port of slot 1
            Octets (2*M+1)- 4*M           -- 1 to M port of slot 2
            Octets (4*M + 1) - 6*M        -- 1 to M port of slot 3
            ........
            Octets (2*(N-1)*M + 1) - 2*N*M  -- 1 to M port of slot N
            Note: M means maximum port number of card, 
                  N means maximum card number of vectoring group."
        ::= { zxAnXdsl2VectoringCrosstalkEntry 2 }
            
--------------------------------------------------------------------------------
-- zxAnXdsl2XlogSampleTable  
--------------------------------------------------------------------------------

    zxAnXdsl2XlogSampleTable  OBJECT-TYPE
        SYNTAX      SEQUENCE  OF  ZxAnXdsl2XlogSampleEntry
        MAX-ACCESS  not-accessible
        STATUS      current
        DESCRIPTION
            "The vectoring crosstalk logarithm sample table." 
        ::= { zxAnXdsl2Vectoring 5 }
 
    zxAnXdsl2XlogSampleEntry  OBJECT-TYPE
        SYNTAX      ZxAnXdsl2XlogSampleEntry
        MAX-ACCESS  not-accessible
        STATUS      current
        DESCRIPTION
            "A zxAnXdsl2XlogSampleTable entry."
        INDEX  
        { 
            ifIndex,
            zxAnXdsl2XlogSampleDirection,
            zxAnXdsl2XlogSampleToneIndex
        }
        ::= { zxAnXdsl2XlogSampleTable 1 }   
              
    ZxAnXdsl2XlogSampleEntry  ::=
        SEQUENCE 
        {
            zxAnXdsl2XlogSampleDirection  Xdsl2Direction,
            zxAnXdsl2XlogSampleToneIndex  Integer32,
            zxAnXdsl2XlogSampleValue      OCTET STRING
        }
        
    zxAnXdsl2XlogSampleDirection  OBJECT-TYPE
        SYNTAX      Xdsl2Direction
        MAX-ACCESS  not-accessible
        STATUS      current
        DESCRIPTION
            "The direction of vectoring crosstalk logarithm sample."
        ::= { zxAnXdsl2XlogSampleEntry 1 }
        
    zxAnXdsl2XlogSampleToneIndex  OBJECT-TYPE
        SYNTAX      Integer32(1..4096)
        MAX-ACCESS  not-accessible
        STATUS      current
        DESCRIPTION
            "Tone index."
        ::= { zxAnXdsl2XlogSampleEntry 2 }

    zxAnXdsl2XlogSampleValue  OBJECT-TYPE
        SYNTAX      OCTET STRING(SIZE(0..768))
        MAX-ACCESS  read-only
        STATUS      current
        DESCRIPTION
            "It indicates the crosstalk logarithm sample value list of up to 
            M*N<=384 ports as following structure, each logarithm sample value 
            is present with two octets, and 'FF' is set if octet is not in use.
            Octets 1-2*M                  -- 1 to M port of slot 1
            Octets (2*M+1)- 4*M           -- 1 to M port of slot 2
            Octets (4*M + 1) - 6*M        -- 1 to M port of slot 3
            ........
            Octets (2*(N-1)*M + 1) - 2*N*M  -- 1 to M port of slot N
            Note: M means maximum port number of card, 
                  N means maximum card number of vectoring group.
            
            The real Xlog(f) value is represented as (6-m(i)/10), with m(i)
            in the range 0 to 1022. A special value m=1023 indicates that
            no measurement could be done because it is out of the passband or 
            that the crosstalk is out of range to be represented."
        ::= { zxAnXdsl2XlogSampleEntry 3 }
   
--------------------------------------------------------------------------------
-- zxAnXdsl2SCStatusTable
--------------------------------------------------------------------------------

    zxAnXdsl2SCStatusTable  OBJECT-TYPE
        SYNTAX      SEQUENCE  OF  ZxAnXdsl2SCStatusEntry
        MAX-ACCESS  not-accessible
        STATUS      current
        DESCRIPTION
            "VDSL Sub-carrier status table."
        ::= { zxAnXdsl2Status 2 }
       
    zxAnXdsl2SCStatusEntry  OBJECT-TYPE
        SYNTAX      ZxAnXdsl2SCStatusEntry
        MAX-ACCESS  not-accessible
        STATUS      current
        DESCRIPTION
            "VDSL sub-carrier status entry."
        INDEX  
        { 
            ifIndex,
            xdsl2SCStatusDirection
        }
        ::= { zxAnXdsl2SCStatusTable 1 }
    
    ZxAnXdsl2SCStatusEntry ::=  SEQUENCE 
        {
            zxAnXdsl2SCStatusRmsGain      Integer32
        }
    
    zxAnXdsl2SCStatusRmsGain  OBJECT-TYPE
        SYNTAX      Integer32
        UNITS       "0.01dB"
        MAX-ACCESS  read-only
        STATUS      current
        DESCRIPTION
            "The average gi value (RMSGI)."
        REFERENCE  "ITU-T G.992.3, paragraph #8.5.1"
        ::= { zxAnXdsl2SCStatusEntry 1 }

--------------------------------------------------------------------------------
-- Trap
--------------------------------------------------------------------------------

    zxAnXdsl2LinePerfLOFSThreshXtuc NOTIFICATION-TYPE
       OBJECTS
       {
            zxAnXdsl2PMLCurr15MLofs,
            zxAnXdsl2XtucThreshLofs
       }
       STATUS     current
       DESCRIPTION
         "This notification indicates that the LOF seconds
          threshold has been reached/exceeded for the referred XTU-C."
       ::= { zxAnXdsl2TrapObjects 1 }
    
    zxAnXdsl2LinePerfLOFSThreshXtur NOTIFICATION-TYPE
       OBJECTS
       {
            zxAnXdsl2PMLCurr15MLofs,
            zxAnXdsl2XturThreshLofs
       }
       STATUS     current
       DESCRIPTION
         "This notification indicates that the LOF seconds
          threshold has been reached/exceeded for the referred XTU-R."
       ::= { zxAnXdsl2TrapObjects 2 }

    zxAnXdsl2LinePerfLOLSThreshXtuc NOTIFICATION-TYPE
       OBJECTS
       {
            zxAnXdsl2PMLCurr15MLols,
            zxAnXdsl2XtucThreshLols
       }
       STATUS     current
       DESCRIPTION
         "This notification indicates that the LOL seconds
          threshold has been reached/exceeded for the referred XTU-C."
       ::= { zxAnXdsl2TrapObjects 3 }
    
--    zxAnXdsl2LinePerfLOLSThreshXtur NOTIFICATION-TYPE
--       OBJECTS
--       {
--            zxAnXdsl2PMLCurr15MLols,
--            zxAnXdsl2XturThreshLols
--       }
--       STATUS     current
--       DESCRIPTION
--         "This notification indicates that the LOL seconds
--          threshold has been reached/exceeded for the referred XTU-R."
--       ::= { zxAnXdsl2TrapObjects 4 }

    zxAnXdsl2LinePerfLPRSThreshXtuc NOTIFICATION-TYPE
       OBJECTS
       {
            zxAnXdsl2PMLCurr15MLprs,
            zxAnXdsl2XtucThreshLprs
       }
       STATUS     current
       DESCRIPTION
         "This notification indicates that the LPR seconds
          threshold has been reached/exceeded for the referred XTU-C."
       ::= { zxAnXdsl2TrapObjects 5 }
       
    
    zxAnXdsl2LinePerfLPRSThreshXtur NOTIFICATION-TYPE
       OBJECTS
       {
            zxAnXdsl2PMLCurr15MLprs,
            zxAnXdsl2XturThreshLprs
       }
       STATUS     current
       DESCRIPTION
         "This notification indicates that the LPR seconds
          threshold has been reached/exceeded for the referred XTU-R."
       ::= { zxAnXdsl2TrapObjects 6 }

    zxAnXdsl2LinePerfPtmCrcErrsThreshXtuc NOTIFICATION-TYPE
       OBJECTS
       {
            zxAnXdsl2PMLCurr15MPtmCrcErrs,
            zxAnXdsl2XtucThreshPtmCrcErrs
       }
       STATUS     current
       DESCRIPTION
         "This notification indicates that the  Ptm Crc Errors
          threshold has been reached/exceeded for the referred XTU-C."
       ::= { zxAnXdsl2TrapObjects 7 }
    
    zxAnXdsl2LinePerfPtmCrcErrsThreshXtur NOTIFICATION-TYPE
       OBJECTS
       {
            zxAnXdsl2PMLCurr15MPtmCrcErrs,
            zxAnXdsl2XturThreshPtmCrcErrs
       }
       STATUS     current
       DESCRIPTION
         "This notification indicates that the  Ptm Crc Errors 
          threshold has been reached/exceeded for the referred XTU-R."
       ::= { zxAnXdsl2TrapObjects 8 }

    zxAnXdsl2LinePerfPtmCodViolsThreshXtuc NOTIFICATION-TYPE
       OBJECTS
       {
            zxAnXdsl2PMLCurr15MPtmCodViol,
            zxAnXdsl2XtucThreshPtmCodViol
       }
       STATUS     current
       DESCRIPTION
         "This notification indicates that the Ptm coding violations 
          threshold has been reached/exceeded for the referred XTU-C."
       ::= { zxAnXdsl2TrapObjects 9 }
    
    zxAnXdsl2LinePerfPtmCodViolsThreshXtur NOTIFICATION-TYPE
       OBJECTS
       {
            zxAnXdsl2PMLCurr15MPtmCodViol,
            zxAnXdsl2XturThreshPtmCodViol
       }
       STATUS     current
       DESCRIPTION
         "This notification indicates that the Ptm coding violations 
          threshold has been reached/exceeded for the referred XTU-R."
       ::= { zxAnXdsl2TrapObjects 10 }
            
    zxAnXdsl2LineXtucLowDataRateTrap        NOTIFICATION-TYPE
        OBJECTS 
        { 
            zxAnXdsl2ChConfMaxDataRateDs, 
            xdsl2ChStatusActDataRate,
            zxAnXdsl2XtucLowDataRateTolerance, 
            zxAnXdsl2XtucLowDataRateThresh
        }
        STATUS  current
        DESCRIPTION
            "zxAnXdsl2XtucLowDataRateTolerance threshold or 
             zxAnXdsl2XtucLowDataRateThresh reached."
        ::= { zxAnXdsl2TrapObjects 11 }
            
    zxAnXdsl2LineXtucLowDataRateClearTrap        NOTIFICATION-TYPE
        OBJECTS 
        { 
            zxAnXdsl2ChConfMaxDataRateDs, 
            xdsl2ChStatusActDataRate,
            zxAnXdsl2XtucLowDataRateTolerance, 
            zxAnXdsl2XtucLowDataRateThresh
        }
        STATUS  current
        DESCRIPTION
            " zxAnXdsl2LineXtucLowDataRateTrap clear."
        ::= { zxAnXdsl2TrapObjects 12 }            
            
    zxAnXdsl2LineXturLowDataRateTrap        NOTIFICATION-TYPE
        OBJECTS { zxAnXdsl2ChConfMaxDataRateUs, xdsl2ChStatusActDataRate,
                  zxAnXdsl2XturLowDataRateTolerance, zxAnXdsl2XturLowDataRateThresh}
        STATUS  current
        DESCRIPTION
            "zxAnXdsl2XturLowDataRateTolerance threshold or zxAnXdsl2XturLowDataRateThresh reached."
        ::= { zxAnXdsl2TrapObjects 13 }

    zxAnXdsl2LineXturLowDataRateClearTrap        NOTIFICATION-TYPE
        OBJECTS { zxAnXdsl2ChConfMaxDataRateUs, xdsl2ChStatusActDataRate,
                  zxAnXdsl2XturLowDataRateTolerance, zxAnXdsl2XturLowDataRateThresh}
        STATUS  current
        DESCRIPTION
            " zxAnXdsl2LineXturLowDataRateTrap clear."
        ::= { zxAnXdsl2TrapObjects 14 }
        
    zxAnXdsl2DataPathMismatchTrap           NOTIFICATION-TYPE
        OBJECTS 
            {
                zxAnXdsl2LnStatusDataPathType,
                zxAnXdsl2LnStatusActDataPathType
            }
        STATUS  current
        DESCRIPTION
            "This trap will be sent to managemet system when configured
             data path type is different from actual data path type on the 
             interface."
        ::= { zxAnXdsl2TrapObjects 15 }
        
    zxAnXdsl2DataPathMismatchClrTrap        NOTIFICATION-TYPE
        OBJECTS
            {
                zxAnXdsl2LnStatusDataPathType,
                zxAnXdsl2LnStatusActDataPathType
            }
        STATUS  current
        DESCRIPTION
            "zxAnXdsl2DataPathMismatchTrap will be cleared when configured
             data path type matches actual data path type on the 
             interface."
        ::= { zxAnXdsl2TrapObjects 16 }
        
     zxAnXdsl2LnVectorUnsupportAlm        NOTIFICATION-TYPE
        OBJECTS
            {
            zxAnXdsl2LnFextCancellationDs,
            zxAnXdsl2LnFextCancellationUs
            
            }
        STATUS  current
        DESCRIPTION
            "This trap will be sent when a non-vectoring modem is 
            connecting to a vector port."
        ::= { zxAnXdsl2TrapObjects 17 }
        
    zxAnXdsl2LnVectorUnsupportClr        NOTIFICATION-TYPE
        OBJECTS
            {
            zxAnXdsl2LnFextCancellationDs,
            zxAnXdsl2LnFextCancellationUs
            
            }
        STATUS  current
        DESCRIPTION
            "This trap will be sent when the non-vectoring modem 
            no longer connects to the vector port."
        ::= { zxAnXdsl2TrapObjects 18 }
        
    zxAnXdsl2LnCpeUpboPsdErrorNotify        NOTIFICATION-TYPE
        OBJECTS
            {
                zxAnXdsl2LnUpboConfPrf
            }
        STATUS  current
        DESCRIPTION
            "This trap will be sent when CPE UPBO PSD errored."
        ::= { zxAnXdsl2TrapObjects 19 }

    zxAnXdsl2VectoringConfigCleared        NOTIFICATION-TYPE
        OBJECTS
            {
                zxAnXdsl2VectoringConfigClear
            }
        STATUS  current
        DESCRIPTION
            "This trap will be sent when card vectoring configuration is
             cleared."
        ::= { zxAnXdsl2TrapObjects 20 }

    zxAnXdsl2VectorHwPathAbnormalAlm        NOTIFICATION-TYPE
        OBJECTS
            {
                zxAxXdsl2VectoringHwPathStatus
            }
        STATUS  current
        DESCRIPTION
            "zxAnXdsl2VectorHwPathAbnormalAlm will be sent when vectoring 
             hardware path is abnormal, such as real time clock abnormal, 
             hardware interface abnormal and so on."
        ::= { zxAnXdsl2TrapObjects 21 }

    zxAnXdsl2VectorHwPathAbnormalClr        NOTIFICATION-TYPE
        OBJECTS
            {
                zxAxXdsl2VectoringHwPathStatus
            }
        STATUS  current
        DESCRIPTION
            "zxAnXdsl2VectorHwPathAbnormalClr will be sent when 
             zxAnXdsl2VectorHwPathAbnormalAlm is cleared."
        ::= { zxAnXdsl2TrapObjects 22 }

    zxAnXdsl2XtucEsLossOverThreshAlm        NOTIFICATION-TYPE
        OBJECTS
            {
                zxAnXdsl2PMLCurr1DayTxEsPkts,
                zxAnXdsl2PMLCurr1DayRxEsPkts,
                zxAnXdsl2XtucEsLossRatioThresh
            }
        STATUS  current
        DESCRIPTION
            "This trap will be sent when vector error sample packets loss 
            rate reached threshold in downstream."
        ::= { zxAnXdsl2TrapObjects 23 }

    zxAnXdsl2XtucEsLossOverThreshClr        NOTIFICATION-TYPE
        OBJECTS
            {
                zxAnXdsl2PMLCurr1DayTxEsPkts,
                zxAnXdsl2PMLCurr1DayRxEsPkts,
                zxAnXdsl2XtucEsLossRatioThresh
            }
        STATUS  current
        DESCRIPTION
            "This trap will be sent when vector error sample packets loss 
            rate recoveres below the threshold in downstream."
        ::= { zxAnXdsl2TrapObjects 24 }
 
    zxAnXdsl2XturEsLossOverThreshAlm        NOTIFICATION-TYPE
        OBJECTS
            {
                zxAnXdsl2PMLCurr1DayTxEsPkts,
                zxAnXdsl2PMLCurr1DayRxEsPkts,
                zxAnXdsl2XturEsLossRatioThresh
            }
        STATUS  current
        DESCRIPTION
            "This trap will be sent when vector error sample packets loss 
            rate reached threshold in upstream."
        ::= { zxAnXdsl2TrapObjects 25 }     
 
    zxAnXdsl2XturEsLossOverThreshClr        NOTIFICATION-TYPE
        OBJECTS
            {
                zxAnXdsl2PMLCurr1DayTxEsPkts,
                zxAnXdsl2PMLCurr1DayRxEsPkts,
                zxAnXdsl2XturEsLossRatioThresh
            }
        STATUS  current
        DESCRIPTION
            "This trap will be sent when vector error sample packets loss 
            rate recoveres below the threshold in upstream."
        ::= { zxAnXdsl2TrapObjects 26 }       

    zxAnXdsl2InpLeftrsThreshXtuc NOTIFICATION-TYPE
        OBJECTS
        {
            zxAnXdsl2PMChCurr15MInpLeftrs,
            zxAnXdsl2XtucThreshInpLeftrs
        }
        STATUS     current
        DESCRIPTION
            "This notification indicates that the 'leftr' defect seconds
             threshold has been reached/exceeded in a 15-min interval for 
             the referred XTU-C."
        ::= { zxAnXdsl2TrapObjects 27 } 
          
    zxAnXdsl2InpLeftrsThreshXtur  NOTIFICATION-TYPE
        OBJECTS
        {
            zxAnXdsl2PMChCurr15MInpLeftrs,
            zxAnXdsl2XturThreshInpLeftrs
        }
        STATUS     current
        DESCRIPTION
            "This notification indicates that the 'leftr' defect seconds
             threshold has been reached/exceeded in a 15-min interval for 
             the referred XTU-R."
        ::= { zxAnXdsl2TrapObjects 28 } 

    zxAnXdsl2XtucLosAlm  NOTIFICATION-TYPE
        OBJECTS
        {
            xdsl2LineStatusXtuc
        }
        STATUS     current
        DESCRIPTION
            "When xdsl2LineStatusXtuc bit 3(lossOfSignal) is 1, 
             zxAnXdsl2XtucLosAlm will be sent to indicate that XTU-C current 
             status is loss of signal."
        ::= { zxAnXdsl2TrapObjects 29 }

    zxAnXdsl2XtucLosClr  NOTIFICATION-TYPE
        OBJECTS
        {
            xdsl2LineStatusXtuc
        }
        STATUS     current
        DESCRIPTION
            "zxAnXdsl2XtucLosClr will be sent when zxAnXdsl2XtucLosAlm is 
             cleared."
        ::= { zxAnXdsl2TrapObjects 30 }

    zxAnXdsl2XturLosAlm  NOTIFICATION-TYPE
        OBJECTS
        {
            xdsl2LineStatusXtur
        }
        STATUS     current
        DESCRIPTION
            "When xdsl2LineStatusXtur bit 3(lossOfSignal) is 1, 
             zxAnXdsl2XturLosAlm will be sent to indicate that XTU-R current 
             status is loss of signal."
        ::= { zxAnXdsl2TrapObjects 31 }

    zxAnXdsl2XturLosClr  NOTIFICATION-TYPE
        OBJECTS
        {
            xdsl2LineStatusXtur
        }
        STATUS     current
        DESCRIPTION
            "zxAnXdsl2XturLosClr will be sent when zxAnXdsl2XturLosAlm is 
             cleared."
        ::= { zxAnXdsl2TrapObjects 32 }
        
    zxAnXdsl2XturLprAlm  NOTIFICATION-TYPE
        OBJECTS
        {
            xdsl2LineStatusXtur
        }
        STATUS     current
        DESCRIPTION
            "When xdsl2LineStatusXtur bit 4(lossOfSignal) is 1, 
             zxAnXdsl2XturLprAlm will be sent to indicate that XTU-R current 
             status is loss of power."
        ::= { zxAnXdsl2TrapObjects 33 }

    zxAnXdsl2XturLprClr  NOTIFICATION-TYPE
        OBJECTS
        {
            xdsl2LineStatusXtur
        }
        STATUS     current
        DESCRIPTION
            "zxAnXdsl2XturLprClr will be sent when zxAnXdsl2XturLprAlm is 
             cleared."
        ::= { zxAnXdsl2TrapObjects 34 }
END
