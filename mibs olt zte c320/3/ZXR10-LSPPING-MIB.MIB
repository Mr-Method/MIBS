--  ************************************************
--  $Id: zxr10ping.mib 8 2005-07-28 12:17:08Z zhanglh $
--
--  zxr10lspping.mib: ZXR10 LSP Ping MIB file
--
--  JUL. 2005, Zhang lihui
--
--  Copyright(c) 2005 by ZTE Corporaton
--  All rights reservered
--
--  ************************************************

ZXR10-LSPPING-MIB DEFINITIONS ::= BEGIN

IMPORTS
    MODULE-IDENTITY, OBJECT-TYPE,
    NOTIFICATION-TYPE, experimental,
    enterprises, Integer32,
    Unsigned32, Counter32
                                        FROM SNMPv2-SMI

    MODULE-COMPLIANCE, OBJECT-GROUP,
    NOTIFICATION-GROUP
                                        FROM SNMPv2-CONF

    MacAddress,RowStatus,TruthValue
                                        FROM SNMPv2-TC

    zxr10L2vpn
                                        FROM ZXR10-SMI

    mgmt, NetworkAddress, IpAddress,
    Counter, Gauge
                                        FROM RFC1155-SMI
                                        
    InetAddress, InetAddressType,
    InetAddressPrefixLength
                                        FROM INET-ADDRESS-MIB;

    zxr10LspPingMIB OBJECT IDENTIFIER ::= { zxr10L2vpn 5}

    DisplayString ::= OCTET STRING
    --  This data type is used to model textual information taken
    --  from the NVT ASCII character set.  By convention, objects
    --  with this syntax are declared as having
    --  SIZE (0..255)

    lspPingTable  OBJECT-TYPE
        SYNTAX  SEQUENCE OF LspPingEntry
        MAX-ACCESS  not-accessible
        STATUS  current
        DESCRIPTION
            "lsp ping information table."
        ::= { zxr10LspPingMIB 1 }

    lspPingEntry  OBJECT-TYPE
        SYNTAX  LspPingEntry
        MAX-ACCESS  not-accessible
        STATUS  current
        DESCRIPTION
            ""
        INDEX  {lspPingSerial }
        ::= { lspPingTable 1 }

    LspPingEntry ::= SEQUENCE {
        lspPingSerial              Integer32,
        lspPingType                INTEGER,
        lspPingLdpPrefixType       InetAddressType,
        lspPingLdpPrefix           InetAddress,
        lspPingLdpPrefixlen        InetAddressPrefixLength,
        lspPingMplsTeTunnelNumber  Integer32,
        lspPingPwNextAddrType      InetAddressType,
        lspPingPwNextAddr          InetAddress,
        lspPingPwNextVcId          Counter32,
        lspPingPwDestAddrType      InetAddressType,
        lspPingPwDestAddr          InetAddress,
        lspPingPwDestVcId          Counter32,
        lspPingPwTtl               Integer32,
        lspPingIfOption            INTEGER,
        lspPingPacketCount         Integer32,
        lspPingTimeOut             Integer32,
        lspPingDataLen             Integer32,
        lspPingTrapOncompletion    TruthValue,
        lspPingRosStatus           INTEGER,
        lspPingEntryOwner          DisplayString,
        lspPingPwName              DisplayString
    }

    lspPingSerial  OBJECT-TYPE
        SYNTAX  Integer32
        MAX-ACCESS  read-only
        STATUS  current
        DESCRIPTION
            ""
        ::= { lspPingEntry 1 }

    lspPingType  OBJECT-TYPE
        SYNTAX  INTEGER
        {
            ldp(0),
            rsvp-te(1),
            vccv(2)
        }
        MAX-ACCESS  read-write
        STATUS  current
        DESCRIPTION
            "lsp ping type (0:ldp,1:rsvp-te,2:vccv)"
        ::= { lspPingEntry 2 }

    lspPingLdpPrefix  OBJECT-TYPE
        SYNTAX  InetAddress
        MAX-ACCESS  read-write
        STATUS  current
        DESCRIPTION
            "ldp prefix"
        ::= { lspPingEntry 3 }

    lspPingLdpPrefixlen  OBJECT-TYPE
        SYNTAX  InetAddressPrefixLength
        MAX-ACCESS  read-write
        STATUS  current
        DESCRIPTION
            "ldp prefix length.
             Indicates the number of leading one bits that form the mask 
             to be logical-ANDed with the destination address before being
             compared to the value in the lspPingLdpPrefix field."
        ::= { lspPingEntry 4 }

    lspPingMplsTeTunnelNumber  OBJECT-TYPE
        SYNTAX  Integer32 (1..8192)
        MAX-ACCESS  read-write
        STATUS  current
        DESCRIPTION
            "tunnel number "
        ::= { lspPingEntry 5 }

    lspPingPwNextAddr  OBJECT-TYPE
        SYNTAX  InetAddress
        MAX-ACCESS  read-write
        STATUS  current
        DESCRIPTION
            "vccv next address"
        ::= { lspPingEntry 6 }

    lspPingPwNextVcId  OBJECT-TYPE
        SYNTAX  Counter32
        MAX-ACCESS  read-write
        STATUS  current
        DESCRIPTION
            "next vc id  "
        ::= { lspPingEntry 7 }

    lspPingPwDestAddr  OBJECT-TYPE
        SYNTAX  InetAddress
        MAX-ACCESS  read-write
        STATUS  current
        DESCRIPTION
            "vccv target address"
        ::= { lspPingEntry 8 }

    lspPingPwDestVcId  OBJECT-TYPE
        SYNTAX  Counter32
        MAX-ACCESS  read-write
        STATUS  current
        DESCRIPTION
            "target vc id  "
        ::= { lspPingEntry 9 }

    lspPingPwTtl  OBJECT-TYPE
        SYNTAX  Integer32 (1..255)
        MAX-ACCESS  read-write
        STATUS  current
        DESCRIPTION
            "pw label ttl "
        DEFVAL { 1 }
        ::= { lspPingEntry 10 }

    lspPingIfOption  OBJECT-TYPE
        SYNTAX  INTEGER{none(0),option(1)}
        MAX-ACCESS  read-write
        STATUS  current
        DESCRIPTION
            "if select option,default:none  "
        DEFVAL { 0 }
        ::= { lspPingEntry 11 }

    lspPingPacketCount  OBJECT-TYPE
        SYNTAX  Integer32
        MAX-ACCESS  read-write
        STATUS  current
        DESCRIPTION
            "send packets count,default:5   "
        DEFVAL { 5 }
        ::= { lspPingEntry 12 }

    lspPingTimeOut  OBJECT-TYPE
        SYNTAX  Integer32 (1..60)
        MAX-ACCESS  read-write
        STATUS  current
        DESCRIPTION
            "timeout,defalt:2  "
        DEFVAL { 2 }
        ::= { lspPingEntry 13 }

    lspPingDataLen  OBJECT-TYPE
        SYNTAX  Integer32 (100..1500)
        MAX-ACCESS  read-write
        STATUS  current
        DESCRIPTION
            "data len,default:100  "
        DEFVAL { 100 }
        ::= { lspPingEntry 14 }

    lspPingTrapOncompletion  OBJECT-TYPE
        SYNTAX  TruthValue
        MAX-ACCESS  read-write
        STATUS  current
        DESCRIPTION
            "report the lsp ping result as trap or not"
        DEFVAL { true }
        ::= { lspPingEntry 15 }

    lspPingRosStatus  OBJECT-TYPE
        SYNTAX  INTEGER
        {
            not-active(1),
            start-ping(2),
            ping-processing(3),
            ping-completed(4)
        }
        MAX-ACCESS  read-write
        STATUS  current
        DESCRIPTION
            ""
        DEFVAL { 1 }
        ::= { lspPingEntry 16 }

    lspPingEntryOwner  OBJECT-TYPE
        SYNTAX  DisplayString
        MAX-ACCESS  read-write
        STATUS  current
        DESCRIPTION
            ""
        ::= { lspPingEntry 17 }
        
    lspPingLdpPrefixType  OBJECT-TYPE
        SYNTAX     InetAddressType
        MAX-ACCESS read-write
        STATUS     current
        DESCRIPTION
            "The type of the lspPingLdpPrefix, as defined
            in the InetAddress MIB."
        ::= { lspPingEntry 18 }
        
    lspPingPwNextAddrType  OBJECT-TYPE
        SYNTAX     InetAddressType
        MAX-ACCESS read-write
        STATUS     current
        DESCRIPTION
            "The type of the lspPingPwNextAddr, as defined
            in the InetAddress MIB."
        ::= { lspPingEntry 19 }
        
    lspPingPwDestAddrType  OBJECT-TYPE
        SYNTAX     InetAddressType
        MAX-ACCESS read-write
        STATUS     current
        DESCRIPTION
            "The type of the lspPingPwDestAddr, as defined
            in the InetAddress MIB."
        ::= { lspPingEntry 20 }
        
    lspPingPwName  OBJECT-TYPE
        SYNTAX   DisplayString(SIZE(0..63))
        MAX-ACCESS  read-write
        STATUS  current
        DESCRIPTION
            "Name specified for each configured MPLS L2VPN PW."
        ::= { lspPingEntry 21 }

--- lsp ping result

    lspPingResultTable  OBJECT-TYPE
        SYNTAX  SEQUENCE OF LspPingResultEntry
        MAX-ACCESS  not-accessible
        STATUS  current
        DESCRIPTION
            "lsp ping result table."
        ::= { zxr10LspPingMIB 2 }
 
    lspPingResultEntry  OBJECT-TYPE
        SYNTAX  LspPingResultEntry
        MAX-ACCESS  not-accessible
        STATUS  current
        DESCRIPTION
            ""
        INDEX  { lspPingResultSerial }
        ::= { lspPingResultTable 1 }
 
    LspPingResultEntry ::= SEQUENCE {
        lspPingResultSerial                  Integer32,
        lspPingResultSentPkts                Integer32,
        lspPingResultRcvPkts                 Integer32,
        lspPingResultRoundTripMinTime        Integer32,
        lspPingResultRoundTripMaxTime        Integer32,
        lspPingResultRoundTripAvgTime        Integer32,
        lspPingResultEntryOwner              DisplayString,
        lspPingResultRoundWobbleMinTime      Integer32,
        lspPingResultRoundWobbleMaxTime      Integer32,
        lspPingResultRoundWobbleAvgTime      Integer32
    }

    lspPingResultSerial  OBJECT-TYPE
        SYNTAX  Integer32
        MAX-ACCESS  read-only
        STATUS  current
        DESCRIPTION
            ""
        ::= { lspPingResultEntry 1 }
 
    lspPingResultSentPkts  OBJECT-TYPE
        SYNTAX  Integer32
        MAX-ACCESS  read-only
        STATUS  current
        DESCRIPTION
            "send packet"
        ::= { lspPingResultEntry 2 }
 
    lspPingResultRcvPkts  OBJECT-TYPE
        SYNTAX  Integer32
        MAX-ACCESS  read-only
        STATUS  current
        DESCRIPTION
            "receive packet"
        ::= { lspPingResultEntry 3 }
 
    lspPingResultRoundTripMinTime  OBJECT-TYPE
        SYNTAX  Integer32
        MAX-ACCESS  read-only
        STATUS  current
        DESCRIPTION
            "min RTT"
        ::= { lspPingResultEntry 4 }
 
    lspPingResultRoundTripMaxTime  OBJECT-TYPE
        SYNTAX  Integer32
        MAX-ACCESS  read-only
        STATUS  current
        DESCRIPTION
            "max RTT"
        ::= { lspPingResultEntry 5 }
 
    lspPingResultRoundTripAvgTime  OBJECT-TYPE
        SYNTAX  Integer32
        MAX-ACCESS  read-only
        STATUS  current
        DESCRIPTION
            "average RTT"
        ::= { lspPingResultEntry 6 }
 
    lspPingResultEntryOwner  OBJECT-TYPE
        SYNTAX  DisplayString
        MAX-ACCESS  read-only
        STATUS  current
        DESCRIPTION
            ""
        ::= { lspPingResultEntry 9 }
 
    lspPingResultRoundWobbleMinTime  OBJECT-TYPE
        SYNTAX  Integer32
        MAX-ACCESS  read-only
        STATUS  current
        DESCRIPTION
            "max RWT"
        ::= { lspPingResultEntry 10 }
 
    lspPingResultRoundWobbleMaxTime  OBJECT-TYPE
        SYNTAX  Integer32
        MAX-ACCESS  read-only
        STATUS  current
        DESCRIPTION
            "max RWT"
        ::= { lspPingResultEntry 11 }
 
    lspPingResultRoundWobbleAvgTime  OBJECT-TYPE
        SYNTAX  Integer32
        MAX-ACCESS  read-only
        STATUS  current
        DESCRIPTION
            "max RWT"
        ::= { lspPingResultEntry 12 } 
  
        
-- *******************************************************************
--   Trap Definitions
-- *******************************************************************

    lsppingNotifications   OBJECT IDENTIFIER ::= { zxr10LspPingMIB 3 }

    lsppingTrapResult NOTIFICATION-TYPE
    OBJECTS      { lspPingResultSerial,
                   lspPingResultSentPkts,
                   lspPingResultRcvPkts,
                   lspPingResultRoundTripMinTime,
                   lspPingResultRoundTripMaxTime,
                   lspPingResultRoundTripAvgTime,
                   lspPingResultRoundWobbleMinTime,
                   lspPingResultRoundWobbleMaxTime,
                   lspPingResultRoundWobbleAvgTime
                 }
    STATUS       current
    DESCRIPTION
        "The newMaster trap indicates that the sending agent
        has transitioned to 'Master' state."
    ::= { lsppingNotifications 1 }

 END
