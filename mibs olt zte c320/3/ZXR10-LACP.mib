--  ********************************************************
--  $Id: ZXR10-LACP.mib 2006-09-01 01:34:21Z wuxiaoxiang $
--
--  ZXR10-LACP.mib: ZXR10 LACP MIB file
--
--  Sep. 2006, Wu XiaoXiang
--
--  Copyright(c) 2006 by ZTE Corporation
--  All rights reserved
--
--  ********************************************************

ZXR10-LACP DEFINITIONS ::= BEGIN

IMPORTS
    MODULE-IDENTITY,
    OBJECT-TYPE, NOTIFICATION-TYPE,
    Unsigned32, Integer32,
    Counter32 
        FROM SNMPv2-SMI

    TEXTUAL-CONVENTION
        FROM SNMPv2-TC

    ifIndex
        FROM RFC1213-MIB

    lacp
        FROM ZXR10-SMI;

    lacpMIB MODULE-IDENTITY

        LAST-UPDATED "201110080000Z"

        ORGANIZATION "ZTE Corporation"

        CONTACT-INFO
            "ZTE Corporation

             Nanjing Institute of ZTE Corporation

             No.68 ZiJinghua Rd. YuHuatai District, Nanjing, China

             Tel: +86-25-52870000"

        DESCRIPTION
            "ZXROS V4.6.03B LACP MIB"

    ::= { lacp 1 }


    lacpMibObjects  OBJECT IDENTIFIER ::= { lacpMIB  1 }
    zxAnLacpNotifications  OBJECT IDENTIFIER ::= { lacpMIB  2 }


--TEXTUAL-CONVENTION

    UINT32 ::=
           Unsigned32
    -- This data type is used to unsigned integer.

    Char ::=
         OCTET STRING
    -- This data type is used to model textual information taken
    -- from the NVT ASCII character set.  By convention, objects
    -- with this syntax are declared as having 0-65535 characters.

    LACPLoadBalanceType ::= TEXTUAL-CONVENTION
        DISPLAY-HINT  "d"
        STATUS        current
        DESCRIPTION   "LACP Load Balance Type"
        SYNTAX        INTEGER
                      {
                         dst-ip(1),
                         dst-mac(2),
                         src-dst-ip(3),
                         src-dst-mac(4),
                         src-ip(5),
                         src-mac(6),
                         src-port(7),
                         dst-port(8),
                         src-dst-port(9),
                         invalid(50)
                      }

    LACPPortType ::= TEXTUAL-CONVENTION
        DISPLAY-HINT  "d"
        STATUS        current
        DESCRIPTION   "LACP Port Type"
        SYNTAX        INTEGER
                      {
                         passive(1),
                         on(2),
                         active(3)
                      }

    LACPPortTimeoutType ::= TEXTUAL-CONVENTION
        DISPLAY-HINT  "d"
        STATUS        current
        DESCRIPTION   "LACP Port Timeout Type"
        SYNTAX        INTEGER
                      {
                         long-time(0),
                         short-time(1)
                      }


-- groups in lacpMibObjects

      lacpAggregatingPara      OBJECT IDENTIFIER ::= { lacpMibObjects  1 }

      lacpAggregatedPara       OBJECT IDENTIFIER ::= { lacpMibObjects  2 }
      lacpGroupObjects         OBJECT IDENTIFIER ::= { lacpMibObjects  3 }


---lacpAggregatingPara

      lacpAggregatingTable    OBJECT-TYPE
          SYNTAX            SEQUENCE OF LacpAggregatingEntry
          MAX-ACCESS      not-accessible
          STATUS            current
          DESCRIPTION   "Configure Aggregating Port parameters."
      ::=  { lacpAggregatingPara  1 }

      lacpAggregatingEntry    OBJECT-TYPE
          SYNTAX            LacpAggregatingEntry
          MAX-ACCESS      not-accessible
          STATUS            current
          DESCRIPTION   "Each row index by ifIndex And contain imformation of Aggregating Port."
            INDEX              {  ifIndex  }
    ::=  { lacpAggregatingTable 1 }

      LacpAggregatingEntry
      ::=  SEQUENCE
      {
          lacpAggSgIfName              Char,
          lacpAggMacAddress            Char,
          lacpAggActorSystemPriority   UINT32,
          lacpAggMode                  INTEGER,
          lacpAggLoadBalanceMode       LACPLoadBalanceType,
          lacpAggSubIfIndexName1       Char,
          lacpAggSubIfIndexName2       Char,
          lacpAggSubIfIndexName3       Char,
          lacpAggSubIfIndexName4       Char,
          lacpAggSubIfIndexName5       Char,
          lacpAggSubIfIndexName6       Char,
          lacpAggSubIfIndexName7       Char,
          lacpAggSubIfIndexName8       Char,
          zxAnLacpAggActorAdminKey     UINT32
      }

      lacpAggSgIfName   OBJECT-TYPE
        SYNTAX            Char
            MAX-ACCESS      read-only
            STATUS            current
            DESCRIPTION   "Smartgroup interface name."
      ::=  { lacpAggregatingEntry  1 }

      lacpAggMacAddress   OBJECT-TYPE
        SYNTAX            Char
          MAX-ACCESS      read-only
            STATUS            current
            DESCRIPTION   "Mac address."
      ::=  { lacpAggregatingEntry  2 }

      lacpAggActorSystemPriority   OBJECT-TYPE
        SYNTAX            UINT32(1..65535)
            MAX-ACCESS      read-write
            STATUS            current
            DESCRIPTION   "LACP System priority."
      ::=  { lacpAggregatingEntry  3 }

      lacpAggMode   OBJECT-TYPE
        SYNTAX      INTEGER {
            static(1),
            dynamic(2)
        }
        MAX-ACCESS  read-write
        STATUS      current
        DESCRIPTION     
            "Aggregation mode.
            If lacpAggMode is 'static', the lacpAggPortMode of sub-interface
            can be set to 'on'.
            If lacpAggMode is 'dynamic', the lacpAggPortMode of sub-interface 
            can be set to 'active' or 'passive'."
        ::=  { lacpAggregatingEntry  4 }

      lacpAggLoadBalanceMode   OBJECT-TYPE
        SYNTAX            LACPLoadBalanceType
            MAX-ACCESS    read-write
            STATUS        current
            DESCRIPTION   
                "Aggregation Load Balance Type.
                Only when the value of zxAnLacpLoadBalanceLevel is system(2),
                reading the value of lacpAggLoadBalanceMode will 
                return invalid(50),and lacpAggLoadBalanceMode can't be written.
                Otherwise, it can be read and written."
      ::=  { lacpAggregatingEntry  5 }

      lacpAggSubIfIndexName1   OBJECT-TYPE
        SYNTAX            Char
            MAX-ACCESS      read-only
            STATUS            current
            DESCRIPTION   "Aggregated Port Name."
      ::=  { lacpAggregatingEntry  6 }

      lacpAggSubIfIndexName2   OBJECT-TYPE
        SYNTAX            Char
            MAX-ACCESS      read-only
            STATUS            current
            DESCRIPTION   "Aggregated Port Name."
      ::=  { lacpAggregatingEntry  7 }

      lacpAggSubIfIndexName3   OBJECT-TYPE
        SYNTAX            Char
            MAX-ACCESS      read-only
            STATUS            current
            DESCRIPTION   "Aggregated Port Name."
      ::=  { lacpAggregatingEntry  8 }

      lacpAggSubIfIndexName4   OBJECT-TYPE
        SYNTAX            Char
            MAX-ACCESS      read-only
            STATUS            current
            DESCRIPTION   "Aggregated Port Name."
      ::=  { lacpAggregatingEntry  9 }

      lacpAggSubIfIndexName5   OBJECT-TYPE
        SYNTAX            Char
            MAX-ACCESS      read-only
            STATUS            current
            DESCRIPTION   "Aggregated Port Name."
      ::=  { lacpAggregatingEntry  10 }

      lacpAggSubIfIndexName6   OBJECT-TYPE
        SYNTAX            Char
            MAX-ACCESS      read-only
            STATUS            current
            DESCRIPTION   "Aggregated Port Name."
      ::=  { lacpAggregatingEntry  11 }

      lacpAggSubIfIndexName7   OBJECT-TYPE
        SYNTAX            Char
            MAX-ACCESS      read-only
            STATUS            current
            DESCRIPTION   "Aggregated Port Name."
      ::=  { lacpAggregatingEntry  12 }

      lacpAggSubIfIndexName8   OBJECT-TYPE
        SYNTAX            Char
            MAX-ACCESS      read-only
            STATUS            current
            DESCRIPTION   "Aggregated Port Name."
      ::=  { lacpAggregatingEntry  13 }
      
      zxAnLacpAggActorAdminKey  OBJECT-TYPE
          SYNTAX            UINT32(0..65535)
          MAX-ACCESS        read-write
          STATUS            current
          DESCRIPTION       
            "The current administrative value of the Key for the Aggregator.
            This is a 16-bit, read-write value. The meaning of particular Key 
            values is of local significance."
      ::= { lacpAggregatingEntry  14 }


---lacpAggregatedPara

      lacpAggregatedTable    OBJECT-TYPE
          SYNTAX            SEQUENCE OF LacpAggregatedEntry
          MAX-ACCESS      not-accessible
          STATUS            current
          DESCRIPTION   "Configure Aggregated Port parameters."
      ::=  { lacpAggregatedPara  1 }

      lacpAggregatedEntry    OBJECT-TYPE
          SYNTAX            LacpAggregatedEntry
          MAX-ACCESS      not-accessible
          STATUS            current
          DESCRIPTION   "Each row index by aggregating and aggregated ifIndex And contain imformation of Aggregated Port."
            INDEX              {  ifIndex  }
    ::=  { lacpAggregatedTable 1 }

      LacpAggregatedEntry
      ::=  SEQUENCE
      {
          lacpAggSgId                   UINT32,
          lacpAggregatedIfName          Char,
          lacpAggPortMode               LACPPortType,
          lacpAggPortTimeOut            LACPPortTimeoutType,
          lacpAggLacpPriority           UINT32,
          lacpAggPortActorOperKey       UINT32,
          lacpAggPortActorOperState     UINT32,
          lacpAggPortPartnerOperKey     UINT32,
          lacpAggPortPartnerOperState   UINT32,
          zxAnLacpAggPortAggregationStatus  INTEGER,
          lacpAggPortSubgroupId         UINT32
      }

      lacpAggSgId   OBJECT-TYPE
            SYNTAX            UINT32(1..68)
            MAX-ACCESS        read-write
            STATUS            current
            DESCRIPTION       "Add to smartgroup interface."
      ::=  { lacpAggregatedEntry  1 }

      lacpAggregatedIfName   OBJECT-TYPE
        SYNTAX            Char
          MAX-ACCESS      read-only
            STATUS            current
            DESCRIPTION   "Aggregated interface name."
      ::=  { lacpAggregatedEntry  2 }

      lacpAggPortMode   OBJECT-TYPE
        SYNTAX            LACPPortType
            MAX-ACCESS      read-write
            STATUS            current
            DESCRIPTION   "LACP Port Type."
      ::=  { lacpAggregatedEntry  3 }

      lacpAggPortTimeOut   OBJECT-TYPE
        SYNTAX            LACPPortTimeoutType
            MAX-ACCESS      read-write
            STATUS            current
            DESCRIPTION   "LACP Port Timeout."
      ::=  { lacpAggregatedEntry  4 }

      lacpAggLacpPriority   OBJECT-TYPE
        SYNTAX            UINT32(1..65535)
            MAX-ACCESS      read-write
            STATUS            current
            DESCRIPTION   "Lacp Priority."
      ::=  { lacpAggregatedEntry  5 }

      lacpAggPortActorOperKey   OBJECT-TYPE
        SYNTAX            UINT32
            MAX-ACCESS      read-only
            STATUS            current
            DESCRIPTION   "Lacp Port Operation Key."
      ::=  { lacpAggregatedEntry  6 }

      lacpAggPortActorOperState   OBJECT-TYPE
        SYNTAX            UINT32
            MAX-ACCESS      read-only
            STATUS            current
            DESCRIPTION   "Lacp Port Operation Status."
      ::=  { lacpAggregatedEntry  7 }

      lacpAggPortPartnerOperKey   OBJECT-TYPE
        SYNTAX            UINT32
            MAX-ACCESS      read-only
            STATUS            current
            DESCRIPTION   "Lacp Partner Operation Key."
      ::=  { lacpAggregatedEntry  8 }

      lacpAggPortPartnerOperState   OBJECT-TYPE
        SYNTAX            UINT32
            MAX-ACCESS      read-only
            STATUS            current
            DESCRIPTION   "Lacp Partner Operation Status."
      ::=  { lacpAggregatedEntry  9 }

      zxAnLacpAggPortAggregationStatus   OBJECT-TYPE
         SYNTAX    INTEGER{
                   unselected(1),
                   standby(2),
                   selected(3)
                   }
            MAX-ACCESS      read-only
            STATUS            current
            DESCRIPTION   "Lacp port aggregation status."
      ::=  { lacpAggregatedEntry  10 }
      
    lacpAggPortSubgroupId  OBJECT-TYPE
        SYNTAX         UINT32(0..2)
        MAX-ACCESS     read-write
        STATUS         current
        DESCRIPTION    
            "Subgroup ID.
            Value 0 means no port is bound to subgroup."
        DEFVAL         { 0 }
        ::=  { lacpAggregatedEntry  11 }


    zxAnLacpAggregatedPortStatsTable   OBJECT-TYPE
        SYNTAX        SEQUENCE OF ZxAnLacpAggregatedPortStatsEntry
        MAX-ACCESS    not-accessible
        STATUS        current
        DESCRIPTION   
            "A table that contains Link Aggregation Protocol statistics
             about every port that is associated with this device. A row
             appears in this table for each aggregation port."
        ::= { lacpAggregatedPara  2 }

    zxAnLacpAggregatedPortStatsEntry   OBJECT-TYPE
        SYNTAX        ZxAnLacpAggregatedPortStatsEntry
        MAX-ACCESS    not-accessible
        STATUS        current
        DESCRIPTION   
            "A list of Link Aggregation Control Protocol statistics
             for each aggregation port on this device."
        INDEX         { ifIndex }
        ::= { zxAnLacpAggregatedPortStatsTable 1 }
        
    ZxAnLacpAggregatedPortStatsEntry ::= SEQUENCE {
        zxAnLacpAggPortTxLacpdus            Counter32,
        zxAnLacpAggPortRxLacpdus            Counter32,
        zxAnLacpAggPortTxMarkerPdus         Counter32,
        zxAnLacpAggPortRxMarkerPdus         Counter32,
        zxAnLacpAggPortRxErrLacpdus         Counter32,
        zxAnLacpAggPortRxErrMarkerPdus      Counter32,
        zxAnLacpAggPortStatsReset           INTEGER
        }
    
    zxAnLacpAggPortTxLacpdus   OBJECT-TYPE
        SYNTAX        Counter32
        MAX-ACCESS    read-only
        STATUS        current
        DESCRIPTION
            "Transmitted LACPDUs on this aggregation port."
        ::= { zxAnLacpAggregatedPortStatsEntry 1 }
    
    zxAnLacpAggPortRxLacpdus   OBJECT-TYPE
        SYNTAX        Counter32
        MAX-ACCESS    read-only
        STATUS        current
        DESCRIPTION
            "Received LACPDUs on this aggregation port."
        ::= { zxAnLacpAggregatedPortStatsEntry 2 }
    
    zxAnLacpAggPortTxMarkerPdus   OBJECT-TYPE
        SYNTAX        Counter32
        MAX-ACCESS    read-only
        STATUS        current
        DESCRIPTION
            "Transmitted marker PDUs on this aggregation port."
        ::= { zxAnLacpAggregatedPortStatsEntry 3 }
    
    zxAnLacpAggPortRxMarkerPdus   OBJECT-TYPE
        SYNTAX        Counter32
        MAX-ACCESS    read-only
        STATUS        current
        DESCRIPTION
            "Received marker PDUs on this aggregation port."
        ::= { zxAnLacpAggregatedPortStatsEntry 4 }
    
    zxAnLacpAggPortRxErrLacpdus   OBJECT-TYPE
        SYNTAX        Counter32
        MAX-ACCESS    read-only
        STATUS        current
        DESCRIPTION
            "Received illegal LACPDUs on this aggregation port."
        ::= { zxAnLacpAggregatedPortStatsEntry 5 }
    
    zxAnLacpAggPortRxErrMarkerPdus   OBJECT-TYPE
        SYNTAX        Counter32
        MAX-ACCESS    read-only
        STATUS        current
        DESCRIPTION
            "Received illegal marker PDUs on this aggregation port."
        ::= { zxAnLacpAggregatedPortStatsEntry 6 }
        
    zxAnLacpAggPortStatsReset   OBJECT-TYPE
        SYNTAX      INTEGER
            {
                perfReset(1)
            }
        MAX-ACCESS  read-write
        STATUS      current
        DESCRIPTION
            "Reset LACPDUs statistics when it is set to '1'."
        ::= { zxAnLacpAggregatedPortStatsEntry 100 }
      
    zxAnLacpCapabilities OBJECT-TYPE
        SYNTAX     BITS
        {
            portSubgroup(0),
            lacpAggModeWritable(1),
            lacpSysLoadBalance(2)
        }
        MAX-ACCESS  read-only
        STATUS      current
        DESCRIPTION
            "The LACP capabilities of this equipment.
            The bit value 1 means the function represented by this bit is
            supported by this equipment.            
            portSubgroup(0): value 1 means support LACP port subgroup.
            lacpAggModeWritable(1): value 1 means support write access of 
            the aggregating mode.
            lacpSysLoadBalance(2):value 1 means NE supports 
            zxAnLacpLoadBalanceLevel and zxAnLacpSysLoadBalanceMode."
        ::= { lacpGroupObjects 1 }
        
    zxAnLacpLoadBalanceLevel OBJECT-TYPE
        SYNTAX     INTEGER {
                   aggregator(1),
                   system(2)
                   }
        MAX-ACCESS  read-only
        STATUS      current
        DESCRIPTION
            "The system LACP load balance level of this equipment.
            NE may support system level load balance or support load balance
            per aggregator, this attribute determind by hardware.
            The following is the explanation of each value of variable 
            - aggregator(1): 
              means NE can configure the load balance per aggregator,the
              related MIB object is lacpAggLoadBalanceMode.
            - systems(2): 
              means NE can configure the load balance by system,the
              related MIB object is zxAnLacpSysLoadBalanceMode."
        ::= { lacpGroupObjects 2 }

        
    zxAnLacpSysLoadBalanceMode OBJECT-TYPE
        SYNTAX     LACPLoadBalanceType
        MAX-ACCESS  read-write
        STATUS      current
        DESCRIPTION
            "The system LACP load balance mode of this equipment.
            The related MIB object is zxAnLacpLoadBalanceLevel.
            When the value of zxAnLacpLoadBalanceLevel is system(2),this MIB
            object is valid with default value src-dst-mac(4),and every
            aggregator's load balance will be determind by this MIB object.
            
            When the value of zxAnLacpLoadBalanceLevel is aggregator(1),this
            MIB object is read-only, and the value will always be
            invalid(50), then every aggregator's load balance will be determind
            by lacpAggLoadBalanceMode."
        ::= { lacpGroupObjects 3 }         

--------------------------------------------------------------------------------
-- LACP Traps
--------------------------------------------------------------------------------        
    zxAnLacpAggPortActive NOTIFICATION-TYPE
        OBJECTS { lacpAggSgId,lacpAggregatedIfName }
        STATUS  current
        DESCRIPTION
            "A zxAnLacpAggPortActive trap is sent when the agent has detected 
            that the LACP aggregation port status switch to active."
        ::= { zxAnLacpNotifications 1 }
        
    zxAnLacpAggPortInactive NOTIFICATION-TYPE
        OBJECTS { lacpAggSgId,lacpAggregatedIfName }
        STATUS  current
        DESCRIPTION
            "A zxAnLacpAggPortInactive trap is sent when the agent has detected 
            that the LACP aggregation port status switch to inactive."
        ::= { zxAnLacpNotifications 2 }    
    
    zxAnLacpAggPortInactiveAlm NOTIFICATION-TYPE
        OBJECTS { lacpAggSgId,lacpAggregatedIfName }
        STATUS  current
        DESCRIPTION
            "A zxAnLacpAggPortInactiveAlm trap is sent when the agent has 
            detected that the LACP aggregation port status switch to inactive."
        ::= { zxAnLacpNotifications 3 }

    zxAnLacpAggPortInactiveClr NOTIFICATION-TYPE
        OBJECTS { lacpAggSgId,lacpAggregatedIfName }
        STATUS  current
        DESCRIPTION
            "A zxAnLacpAggPortInactiveClr trap is sent when the agent has 
            detected that the LACP aggregation port status switch to active"
        ::= { zxAnLacpNotifications 4 }
END
