-- *****************************************************************
-- ZTE GPON ONT MANAGEMENT MIB
--
-- 12-26-2006
--
-- Copyright(c) 2006 ZTE Corporation
-- All rights reserved.
-- *****************************************************************

ZXGPON-ONTMGMT-MIB DEFINITIONS ::= BEGIN 
    IMPORTS 
        enterprises                      FROM RFC1155-SMI
        RowStatus                        FROM SNMPv2-TC
        TruthValue                       FROM SNMPv2-TC
        DisplayString                    FROM SNMPv2-TC
        IpAddress                        FROM SNMPv2-SMI
        Unsigned32                       FROM SNMPv2-SMI
        Counter64                        FROM SNMPv2-SMI
        MacAddress                       FROM SNMPv2-TC
        TEXTUAL-CONVENTION               FROM SNMPv2-TC
        MODULE-IDENTITY                  FROM SNMPv2-SMI
        OBJECT-TYPE                      FROM SNMPv2-SMI
        NOTIFICATION-TYPE                FROM SNMPv2-SMI
        ifIndex                          FROM RFC1213-MIB
        zxGponOntDevMgmtName             FROM ZXGPON-SERVICE-MIB
        zxGponOntDevMgmtTypeName         FROM ZXGPON-SERVICE-MIB
        zxGponOntDevMgmtDescription      FROM ZXGPON-SERVICE-MIB;

    zxGponOntMgmt MODULE-IDENTITY
        LAST-UPDATED "200702020000Z"  -- Feb 2, 2007"
        ORGANIZATION "ZTE Corp."
        CONTACT-INFO 
            "ZTE GPON Working Group: 
            http://www.zte.com.cn
            e-mail:
            guo.hongjian@zte.com.cn
            "
        DESCRIPTION
            "zxGponRootMib 50    , ONT management and control interface(zxGponOMCI)"
        ::= { zxGponRootMib 50 }

    zxEnterpriseMib   OBJECT IDENTIFIER ::= { enterprises 3902}
    zxPON             OBJECT IDENTIFIER ::= { zxEnterpriseMib 1012}
    zxGponRootMib     OBJECT IDENTIFIER ::= { zxPON 3 }

        zxGponONTEquipMgmt    OBJECT IDENTIFIER ::= { zxGponOntMgmt 1}
        zxGponANIMgmt         OBJECT IDENTIFIER ::= { zxGponOntMgmt 2}
        zxGponL2Mgmt         OBJECT IDENTIFIER ::= { zxGponOntMgmt 3}
        zxGponConnectMgmt     OBJECT IDENTIFIER ::= { zxGponOntMgmt 4}
        zxGponTrafficMgmt     OBJECT IDENTIFIER ::= { zxGponOntMgmt 5}
        zxGponOmciTrapsInfo   OBJECT IDENTIFIER ::= { zxGponOntMgmt 6}
        zxGponOmciTraps       OBJECT IDENTIFIER ::= { zxGponOntMgmt 7}
        zxGponOmciStatistics  OBJECT IDENTIFIER ::= { zxGponOntMgmt 8}
        zxGponTDMMgmt         OBJECT IDENTIFIER ::= { zxGponOntMgmt 9}

    OntVendorId ::= TEXTUAL-CONVENTION
        STATUS       current
        DESCRIPTION
            "Represents the vendor of the ONT."
        SYNTAX       OCTET STRING (SIZE (4))

    OntVersionId ::= TEXTUAL-CONVENTION
        STATUS       current
        DESCRIPTION
            "Represents the version of the ONT."
        SYNTAX       OCTET STRING (SIZE (14))

    OntSerialNumber ::= TEXTUAL-CONVENTION
        STATUS       current
        DESCRIPTION
            "Represents the unique for each ONT."
        SYNTAX       OCTET STRING (SIZE (8))

    OntEquipmentId ::= TEXTUAL-CONVENTION
        STATUS       current
        DESCRIPTION
            "Represents the specific type of ONT."
        SYNTAX       OCTET STRING (SIZE (20))

    zxGponOntIndexTable OBJECT-TYPE
        SYNTAX      SEQUENCE OF ZxGponOntIndexEntry
        MAX-ACCESS  not-accessible
        STATUS      current
        DESCRIPTION
            "Define the index of ONT."
        ::= { zxGponONTEquipMgmt 1 }

    zxGponOntIndexEntry OBJECT-TYPE
        SYNTAX      ZxGponOntIndexEntry
        MAX-ACCESS  not-accessible
        STATUS      current
        DESCRIPTION
            ""
        INDEX   { zxGponOltIndex, zxGponONTIndex }
        ::= { zxGponOntIndexTable 1 }

    ZxGponOntIndexEntry ::=
        SEQUENCE {
            zxGponOltIndex               INTEGER,
            zxGponONTIndex               INTEGER,
            zxGponUNIIndex               INTEGER,
            zxGponUpLinkIndex            INTEGER,
            zxGponPonIndex               INTEGER,
            zxGponTcontIndex             INTEGER,
            zxGponBridgeIndex            INTEGER,
            zxGponGemPortIndex           INTEGER,
            zxGponBridgePortType         INTEGER,
            zxGponBridgePortIndex        INTEGER,
            zxGponServiceIndex           INTEGER
        }
        
    zxGponOltIndex OBJECT-TYPE
        SYNTAX      INTEGER
        MAX-ACCESS  not-accessible
        STATUS      current
        DESCRIPTION
            "The 4 bytes index includes:
            interface type(bit31~28);shelfId(bit27~24);slotId(bit23~16);oltId(bit16~8);reserved(bit7~bit0)"
        ::= { zxGponOntIndexEntry 1}

    zxGponONTIndex OBJECT-TYPE
        SYNTAX      INTEGER
        MAX-ACCESS  not-accessible
        STATUS      current
        DESCRIPTION
            "This attribute indicates the index of ONT, from 1 to M."
        ::= { zxGponOntIndexEntry 2}

    zxGponUNIIndex OBJECT-TYPE
        SYNTAX      INTEGER
        MAX-ACCESS  read-only
        STATUS      current
        DESCRIPTION
            "This attribute indicates the index of UNI in ONT, from 1 to M.
            The first byte specifies the slot Id associated with this UNI;
            the second byte specifies the port Id associated with this UNI.(2 bytes)"
        ::= { zxGponOntIndexEntry 3}
        
    zxGponUpLinkIndex OBJECT-TYPE
        SYNTAX      INTEGER
        MAX-ACCESS  read-only
        STATUS      current
        DESCRIPTION
            "This attribute indicates the index of uplink in ONT, from 1 to M.
            The first 2 bytes specifies the slot Id and bridge group Id associated with the bridge;
            the second 2 bytes specifies the bridge port associated with this uplink.(4 bytes)"
        ::= { zxGponOntIndexEntry 4}

    zxGponPonIndex OBJECT-TYPE
        SYNTAX      INTEGER
        MAX-ACCESS  read-only
        STATUS      current
        DESCRIPTION
            "This attribute indicates the index of ANI in ONT, from 1 to M.
            The first byte specifies the slot Id associated with this PON;
            the second byte specifies the port Id associated with this PON.(2 bytes)"
        ::= { zxGponOntIndexEntry 5}
        
    zxGponTcontIndex OBJECT-TYPE
        SYNTAX      INTEGER
        MAX-ACCESS  read-only
        STATUS      current
        DESCRIPTION
            "This attribute indicates the index of T-CONT in ONT, from 1 to M."
        ::= { zxGponOntIndexEntry 6}
        
    zxGponBridgeIndex OBJECT-TYPE
        SYNTAX      INTEGER
        MAX-ACCESS  read-only
        STATUS      current
        DESCRIPTION
            "This attribute indicates the index of MAC bridge in ONT, from 1 to M.
            The first byte specifies the slot Id associated with this MAC bridge;
            the second byte specifies the bridge group Id associated with this MAC bridge.(2 bytes)"
        ::= { zxGponOntIndexEntry 7}
        
    zxGponGemPortIndex OBJECT-TYPE
        SYNTAX      INTEGER
        MAX-ACCESS  read-only
        STATUS      current
        DESCRIPTION
        "This attribute specifies the gemport id."
        REFERENCE   "G.984.4 & G.983.2"
        ::= { zxGponOntIndexEntry 8 }

    zxGponBridgePortType OBJECT-TYPE
        SYNTAX      INTEGER{
                    ethuni(1),
                    uplink(2),
                    iphost(3)
                    }
        MAX-ACCESS  read-only
        STATUS      current
        DESCRIPTION
        "This attribute specifies the bridge port type.
         UNI/UPLINK/IPHOST"
        REFERENCE   "G.984.4"
        ::= { zxGponOntIndexEntry 9 }

    zxGponBridgePortIndex OBJECT-TYPE
        SYNTAX      INTEGER
        MAX-ACCESS  read-only
        STATUS      current
        DESCRIPTION
        "This attribute specifies the bridge port index.
        type    size         MSB                LSB
        ------------------------------------------------
        UNI:    2bytes ----- slot(1byte)/port(1byte)
        UPLINK: 4bytes ----- slot(1byte)/bridge(1byte)/port(2byte)
        IPHOST: 1byte  ----- hostid(1byte)
        "
        REFERENCE   "G.984.4"
        ::= { zxGponOntIndexEntry 10 }

    zxGponServiceIndex OBJECT-TYPE
        SYNTAX      INTEGER
        MAX-ACCESS  not-accessible
        STATUS      current
        DESCRIPTION
        "This attribute specifies the index of the service."
        REFERENCE   "G.984.4"
        ::= { zxGponOntIndexEntry 11 }

    zxGponONTTable    OBJECT-TYPE
        SYNTAX      SEQUENCE OF ZxGponONTEntry
        MAX-ACCESS  not-accessible
        STATUS      current
        DESCRIPTION
            ""
        ::= { zxGponONTEquipMgmt 2 }
        
    zxGponONTEntry OBJECT-TYPE
        SYNTAX      ZxGponONTEntry
        MAX-ACCESS  not-accessible
        STATUS      current
        DESCRIPTION
            "It is entry in the zxGponONTTable."
        INDEX   { zxGponOltIndex, zxGponONTIndex }
        ::= { zxGponONTTable 1 }
        
    ZxGponONTEntry ::=
        SEQUENCE {
            zxGponONTVendorId              OntVendorId,
            zxGponONTVersion               OntVersionId,
            zxGponONTSerialNum             OntSerialNumber,
            zxGponONTTrafficOpt            INTEGER,
            zxGponONTVpVcCrossOpt          INTEGER,
            zxGponONTBatteryBackup         TruthValue,
            zxGponONTAdminState            INTEGER,
            zxGponONTOperState             INTEGER,
            zxGponONTEquipId               OntEquipmentId,
            zxGponONTOmccVersion           INTEGER,
            zxGponONTVendorProductCode     INTEGER,
            zxGponONTSecurityCap           INTEGER,
            zxGponONTSecurityMode          INTEGER,
            zxGponONTTotalPrioQueueNum     INTEGER,
            zxGponONTTotalTrafficSchNum    INTEGER,
            zxGponONTMode                  INTEGER
        }

    zxGponONTVendorId OBJECT-TYPE
        SYNTAX      OntVendorId
        MAX-ACCESS  read-only
        STATUS      current
        DESCRIPTION
        "This attribute identifies the vendor of the ONT, and is the same as the 4 most significant bytes of the ONT serial number as specified in ITU-T Rec. G.983.1. 
        Upon autonomous instantiation, this attribute consists of all spaces.(4 bytes)"
        REFERENCE   "G.984.4 section 9.1.1 ONT-G"
        ::= { zxGponONTEntry 1 }

    zxGponONTVersion OBJECT-TYPE
        SYNTAX      OntVersionId
        MAX-ACCESS  read-only
        STATUS      current
        DESCRIPTION
        "This attribute identifies the version of the ONT as defined by the vendor. The printable value of '0' 
        is used when version information is not available or applicable to the ONT being represented. 
        Upon autonomous instantiation, this attribute consists of all spaces.(14 bytes)"
        REFERENCE   "G.984.4 section 9.1.1 ONT-G"
        ::= { zxGponONTEntry 2 }

    zxGponONTSerialNum OBJECT-TYPE
        SYNTAX      OntSerialNumber
        MAX-ACCESS  read-only
        STATUS      current
        DESCRIPTION
        "The serial number is unique for each ONT. 
        The first four bytes are the ASCII encoded vendor ID four letter mnemonic.
        The second four bytes are a binary encoded 'serial number', under the complete control 
        of the vendor in question.
        Upon autonomous instantiation, this attribute consists of four spaces and four null characters.(8 bytes)"
        REFERENCE   "G.984.4 section 9.1.1 ONT-G"
        ::= { zxGponONTEntry 3 }

    zxGponONTTrafficOpt OBJECT-TYPE
        SYNTAX      INTEGER{
                    priQueueScheduler(1),
                    cellRateControl(2)
                    }
        MAX-ACCESS  read-only
        STATUS      current
        DESCRIPTION
        "This attribute identifies the upstream traffic management function implememted 
        in the ONT.
        1) 'Priority controlled and flexibly scheduled upstream traffic' (0x00): The traffic
        scheduler and priority queue mechanism are used for the upstream traffic.
        2) 'Cell rate controlled upstream traffic' (0x01): The maximum upstream traffic of each
        individual connection is guaranteed. 
        Note that the Traffic management option will not apply to downstream traffic.
        In other words, there is no need for a traffic descriptor for the downstream direction 
        and downstream priority queues can be used. 
        Upon autonomous instantiation, this attribute is set to the value that describes the 
        ONT's implementation. The OLT must adapt its model to conform to the ONT's selection.(1 byte)"
        REFERENCE   "G.984.4 section 9.1.1 ONT-G"
        ::= { zxGponONTEntry 4 }
        
    zxGponONTVpVcCrossOpt OBJECT-TYPE
        SYNTAX      INTEGER{
                    null(1),
                    vp(2),
                    vpvc(3)
                    }
        MAX-ACCESS  read-only
        STATUS      current
        DESCRIPTION
            "It identifies the support of ATM VP or VC cross-connection management
             functions for the interworking connections to non ATM UNIs. 
             0 means no cross-connection management functions are modelled. 
             1 means ATM VP cross-connection management functions are modelled.
             2 means ATM VP and VC cross-connection management functions are modelled."
        REFERENCE
            "G.984.4 Section 9.1.1 ONT-G"
        ::= { zxGponONTEntry 5}

    zxGponONTBatteryBackup OBJECT-TYPE
        SYNTAX      TruthValue
        MAX-ACCESS  read-write
        STATUS      current
        DESCRIPTION
            "This attribute provides a Boolean indication of whether or not the ONT/NT supports battery backup.
            False will indicate that no battery is provisioned; true indicates that a battery is provisioned.
            Upon autonomous instantiation, this attribute is set to false.(1 byte)"
        REFERENCE
            "G.984.4 Section 9.1.1 ONT-G"
        ::= { zxGponONTEntry 6}

    zxGponONTAdminState OBJECT-TYPE
        SYNTAX      INTEGER{
                    unlock(1),
                    lock(2)
                    }
        MAX-ACCESS  read-write
        STATUS      current
        DESCRIPTION
            "This attribute is used to activate (unlock: value 0x00) and deactivate (lock: value 0x01) 
            the functions performed by instances of this managed entity.(1 byte)"
        REFERENCE
            "G.984.4 Section 9.1.1 ONT-G"
        ::= { zxGponONTEntry 7}

    zxGponONTOperState OBJECT-TYPE
        SYNTAX      INTEGER{
                    enable(1),
                    disable(2)
                    }
        MAX-ACCESS  read-only
        STATUS      current
        DESCRIPTION
            "This attribute indicates whether or not a managed entity is capable of 
            performing its task. Valid values are enabled (0x00) and disabled (0x01).(1 byte)"
        REFERENCE
            "G.984.4 Section 9.1.1 ONT-G"
        ::= { zxGponONTEntry 8}

    zxGponONTEquipId OBJECT-TYPE
        SYNTAX      OntEquipmentId
        MAX-ACCESS  read-only
        STATUS      current
        DESCRIPTION
        "This attribute may be used to identify the specific type of ONT. In North America, 
        this may be used for the equipment CLEI code.(20 bytes)"
        REFERENCE   "G.984.4 section 9.1.2 ONT2-G"
        ::= { zxGponONTEntry 9 }

    zxGponONTOmccVersion OBJECT-TYPE
        SYNTAX      INTEGER
        MAX-ACCESS  read-only
        STATUS      current
        DESCRIPTION
        "This attribute is used to identify the specific version of the OMCC  
        protocol being used by the ONT. This is used to allow the OLT to manage a 
        network with ONTs that support different OMCC versions. 
        The only valid value at this time is 0x80. Future versions will be added sequentially.
        Upon autonomous instantiation, this attribute consists of the value 0x80.(1 byte)"
        REFERENCE   "G.984.4 section 9.1.2 ONT2-G"
        ::= { zxGponONTEntry 10 }

    zxGponONTVendorProductCode OBJECT-TYPE
        SYNTAX      INTEGER
        MAX-ACCESS  read-only
        STATUS      current
        DESCRIPTION
        "This attribute is used to provide a vendor-specific product code for the ONT.(2 bytes)"
        REFERENCE   "G.984.4 section 9.1.2 ONT2-G"
        ::= { zxGponONTEntry 11 }

    zxGponONTSecurityCap OBJECT-TYPE
        SYNTAX      INTEGER(0..255)
        MAX-ACCESS  read-only
        STATUS      current
        DESCRIPTION
        "This attribute is used to advertise the advanced security modes of the ONT. 
        The following codepoints are defined: 
        0: Reserved for future use;
        1: AES encryption of the downstream payload is supported;
        2..255: Reserved for future use.(1 byte)"
        REFERENCE   "G.984.4 section 9.1.2 ONT2-G"
        ::= { zxGponONTEntry 12 }
        
    zxGponONTSecurityMode OBJECT-TYPE
        SYNTAX      INTEGER(0..255)
        MAX-ACCESS  read-write
        STATUS      current
        DESCRIPTION
            "This attribute is used to select the advanced security mode for the ONT.
             Note that all secure VPs/VCs or GEM ports in an ONT must use the same security mode at
             any time. The following codepoints are defined:  
             0: Reserved for future use;
             1: AES algorithm for unicast traffic will be used;
             2..255: Reserved for future use.
             Upon autonomous instantiation this attribute consists of the value 0x01.(1 byte)"
        REFERENCE
            "G.984.4 Section 9.1.2 ONT2-G"
        ::= { zxGponONTEntry 13}

    zxGponONTTotalPrioQueueNum OBJECT-TYPE
        SYNTAX      INTEGER
        MAX-ACCESS  read-only
        STATUS      current
        DESCRIPTION
            "This attribute provides a total number of priority queues which are not associated with the PON IF circuit pack. 
            Maximum value is 0x0FFF. Upautonomous instantiation, this attribute is set to zero.(2 bytes)"
        REFERENCE
            "G.984.4 Section 9.1.2 ONT2-G"
        ::= { zxGponONTEntry 14}

    zxGponONTTotalTrafficSchNum OBJECT-TYPE
        SYNTAX      INTEGER
        MAX-ACCESS  read-only
        STATUS      current
        DESCRIPTION
            "This attribute provides a total number of Traffic Schedulers which 
            are not associated with the PON IF circuit pack. The ONT supports NULL function, 
            HOL scheduling and WRR from the priority control and guarantee of 
            minimum rate control points of view, respectively. 
            If the ONT does noScheduler, this attribute should be 0x00. 
            Upon autonomous instantiation, this attribute is set to zero.(1 byte)"
        REFERENCE
            "G.984.4 Section 9.1.2 ONT2-G"
        ::= { zxGponONTEntry 15}

    zxGponONTMode OBJECT-TYPE
        SYNTAX      INTEGER{
                    atmOnly(1),
                    gemOnly(2),
                    dual(3)
                    }
        MAX-ACCESS  read-only
        STATUS      current
        DESCRIPTION
            "This attribute identifies whether the ONT can operate in ATM-only mode (0x00), 
            GEM-only mode (0x01), or dual (both ATM and GEM) mode (0x02).(1 byte)"
        REFERENCE
            "G.984.4 Section 9.1.2 ONT2-G"
        ::= { zxGponONTEntry 16}

--ONT action
    zxGponONTActionTable    OBJECT-TYPE
        SYNTAX      SEQUENCE OF ZxGponONTActionEntry
        MAX-ACCESS  not-accessible
        STATUS      current
        DESCRIPTION
            ""
        ::= { zxGponONTEquipMgmt 3 }
        
    zxGponONTActionEntry OBJECT-TYPE
        SYNTAX      ZxGponONTActionEntry
        MAX-ACCESS  not-accessible
        STATUS      current
        DESCRIPTION
            "It is entry in the zxGponONTActionTable."
        INDEX   { zxGponOltIndex, zxGponONTIndex }
        ::= { zxGponONTActionTable 1 }
        
    ZxGponONTActionEntry ::=
        SEQUENCE {
            zxGponONTReboot              TruthValue,
            zxGponONTTest                TruthValue,
            zxGponONTSyncTime            TruthValue,
            zxGponONTRestore             TruthValue,
            zxGponONTTestResult          INTEGER
        }

    zxGponONTReboot OBJECT-TYPE
        SYNTAX      TruthValue
        MAX-ACCESS  read-write
        STATUS      current
        DESCRIPTION
        "This attribute identifies the action of the ONT."
        REFERENCE   "G.984.4 section 9.1.1 ONT-G"
        ::= { zxGponONTActionEntry 1 }
        
    zxGponONTTest OBJECT-TYPE
        SYNTAX      TruthValue
        MAX-ACCESS  read-write
        STATUS      current
        DESCRIPTION
        "This attribute identifies the action of the ONT."
        REFERENCE   "G.984.4 section 9.1.1 ONT-G"
        ::= { zxGponONTActionEntry 2 }
        
    zxGponONTSyncTime OBJECT-TYPE
        SYNTAX      TruthValue
        MAX-ACCESS  read-write
        STATUS      current
        DESCRIPTION
        "This attribute identifies the action of the ONT."
        REFERENCE   "G.984.4 section 9.1.1 ONT-G"
        ::= { zxGponONTActionEntry 3 }
        
    zxGponONTRestore OBJECT-TYPE
        SYNTAX      TruthValue
        MAX-ACCESS  read-write
        STATUS      current
        DESCRIPTION
        "This attribute identifies the action of the ONT. That is resetting the ONT's MIB."
        REFERENCE   "G.984.4 section 9.1.1 ONT-G"
        ::= { zxGponONTActionEntry 4 }

    zxGponONTTestResult OBJECT-TYPE
        SYNTAX      INTEGER{
                    pass(1),
                    fail(2)
                    }
        MAX-ACCESS  read-only
        STATUS      current
        DESCRIPTION
        "This attribute identifies the result of testing ONT."
        REFERENCE   "G.984.4 section 9.1.1 ONT-G"
        ::= { zxGponONTActionEntry 5 }

--software image
    zxGponSoftwareImageTable    OBJECT-TYPE
        SYNTAX      SEQUENCE OF ZxGponSoftwareImageEntry
        MAX-ACCESS  not-accessible
        STATUS      current
        DESCRIPTION
            "This managed entity represents a program stored in the ONT.
            Two instances of the software image managed entity are contained in an instance of 
            an ONT or equipment managed entity whose software is independently managed."
        REFERENCE   "G.983.2 section 7.1.7 Software image"
        ::= { zxGponONTEquipMgmt 4 }
        
    zxGponSoftwareImageEntry OBJECT-TYPE
        SYNTAX      ZxGponSoftwareImageEntry
        MAX-ACCESS  not-accessible
        STATUS      current
        DESCRIPTION
            "It is entry in the zxGponSoftwareImageTable."
        INDEX   { zxGponOltIndex, zxGponONTIndex, zxGponSoftwareImageIndex }
        ::= { zxGponSoftwareImageTable 1 }
        
    ZxGponSoftwareImageEntry ::=
        SEQUENCE {
            zxGponSoftwareImageIndex                   INTEGER,
            zxGponSoftwareImageVersion                 OCTET STRING,
            zxGponSoftwareImageIsCommitted             TruthValue,
            zxGponSoftwareImageIsActive                TruthValue,
            zxGponSoftwareImageIsValid                 TruthValue
        }

    zxGponSoftwareImageIndex OBJECT-TYPE
        SYNTAX      INTEGER
        MAX-ACCESS  read-only
        STATUS      current
        DESCRIPTION
        "This attribute provides a unique number for each instance of this managed entity. 
        The number consists of a two-byte field. The first field (MSB) identifies the ME 
        instance (ONT (value 0x00) or circuit pack slot (value 0x01-0xFF) containing the 
        associated software image ME. The second field (LSB) distinguishes between the 
        two (redundant) software image ME instances (values 0x00 and 0x01).(2 bytes)"
        REFERENCE   "G.983.2 section 7.1.7 Software image"
        ::= { zxGponSoftwareImageEntry 1 }
        
    zxGponSoftwareImageVersion OBJECT-TYPE
        SYNTAX      OCTET STRING(SIZE(0..14))
        MAX-ACCESS  read-only
        STATUS      current
        DESCRIPTION
        "This attribute identifies the version of the software. 
        Upon autonomous instantiation, this attribute consists of all spaces.(14 bytes)"
        REFERENCE   "G.983.2 section 7.1.7 Software image"
        ::= { zxGponSoftwareImageEntry 2 }
        
    zxGponSoftwareImageIsCommitted OBJECT-TYPE
        SYNTAX      TruthValue
        MAX-ACCESS  read-only
        STATUS      current
        DESCRIPTION
        "This attribute indicates whether the associated software image is 'committed' (value 0x01) 
        or 'uncommitted' (value 0x00). By definition, the 'committed' software image will be loaded 
        and executed upon a reboot of the ONT and/or associated circuit pack.Upon autonomous 
        instantiation, this attribute of instance 0 shall be initialized to 'committed' and 
        this attribute of instance 1 shall be initialized to 'uncommitted'.(1 byte)"
        REFERENCE   "G.983.2 section 7.1.7 Software image"
        ::= { zxGponSoftwareImageEntry 3 }
        
    zxGponSoftwareImageIsActive OBJECT-TYPE
        SYNTAX      TruthValue
        MAX-ACCESS  read-only
        STATUS      current
        DESCRIPTION
        "This attribute indicates whether the associated software image is 'active' (value 0x01) 
        or 'inactive' (value 0x00). By definition, the active software image is one that is 
        currently loaded and executing in the ONT (or associated circuit pack).Upon autonomous 
        instantiation, this attribute of instance 0 shall be initialized to 'active' and this 
        attribute of instance 1 shall be initialized to 'inactive'.(1 byte)"
        REFERENCE   "G.983.2 section 7.1.7 Software image"
        ::= { zxGponSoftwareImageEntry 4 }
        
    zxGponSoftwareImageIsValid OBJECT-TYPE
        SYNTAX      TruthValue
        MAX-ACCESS  read-only
        STATUS      current
        DESCRIPTION
        "This attribute indicates whether the associated software image is 'valid' (value 0x01) 
        or 'invalid (value 0x00). By definition, a software image is 'valid' if it has been 
        verified to be an executable code image.Upon autonomous instantiation, the associated 
        code image is verified and this attribute is set according to the result of this verification.(1 byte)"
        REFERENCE   "G.983.2 section 7.1.7 Software image"
        ::= { zxGponSoftwareImageEntry 5 }

--software image action
    zxGponSoftwareImageActionTable    OBJECT-TYPE
        SYNTAX      SEQUENCE OF ZxGponSoftwareImageActionEntry
        MAX-ACCESS  not-accessible
        STATUS      current
        DESCRIPTION
            "This managed entity represents a program management in the ONT."
        REFERENCE   "G.983.2 section 7.1.7 Software image"
        ::= { zxGponONTEquipMgmt 5 }

    zxGponSoftwareImageActionEntry OBJECT-TYPE
        SYNTAX      ZxGponSoftwareImageActionEntry
        MAX-ACCESS  not-accessible
        STATUS      current
        DESCRIPTION
            "It is entry in the zxGponSoftwareImageActionTable."
        INDEX   { zxGponOltIndex }
        ::= { zxGponSoftwareImageActionTable 1 }
        
    ZxGponSoftwareImageActionEntry ::=
        SEQUENCE {
            zxGponSoftwareImageActionDownload              TruthValue,
            zxGponSoftwareImageActionUpdate                TruthValue,
            zxGponSoftwareImageActionDelete                TruthValue,
            zxGponSoftwareImageActionVersion               OCTET STRING,
            zxGponSoftwareImageActionOntList               OCTET STRING,
            zxGponSoftwareImageActionOntNum                INTEGER,
            zxGponSoftwareImageActionOntSlot               INTEGER,
            zxGponSoftwareImageActionUpdateAbort           TruthValue
        }

    zxGponSoftwareImageActionDownload OBJECT-TYPE
        SYNTAX      TruthValue
        MAX-ACCESS  read-write
        STATUS      current
        DESCRIPTION
        "This attribute initiates the version downloading from OLT to ONT.
        'zxGponSoftwareImageActionVersion' must be specified when downloading."
        REFERENCE   "G.983.2 section 7.1.7 Software image"
        ::= { zxGponSoftwareImageActionEntry 1 }
    
    zxGponSoftwareImageActionUpdate OBJECT-TYPE
        SYNTAX      TruthValue
        MAX-ACCESS  read-write
        STATUS      current
        DESCRIPTION
        "This attribute initiates the version updating of ONTs.
        'zxGponSoftwareImageActionOntList','zxGponSoftwareImageActionOntNum' and 
        'zxGponSoftwareImageActionVersion' must be specified when updating."
        REFERENCE   "G.983.2 section 7.1.7 Software image"
        ::= { zxGponSoftwareImageActionEntry 2 }
        
    zxGponSoftwareImageActionDelete OBJECT-TYPE
        SYNTAX      TruthValue
        MAX-ACCESS  read-write
        STATUS      current
        DESCRIPTION
        "This attribute initiates the version cache deleting.
        'zxGponSoftwareImageActionVersion' must be specified."
        REFERENCE   "G.983.2 section 7.1.7 Software image"
        ::= { zxGponSoftwareImageActionEntry 3 }

    zxGponSoftwareImageActionVersion OBJECT-TYPE
        SYNTAX      OCTET STRING(SIZE(0..14))
        MAX-ACCESS  read-write
        STATUS      current
        DESCRIPTION
        "This attribute specifies the version name."
        REFERENCE   "G.983.2 section 7.1.7 Software image"
        ::= { zxGponSoftwareImageActionEntry 4 }
        
    zxGponSoftwareImageActionOntList OBJECT-TYPE
        SYNTAX      OCTET STRING(SIZE(1..128))
        MAX-ACCESS  read-write
        STATUS      current
        DESCRIPTION
        "This attribute specifies the ONT list who will be told to update the version."
        REFERENCE   "G.983.2 section 7.1.7 Software image"
        ::= { zxGponSoftwareImageActionEntry 5 }

    zxGponSoftwareImageActionOntNum OBJECT-TYPE
        SYNTAX      INTEGER(1..128)
        MAX-ACCESS  read-write
        STATUS      current
        DESCRIPTION
        "This attribute specifies the ONT number who will be told to update the version."
        REFERENCE   "G.983.2 section 7.1.7 Software image"
        ::= { zxGponSoftwareImageActionEntry 6 }
        
    zxGponSoftwareImageActionOntSlot OBJECT-TYPE
        SYNTAX      INTEGER(0..255)
        MAX-ACCESS  read-write
        STATUS      current
        DESCRIPTION
        "This attribute specifies the slot of ONT who will be told to update the version.
        If updating the version of ONT itshelf, this attribute can be specified as 0 or not specified."
        REFERENCE   "G.983.2 section 7.1.7 Software image"
        ::= { zxGponSoftwareImageActionEntry 7 }

    zxGponSoftwareImageActionUpdateAbort OBJECT-TYPE
        SYNTAX      TruthValue
        MAX-ACCESS  read-write
        STATUS      current
        DESCRIPTION
        "This attribute aborts the version updating of ONTs.
        'zxGponSoftwareImageActionOntList','zxGponSoftwareImageActionOntNum' and 
        'zxGponSoftwareImageActionOntSlot' must be specified when aborting."
        REFERENCE   "G.983.2 section 7.1.7 Software image"
        ::= { zxGponSoftwareImageActionEntry 8 }

--software image maintenance
    zxGponSoftwareImageMaintTable    OBJECT-TYPE
        SYNTAX      SEQUENCE OF ZxGponSoftwareImageMaintEntry
        MAX-ACCESS  not-accessible
        STATUS      current
        DESCRIPTION
            "This managed entity represents the image maintenance in the ONT."
        REFERENCE   "G.983.2 section 7.1.7 Software image"
        ::= { zxGponONTEquipMgmt 7 }

    zxGponSoftwareImageMaintEntry OBJECT-TYPE
        SYNTAX      ZxGponSoftwareImageMaintEntry
        MAX-ACCESS  not-accessible
        STATUS      current
        DESCRIPTION
            "It is entry in the zxGponSoftwareImageMaintTable."
        INDEX   { zxGponOltIndex }
        ::= { zxGponSoftwareImageMaintTable 1 }
        
    ZxGponSoftwareImageMaintEntry ::=
        SEQUENCE {
            zxGponSoftwareImageMaintType                  INTEGER,
            zxGponSoftwareImageMaintOntList               OCTET STRING,
            zxGponSoftwareImageMaintOntNum                INTEGER,
            zxGponSoftwareImageMaintImgIndex              INTEGER
        }

    zxGponSoftwareImageMaintType OBJECT-TYPE
        SYNTAX      INTEGER{
                    activate(1),
                    commit(2)       
                    }
        MAX-ACCESS  read-write
        STATUS      current
        DESCRIPTION
        "This attribute initiates the maintenance type of image(activate or commit)."
        REFERENCE   "G.983.2 section 7.1.7 Software image"
        ::= { zxGponSoftwareImageMaintEntry 1 }
        
    zxGponSoftwareImageMaintOntList OBJECT-TYPE
        SYNTAX      OCTET STRING(SIZE(1..128))
        MAX-ACCESS  read-write
        STATUS      current
        DESCRIPTION
        "This attribute specifies the ONT list who will be told to activate or commit the version."
        REFERENCE   "G.983.2 section 7.1.7 Software image"
        ::= { zxGponSoftwareImageMaintEntry 2 }

    zxGponSoftwareImageMaintOntNum OBJECT-TYPE
        SYNTAX      INTEGER(1..128)
        MAX-ACCESS  read-write
        STATUS      current
        DESCRIPTION
        "This attribute specifies the ONT number who will be told to update the version."
        REFERENCE   "G.983.2 section 7.1.7 Software image"
        ::= { zxGponSoftwareImageMaintEntry 3 }

    zxGponSoftwareImageMaintImgIndex OBJECT-TYPE
        SYNTAX      INTEGER
        MAX-ACCESS  read-write
        STATUS      current
        DESCRIPTION
        "This two-byte field is composed of 'onu slot' and 'region id'.
        The MSB is 'onu slot', usually as 0;
        The LSB is 'region id', sepecified as 0 or 1."
        REFERENCE   "G.983.2 section 7.1.7 Software image"
        ::= { zxGponSoftwareImageMaintEntry 4 }

--software image update status
    zxGponSoftwareImageUpdateStatusTable    OBJECT-TYPE
        SYNTAX      SEQUENCE OF ZxGponSoftwareImageUpdateStatusEntry
        MAX-ACCESS  not-accessible
        STATUS      current
        DESCRIPTION
            "This managed entity represents the image update status of the ONT."
        REFERENCE   "G.983.2 section 7.1.7 Software image"
        ::= { zxGponONTEquipMgmt 8 }

    zxGponSoftwareImageUpdateStatusEntry OBJECT-TYPE
        SYNTAX      ZxGponSoftwareImageUpdateStatusEntry
        MAX-ACCESS  not-accessible
        STATUS      current
        DESCRIPTION
            "It is entry in the zxGponSoftwareImageUpdateStatusTable."
        INDEX   { zxGponOltIndex, zxGponONTIndex }
        ::= { zxGponSoftwareImageUpdateStatusTable 1 }
        
    ZxGponSoftwareImageUpdateStatusEntry ::=
        SEQUENCE {
            zxGponSoftwareImageUpdateStatus                  INTEGER,
            zxGponSoftwareImageUpdateStatusAbortReason       INTEGER,
            zxGponSoftwareImageUpdateStatusPercent           INTEGER,
            zxGponSoftwareImageUpdateStatusCurUsedVerName    OCTET STRING,
            zxGponSoftwareImageUpdateStatusCurUsedVerTime    OCTET STRING,
            zxGponSoftwareImageUpdateStatusUpdatingVerName   OCTET STRING,
            zxGponSoftwareImageUpdateStatusUpdatingVerTime   OCTET STRING
        }

    zxGponSoftwareImageUpdateStatus OBJECT-TYPE
        SYNTAX      INTEGER{
                    not-start(1),
                    abort(2),
                    downloading(3),
                    commiting(4),
                    activating(5),
                    done(6)
                    }
        MAX-ACCESS  read-only
        STATUS      current
        DESCRIPTION
        "This attribute indicates the status of updaing.0xFFFF indicates status of 'NA'."
        REFERENCE   "G.983.2 section 7.1.7 Software image"
        ::= { zxGponSoftwareImageUpdateStatusEntry 1 }
        
    zxGponSoftwareImageUpdateStatusAbortReason OBJECT-TYPE
        SYNTAX      INTEGER{
                    none(1),
                    download-error(2),
                    commit-error(3),
                    activate-error(4),
                    crc-error(5),
                    valid-error(6),
                    user-abort(7)
                    }
        MAX-ACCESS  read-only
        STATUS      current
        DESCRIPTION
        "This attribute indicates the reason when abort."
        REFERENCE   "G.983.2 section 7.1.7 Software image"
        ::= { zxGponSoftwareImageUpdateStatusEntry 2 }

    zxGponSoftwareImageUpdateStatusPercent OBJECT-TYPE
        SYNTAX      INTEGER(0..100)
        MAX-ACCESS  read-only
        STATUS      current
        DESCRIPTION
        "This attribute indicates the percent of updating."
        REFERENCE   "G.983.2 section 7.1.7 Software image"
        ::= { zxGponSoftwareImageUpdateStatusEntry 3 }

    zxGponSoftwareImageUpdateStatusCurUsedVerName OBJECT-TYPE
        SYNTAX      OCTET STRING
        MAX-ACCESS  read-only
        STATUS      current
        DESCRIPTION
        "This attribute indicates the name of the version current used."
        REFERENCE   "G.983.2 section 7.1.7 Software image"
        ::= { zxGponSoftwareImageUpdateStatusEntry 4 }

    zxGponSoftwareImageUpdateStatusCurUsedVerTime OBJECT-TYPE
        SYNTAX      OCTET STRING
        MAX-ACCESS  read-only
        STATUS      current
        DESCRIPTION
        "This attribute indicates the time of the version current used."
        REFERENCE   "G.983.2 section 7.1.7 Software image"
        ::= { zxGponSoftwareImageUpdateStatusEntry 5 }

    zxGponSoftwareImageUpdateStatusUpdatingVerName OBJECT-TYPE
        SYNTAX      OCTET STRING
        MAX-ACCESS  read-only
        STATUS      current
        DESCRIPTION
        "This attribute indicates the name of the version updating."
        REFERENCE   "G.983.2 section 7.1.7 Software image"
        ::= { zxGponSoftwareImageUpdateStatusEntry 6 }

    zxGponSoftwareImageUpdateStatusUpdatingVerTime OBJECT-TYPE
        SYNTAX      OCTET STRING
        MAX-ACCESS  read-only
        STATUS      current
        DESCRIPTION
        "This attribute indicates the time of the version updating."
        REFERENCE   "G.983.2 section 7.1.7 Software image"
        ::= { zxGponSoftwareImageUpdateStatusEntry 7 }

    zxGponONTPowerSheddingTable    OBJECT-TYPE
        SYNTAX      SEQUENCE OF ZxGponONTPowerSheddingEntry
        MAX-ACCESS  not-accessible
        STATUS      current
        DESCRIPTION
            "This managed entity models the ONT's ability to shed services when the ONT goes into battery operation mode after AC power failure."
        ::= { zxGponONTEquipMgmt 6 }
        
    zxGponONTPowerSheddingEntry OBJECT-TYPE
        SYNTAX      ZxGponONTPowerSheddingEntry
        MAX-ACCESS  not-accessible
        STATUS      current
        DESCRIPTION
            "It is entry in the zxGponONTPowerSheddingTable."
        INDEX   { zxGponOltIndex, zxGponONTIndex }
        ::= { zxGponONTPowerSheddingTable 1 }
        
    ZxGponONTPowerSheddingEntry ::=
        SEQUENCE {
            zxGponONTPowerSheddingRestoreInterval                INTEGER,
            zxGponONTPowerSheddingDataSheddingInterval           INTEGER,
            zxGponONTPowerSheddingVoiceSheddingInterval          INTEGER,
            zxGponONTPowerSheddingVideoOverlaySheddingInterval   INTEGER,
            zxGponONTPowerSheddingVideoReturnSheddingInterval    INTEGER,
            zxGponONTPowerSheddingDSLSheddingInterval            INTEGER,
            zxGponONTPowerSheddingATMSheddingInterval            INTEGER,
            zxGponONTPowerSheddingCESSheddingInterval            INTEGER,
            zxGponONTPowerSheddingFrameSheddingInterval          INTEGER,
            zxGponONTPowerSheddingSONETSheddingInterval          INTEGER,
            zxGponONTPowerSheddingSheddingStatus                 INTEGER
        }

    zxGponONTPowerSheddingRestoreInterval OBJECT-TYPE
        SYNTAX      INTEGER
        MAX-ACCESS  read-write
        STATUS      current
        DESCRIPTION
        "The time delay, in seconds, before resetting shedding timers after full power restoration. 
              Upon ME instantiation, the ONT sets this attribute to 0. (R, W) (mandatory) (2 bytes)"
        REFERENCE   "G.984.4 section 9.1.7 ONT power shedding"
        ::= { zxGponONTPowerSheddingEntry 1 }

    zxGponONTPowerSheddingDataSheddingInterval OBJECT-TYPE
        SYNTAX      INTEGER
        MAX-ACCESS  read-write
        STATUS      current
        DESCRIPTION
        "For each class of service, an interval attribute is defined below. 
               The value 0 disables power shedding, while the value 1 enables immediate power shed, that is, as soon as AC power fails. 
              Other values specify the time, in seconds, to keep the service active after AC failure before shutting them down and shedding power. 
              Upon ME instantiation, the ONT sets each of the interval attributes to 0.(2 bytes)"
        REFERENCE   "G.984.4 section 9.1.7 ONT power shedding"
        ::= { zxGponONTPowerSheddingEntry 2 }

    zxGponONTPowerSheddingVoiceSheddingInterval OBJECT-TYPE
        SYNTAX      INTEGER
        MAX-ACCESS  read-write
        STATUS      current
        DESCRIPTION
        "For each class of service, an interval attribute is defined below. 
               The value 0 disables power shedding, while the value 1 enables immediate power shed, that is, as soon as AC power fails. 
              Other values specify the time, in seconds, to keep the service active after AC failure before shutting them down and shedding power. 
              Upon ME instantiation, the ONT sets each of the interval attributes to 0.(2 bytes)"
        REFERENCE   "G.984.4 section 9.1.7 ONT power shedding"
        ::= { zxGponONTPowerSheddingEntry 3 }

    zxGponONTPowerSheddingVideoOverlaySheddingInterval OBJECT-TYPE
        SYNTAX      INTEGER
        MAX-ACCESS  read-write
        STATUS      current
        DESCRIPTION
        "For each class of service, an interval attribute is defined below. 
               The value 0 disables power shedding, while the value 1 enables immediate power shed, that is, as soon as AC power fails. 
              Other values specify the time, in seconds, to keep the service active after AC failure before shutting them down and shedding power. 
              Upon ME instantiation, the ONT sets each of the interval attributes to 0.(2 bytes)"
        REFERENCE   "G.984.4 section 9.1.7 ONT power shedding"
        ::= { zxGponONTPowerSheddingEntry 4 }

    zxGponONTPowerSheddingVideoReturnSheddingInterval OBJECT-TYPE
        SYNTAX      INTEGER
        MAX-ACCESS  read-write
        STATUS      current
        DESCRIPTION
        "For each class of service, an interval attribute is defined below. 
               The value 0 disables power shedding, while the value 1 enables immediate power shed, that is, as soon as AC power fails. 
              Other values specify the time, in seconds, to keep the service active after AC failure before shutting them down and shedding power. 
              Upon ME instantiation, the ONT sets each of the interval attributes to 0.(2 bytes)"
        REFERENCE   "G.984.4 section 9.1.7 ONT power shedding"
        ::= { zxGponONTPowerSheddingEntry 5 }

    zxGponONTPowerSheddingDSLSheddingInterval OBJECT-TYPE
        SYNTAX      INTEGER
        MAX-ACCESS  read-write
        STATUS      current
        DESCRIPTION
        "For each class of service, an interval attribute is defined below. 
               The value 0 disables power shedding, while the value 1 enables immediate power shed, that is, as soon as AC power fails. 
              Other values specify the time, in seconds, to keep the service active after AC failure before shutting them down and shedding power. 
              Upon ME instantiation, the ONT sets each of the interval attributes to 0.(2 bytes)"
        REFERENCE   "G.984.4 section 9.1.7 ONT power shedding"
        ::= { zxGponONTPowerSheddingEntry 6 }

    zxGponONTPowerSheddingATMSheddingInterval OBJECT-TYPE
        SYNTAX      INTEGER
        MAX-ACCESS  read-write
        STATUS      current
        DESCRIPTION
        "For each class of service, an interval attribute is defined below. 
               The value 0 disables power shedding, while the value 1 enables immediate power shed, that is, as soon as AC power fails. 
              Other values specify the time, in seconds, to keep the service active after AC failure before shutting them down and shedding power. 
              Upon ME instantiation, the ONT sets each of the interval attributes to 0.(2 bytes)"
        REFERENCE   "G.984.4 section 9.1.7 ONT power shedding"
        ::= { zxGponONTPowerSheddingEntry 7 }

    zxGponONTPowerSheddingCESSheddingInterval OBJECT-TYPE
        SYNTAX      INTEGER
        MAX-ACCESS  read-write
        STATUS      current
        DESCRIPTION
        "For each class of service, an interval attribute is defined below. 
               The value 0 disables power shedding, while the value 1 enables immediate power shed, that is, as soon as AC power fails. 
              Other values specify the time, in seconds, to keep the service active after AC failure before shutting them down and shedding power. 
              Upon ME instantiation, the ONT sets each of the interval attributes to 0.(2 bytes)"
        REFERENCE   "G.984.4 section 9.1.7 ONT power shedding"
        ::= { zxGponONTPowerSheddingEntry 8 }

    zxGponONTPowerSheddingFrameSheddingInterval OBJECT-TYPE
        SYNTAX      INTEGER
        MAX-ACCESS  read-write
        STATUS      current
        DESCRIPTION
        "For each class of service, an interval attribute is defined below. 
               The value 0 disables power shedding, while the value 1 enables immediate power shed, that is, as soon as AC power fails. 
              Other values specify the time, in seconds, to keep the service active after AC failure before shutting them down and shedding power. 
              Upon ME instantiation, the ONT sets each of the interval attributes to 0.(2 bytes)"
        REFERENCE   "G.984.4 section 9.1.7 ONT power shedding"
        ::= { zxGponONTPowerSheddingEntry 9 }

    zxGponONTPowerSheddingSONETSheddingInterval OBJECT-TYPE
        SYNTAX      INTEGER
        MAX-ACCESS  read-write
        STATUS      current
        DESCRIPTION
        "For each class of service, an interval attribute is defined below. 
               The value 0 disables power shedding, while the value 1 enables immediate power shed, that is, as soon as AC power fails. 
              Other values specify the time, in seconds, to keep the service active after AC failure before shutting them down and shedding power. 
              Upon ME instantiation, the ONT sets each of the interval attributes to 0.(2 bytes)"
        REFERENCE   "G.984.4 section 9.1.7 ONT power shedding"
        ::= { zxGponONTPowerSheddingEntry 10 }

    zxGponONTPowerSheddingSheddingStatus OBJECT-TYPE
        SYNTAX      INTEGER
        MAX-ACCESS  read-only
        STATUS      current
        DESCRIPTION
        "Boolean indication of power shedding status for each shedding class. 
         If this two-byte field is depicted 0b ABCD EFGH IJKL MNOP, its bits are assigned:
         A    Data class
         B    Voice class
         C    Video overlay class
         D    Video return class
         E    DSL class
         F    ATM class
         G    CES class
         H    Frame class
         I    Sonet class
         J..P    Reserved and set to 0
         The ONT sets each bit when power shedding is active, and clears it when the service is restored. (R) (optional) (2 bytes)"
        REFERENCE   "G.984.4 section 9.1.7 ONT power shedding"
        ::= { zxGponONTPowerSheddingEntry 11 }

--ANI management/9.2
    zxGponPonTable    OBJECT-TYPE
        SYNTAX      SEQUENCE OF ZxGponPonEntry
        MAX-ACCESS  not-accessible
        STATUS      current
        DESCRIPTION
            "This managed entity is used to organize data associated with the 
            Access Network Interface supported by the ONT.
            One instance of this managed entity exists for each PON physical port.
            One or more instance of this managed entity are contained in an instance of 
            a circuit pack that supports a PON IF function."
        ::= { zxGponANIMgmt 1 }

    zxGponPonEntry OBJECT-TYPE
        SYNTAX      ZxGponPonEntry
        MAX-ACCESS  not-accessible
        STATUS      current
        DESCRIPTION
            "It is entry in the zxGponPonTable."
        INDEX   { zxGponOltIndex, zxGponONTIndex, zxGponPonIndex }
        ::= { zxGponPonTable 1 }
        
    ZxGponPonEntry ::=
        SEQUENCE {
            zxGponPonSRInd                     TruthValue,
            zxGponPonTotalTcontNum             INTEGER,
            zxGponPonGemBlockLen               INTEGER,
            zxGponPonPiggybackDBAReporting     INTEGER,
            zxGponPonWholeOnuDBAReporting      INTEGER,
            zxGponPonSFThreshold               INTEGER,
            zxGponPonSDThreshold               INTEGER,
            zxGponPonAlarmReport               INTEGER,
            zxGponPonAlarmDisableInterval      INTEGER,
            zxGponPonRxOpticalLevel            INTEGER,
            zxGponPonLowerRxOpticalThreshold   INTEGER,
            zxGponPonUpperRxOpticalThreshold   INTEGER,
            zxGponPonOntResponseTime           INTEGER,
            zxGponPonTxOpticalLevel            INTEGER,
            zxGponPonLowerTxOpticalThreshold   INTEGER,
            zxGponPonUpperTxOpticalThreshold   INTEGER,
            zxGponPonPowerFeedVoltage          INTEGER,
            zxGponPonLaserBiasCurrent          INTEGER,
            zxGponPonTemperature               INTEGER,
            zxGponPonLowerVoltageThreshold     INTEGER,
            zxGponPonUpperVoltageThreshold     INTEGER,
            zxGponPonLowerCurrentThreshold     INTEGER,
            zxGponPonUpperCurrentThreshold     INTEGER,
            zxGponPonLowerTemperatureThreshold INTEGER,
            zxGponPonUpperTemperatureThreshold INTEGER
        }

    zxGponPonSRInd OBJECT-TYPE
        SYNTAX      TruthValue
        MAX-ACCESS  read-only
        STATUS      current
        DESCRIPTION
        "This Boolean attribute indicates the capability of status reporting. The
        value TRUE means that the status reporting is available for all T-CONTs which 
        are associated with the ANI. The default value is false.(1 bytes)"
        REFERENCE   "G.984.4 section 9.2.1 ANI-G"
        DEFVAL {false}
        ::= { zxGponPonEntry 1 }

    zxGponPonTotalTcontNum OBJECT-TYPE
        SYNTAX      INTEGER
        MAX-ACCESS  read-only
        STATUS      current
        DESCRIPTION
        "This attribu provides the total number of T-CONTs that are able to be supported 
        in this ANI port.(2 bytes)"
        REFERENCE   "G.984.4 section 9.2.1 ANI-G"
        ::= { zxGponPonEntry 2 }

    zxGponPonGemBlockLen OBJECT-TYPE
        SYNTAX      INTEGER
        MAX-ACCESS  read-write
        STATUS      current
        DESCRIPTION
        "This attribute indicates the reporting block size for GEM mode in units of bytes.
        The value which the OLT sets is used by all T-CONTs in this ANI. 
        Upon autonomous instantiation this attribute consists of the value 0x0030.(2 bytes)"
        REFERENCE   "G.984.4 section 9.2.1 ONT2-G"
        ::= { zxGponPonEntry 3 }

    zxGponPonPiggybackDBAReporting OBJECT-TYPE
        SYNTAX      INTEGER{
                    mode0Only(1),
                    mode01(2),
                    mode02(3),
                    mode012(4),
                    notsupport(5)
                    }
        MAX-ACCESS  read-only
        STATUS      current
        DESCRIPTION
        "The following coding is used to indicate the ONT's piggyback DBA reporting 
        mode capabilities:
        0x00: supports mode 0 only;
        0x01: supports modes 0 and 1;
        0x02: supports modes 0 and 2;
        0x03: supports modes 0,1,and 2;
        0x04: piggyback DBA reporting not supported.(1 byte)"
        REFERENCE   "G.984.4 section 9.2.1 ANI-G"
        ::= { zxGponPonEntry 4 }
        
    zxGponPonWholeOnuDBAReporting OBJECT-TYPE
        SYNTAX      INTEGER{
                    notsupport(1),
                    support(2)
                    }
        MAX-ACCESS  read-only
        STATUS      current
        DESCRIPTION
            "Valid values are 0x00 (whole ONU DBA reporting is not supported) 
            and 0x01 (whole ONU DBA reporting is supported).(1 byte)"
        REFERENCE
            "G.984.4 Section 9.2.1 ANI-G"
        ::= { zxGponPonEntry 5}

    zxGponPonSFThreshold OBJECT-TYPE
        SYNTAX      INTEGER
        MAX-ACCESS  read-write
        STATUS      current
        DESCRIPTION
            "This attribute represents the upstream/downstream BER threshold to detect SFi/SF alarm. 
            When this value is y in decimal, the BER threshold for SFi/SF is 10^(-y).
            The valid values are from 3 to 8 inclusive.
            Upon autonomous instantiation, this attribute consists of 5.(1 byte)"
        REFERENCE
            "G.984.4 Section 9.2.1 ANI-G"
        ::= { zxGponPonEntry 6}

    zxGponPonSDThreshold OBJECT-TYPE
        SYNTAX      INTEGER
        MAX-ACCESS  read-write
        STATUS      current
        DESCRIPTION
            "This attribute represents the upstream/downstream BER threshold to detect SDi/SD alarm. 
            When this value is x in decimal, the BER threshold for SDi/SD is 10^(-x).
            The valid values are from 4 to 10 inclusive. Please note that the SD threshold shall be 
            smaller than the SF threshold. This means that the value of x shall be larger than the value of y.  
            Upon autonomous instantiation, this attribute consists of 9.(1 byte)"
        REFERENCE
            "G.984.4 Section 9.2.1 ANI-G"
        ::= { zxGponPonEntry 7}

    zxGponPonAlarmReport OBJECT-TYPE
        SYNTAX      INTEGER
        MAX-ACCESS  read-write
        STATUS      current
        DESCRIPTION
            "Alarm reporting control. 
             0(enable): Allow alarm reporting, 1(disable): Suppress alarm reporting.(1 byte)"
        REFERENCE
            "G.984.4 Section 9.2.1 ANI-G"
        ::= { zxGponPonEntry 8}

    zxGponPonAlarmDisableInterval OBJECT-TYPE
        SYNTAX      INTEGER
        MAX-ACCESS  read-write
        STATUS      current
        DESCRIPTION
            "Alarm reporting control interval.
             0: Allow alarm reporting immediately when port is trouble free.
             1-254: The duration in minutes for alarm suppression.
             255: Suppress alarm reporting until alarm is enabled. (1 byte)"
        REFERENCE
            "G.984.4 Section 9.2.1 ANI-G"
        ::= { zxGponPonEntry 9}

    zxGponPonRxOpticalLevel OBJECT-TYPE
        SYNTAX      INTEGER
        MAX-ACCESS  read-only
        STATUS      current
        DESCRIPTION
            "This attribute reports the current measurement of total 
             optical signal level at 1490 nm. Its value is a 2s complement 
             integer referred to 1 mW (ie dBm), with 0.002 dB granularity.(2 byte)"
        REFERENCE
            "G.984.4 Section 9.2.1 ANI-G"
        ::= { zxGponPonEntry 10}

    zxGponPonLowerRxOpticalThreshold OBJECT-TYPE
        SYNTAX      INTEGER
        MAX-ACCESS  read-write
        STATUS      current
        DESCRIPTION
            "This attribute specifies the optical level the ONT uses to 
            declare the 1490 nm low received optical power alarm. 
            Valid values are -127 dBm (coded as 254) to 0 dBm (coded as 0) 
            in 0.5 dB increments. The default value 0xFF selects the ONT's internal policy.(1 byte)"
        REFERENCE
            "G.984.4 Section 9.2.1 ANI-G"
        ::= { zxGponPonEntry 11}

    zxGponPonUpperRxOpticalThreshold OBJECT-TYPE
        SYNTAX      INTEGER
        MAX-ACCESS  read-write
        STATUS      current
        DESCRIPTION
            "This attribute specifies the optical level the ONT uses to 
            declare the 1490 nm high received optical power alarm. 
            Valid values are -127 dBm (coded as 254) to 0 dBm (coded as 0) 
            in 0.5 dB increments. The default value 0xFF selects the ONT's internal policy.(1 byte)"
        REFERENCE
            "G.984.4 Section 9.2.1 ANI-G"
        ::= { zxGponPonEntry 12}

    zxGponPonOntResponseTime OBJECT-TYPE
        SYNTAX      INTEGER
        MAX-ACCESS  read-only
        STATUS      current
        DESCRIPTION
            "This attribute indicates actual ONT response time recorded by ONT. 
             The unit is nanoseconds.(2 byte)"
        REFERENCE
            "G.984.4 Section 9.2.1 ANI-G"
        ::= { zxGponPonEntry 13}

    zxGponPonTxOpticalLevel OBJECT-TYPE
        SYNTAX      INTEGER
        MAX-ACCESS  read-only
        STATUS      current
        DESCRIPTION
            "This attribute reports the current measurement of optical 
             transmit power level. Its value is a 2s complement integer 
             referred to 1 mW (ie dBm), with 0.002 dB granularity.(2 byte)"
        REFERENCE
            "G.984.4 Section 9.2.1 ANI-G"
        ::= { zxGponPonEntry 14}

    zxGponPonLowerTxOpticalThreshold OBJECT-TYPE
        SYNTAX      INTEGER
        MAX-ACCESS  read-write
        STATUS      current
        DESCRIPTION
            "This attribute specifies the transmit power level the ONT uses to 
            declare the low transmit optical power alarm. Its value is a 2s complement 
            integer referred to 1 mW (ie dBm), with 0.5 dB granularity. 
            The default value -63.5 (0x81) selects the ONT's internal policy.(1 byte)"
        REFERENCE
            "G.984.4 Section 9.2.1 ANI-G"
        ::= { zxGponPonEntry 15}

    zxGponPonUpperTxOpticalThreshold OBJECT-TYPE
        SYNTAX      INTEGER
        MAX-ACCESS  read-write
        STATUS      current
        DESCRIPTION
            "This attribute specifies the transmit power level the ONT uses to 
            declare the high transmit optical power alarm. Its value is a 2s complement 
            integer referred to 1 mW (ie dBm), with 0.5 dB granularity. 
            The default value -63.5 (0x81) selects the ONT's internal policy.(1 byte)"
        REFERENCE
            "G.984.4 Section 9.2.1 ANI-G"
        ::= { zxGponPonEntry 16}

    zxGponPonPowerFeedVoltage OBJECT-TYPE
        SYNTAX      INTEGER
        MAX-ACCESS  read-only
        STATUS      current
        DESCRIPTION
            "DC voltage, 2s complement, 20 mV resolution.(2 byte)"
        REFERENCE
            "G.984.4 Section 11.1.10 Test result enumeration"
        ::= { zxGponPonEntry 17}

    zxGponPonLaserBiasCurrent OBJECT-TYPE
        SYNTAX      INTEGER
        MAX-ACCESS  read-only
        STATUS      current
        DESCRIPTION
            "2s complement, 2 uA resolution.(2 byte)"
        REFERENCE
            "G.984.4 Section 11.1.10 Test result enumeration"
        ::= { zxGponPonEntry 18}

    zxGponPonTemperature OBJECT-TYPE
        SYNTAX      INTEGER
        MAX-ACCESS  read-only
        STATUS      current
        DESCRIPTION
            "2s complement, 1/256 degree C resolution.(2 byte)"
        REFERENCE
            "G.984.4 Section 11.1.10 Test result enumeration"
        ::= { zxGponPonEntry 19}

    zxGponPonLowerVoltageThreshold OBJECT-TYPE
        SYNTAX      INTEGER
        MAX-ACCESS  read-write
        STATUS      current
        DESCRIPTION
            "(2 byte)"
        REFERENCE
            "G.984.4 Section 9.2.1 ANI-G"
        ::= { zxGponPonEntry 20}

    zxGponPonUpperVoltageThreshold OBJECT-TYPE
        SYNTAX      INTEGER
        MAX-ACCESS  read-write
        STATUS      current
        DESCRIPTION
            "(2 byte)"
        REFERENCE
            "G.984.4 Section 9.2.1 ANI-G"
        ::= { zxGponPonEntry 21}

    zxGponPonLowerCurrentThreshold OBJECT-TYPE
        SYNTAX      INTEGER
        MAX-ACCESS  read-write
        STATUS      current
        DESCRIPTION
            "(2 byte)"
        REFERENCE
            "G.984.4 Section 9.2.1 ANI-G"
        ::= { zxGponPonEntry 22}

    zxGponPonUpperCurrentThreshold OBJECT-TYPE
        SYNTAX      INTEGER
        MAX-ACCESS  read-write
        STATUS      current
        DESCRIPTION
            "(2 byte)"
        REFERENCE
            "G.984.4 Section 9.2.1 ANI-G"
        ::= { zxGponPonEntry 23}

    zxGponPonLowerTemperatureThreshold OBJECT-TYPE
        SYNTAX      INTEGER
        MAX-ACCESS  read-write
        STATUS      current
        DESCRIPTION
            "(2 byte)"
        REFERENCE
            "G.984.4 Section 9.2.1 ANI-G"
        ::= { zxGponPonEntry 24}

    zxGponPonUpperTemperatureThreshold OBJECT-TYPE
        SYNTAX      INTEGER
        MAX-ACCESS  read-write
        STATUS      current
        DESCRIPTION
            "(2 byte)"
        REFERENCE
            "G.984.4 Section 9.2.1 ANI-G"
        ::= { zxGponPonEntry 25}

--ONU Loopback
    zxGponLoopbackTable    OBJECT-TYPE
        SYNTAX      SEQUENCE OF ZxGponLoopbackEntry
        MAX-ACCESS  not-accessible
        STATUS      current
        DESCRIPTION ""
        ::= { zxGponANIMgmt 2 }

    zxGponLoopbackEntry OBJECT-TYPE
        SYNTAX      ZxGponLoopbackEntry
        MAX-ACCESS  not-accessible
        STATUS      current
        DESCRIPTION
            "It is entry in the zxGponLoopbackTable."
        INDEX   { zxGponOltIndex, zxGponONTIndex }
        ::= { zxGponLoopbackTable 1 }
        
    ZxGponLoopbackEntry ::=
        SEQUENCE {
            zxGponIsLoopback                     TruthValue
        }

    zxGponIsLoopback OBJECT-TYPE
        SYNTAX      TruthValue
        MAX-ACCESS  read-write
        STATUS      current
        DESCRIPTION ""
        REFERENCE   ""
        ::= { zxGponLoopbackEntry 1 }


--UNI management
--UNI-G

--PPTP ETH UNI
    zxGponPptpEthUNITable    OBJECT-TYPE
        SYNTAX      SEQUENCE OF ZxGponPptpEthUNIEntry
        MAX-ACCESS  not-accessible
        STATUS      current
        DESCRIPTION
            "This managed entity represents the points at an Ethernet UNI in the ONT where physical paths 
            terminate and physical path level functions (e.g., Ethernet function) are performed.
            One or more instances of this managed entity shall be contained in an instance of a Circuit Pack 
            managed entity classified as a native LAN type (e.g., Ethernet)."
        REFERENCE   "G.983.2 section 7.3.2 Physical path termination point Ethernet UNI"
        ::= { zxGponL2Mgmt 2 }

    zxGponPptpEthUNIEntry OBJECT-TYPE
        SYNTAX      ZxGponPptpEthUNIEntry
        MAX-ACCESS  not-accessible
        STATUS      current
        DESCRIPTION
            "It is entry in the zxGponPptpEthUNITable."
        INDEX   { zxGponOltIndex, zxGponONTIndex, zxGponUNIIndex }
        ::= { zxGponPptpEthUNITable 1 }
        
    ZxGponPptpEthUNIEntry ::=
        SEQUENCE {
            zxGponPptpEthUNIExpectedType            INTEGER,
            zxGponPptpEthUNISensedType              INTEGER,
            zxGponPptpEthUNIIfSpeedConfig           INTEGER,
            zxGponPptpEthUNIEthLookbackConfig       INTEGER,
            zxGponPptpEthUNIAdminState              INTEGER,
            zxGponPptpEthUNIOperState               INTEGER,
            zxGponPptpEthUNIIfSpeedStatus           INTEGER,
            zxGponPptpEthUNIMaxFrameSize            INTEGER,
            zxGponPptpEthUNIDteOrDceInd             INTEGER,
            zxGponPptpEthUNIPauseTime               INTEGER,
            zxGponPptpEthUNIBridgeOrIpInd           INTEGER,
            zxGponPptpEthUNIARC                     INTEGER,
            zxGponPptpEthUNIARCInterval             INTEGER,
            zxGponPptpEthUNIPPPoEFilter             INTEGER,
            zxGponPptpEthUNIPowerControl            INTEGER
        }

    zxGponPptpEthUNIExpectedType OBJECT-TYPE
        SYNTAX      INTEGER
        MAX-ACCESS  read-write
        STATUS      current
        DESCRIPTION
        "The following coding is used for this attribute: 0x00 = by autosensing, 
        0x01 to 0xFE (1 to 254) = one of the values from Table 3 that is compatible with the 
        type of the LIM. Upon autonomous instantiation, the value 0x00 is used.(1 byte)"
        REFERENCE   "G.983.2 section 7.3.2 Physical path termination point Ethernet UNI"
        ::= { zxGponPptpEthUNIEntry 1 }

    zxGponPptpEthUNISensedType OBJECT-TYPE
        SYNTAX      INTEGER
        MAX-ACCESS  read-only
        STATUS      current
        DESCRIPTION
        "If the value of 'Expected type' is not equal to 0x00, then the value of 'Sensed type' 
        equals the value of 'Expected type'. If the value of 'Expected type' equals 0x00, then 
        the value of 'Sensed type' equals one of the values from Table 3 (0x01 to 0xFE) and by 
        necessity is compatible with the Type of the Circuit Pack managed entity. 
        Upon autonomous instantiation, the value 0x00 is used.(1 byte)"
        REFERENCE   "G.983.2 section 7.3.2 Physical path termination point Ethernet UNI"
        ::= { zxGponPptpEthUNIEntry 2 }
        
    zxGponPptpEthUNIIfSpeedConfig OBJECT-TYPE
        SYNTAX      INTEGER{
                    auto(1),
                    half10(2),
                    full10(3),
                    half100(4),
                    full100(5),
                    full1000(6)
                    }
        MAX-ACCESS  read-write
        STATUS      current
        DESCRIPTION
        "For 10/100 Base-Tx Ethernet interfaces, this attribute is used to set the configuration 
        options: 
        Auto-sensing: 0x00; 
        10BaseT: 0x01; 
        100BaseT: 0x02: 
        Gigabit Ethernet: 0x03; 
        10BaseT Auto-sensing: 0x10; 
        10BaseT (half duplex): 0x11; 
        100BaseT (half duplex): 0x12; 
        Gigabit Ethernet (half duplex): 0x13; 
        Gigabit Ethernet Auto-sensing: 0x20. 
        Upon autonomous instantiation, the value 0x00 is used.(1 byte)"
        REFERENCE   "G.983.2 section 7.3.2 Physical path termination point Ethernet UNI"
        ::= { zxGponPptpEthUNIEntry 3 }
        
    zxGponPptpEthUNIEthLookbackConfig OBJECT-TYPE
        SYNTAX      INTEGER{
                    noloop(1),
                    loop3(4)
                    }
        MAX-ACCESS  read-write
        STATUS      current
        DESCRIPTION
        "This attribute is used to set the Ethernet loopback configuration: 
        No loopback (value 0x00), Loop3 (value 0x03, Loopback of downstream traffic after PHY transceiver).
        Upon autonomous instantiation, the value 0x00 is used.(1 byte)"
        REFERENCE   "G.983.2 section 7.3.2 Physical path termination point Ethernet UNI"
        ::= { zxGponPptpEthUNIEntry 4 }
        
    zxGponPptpEthUNIAdminState OBJECT-TYPE
        SYNTAX      INTEGER{
                    unlock(1),
                    lock(2)
                    }
        MAX-ACCESS  read-write
        STATUS      current
        DESCRIPTION
        "This attribute is used to activate (unlock: value 0x00) and deactivate (lock: value 0x01) 
        the functions performed by instances of this managed entity.(1 byte)"
        REFERENCE   "G.983.2 section 7.3.2 Physical path termination point Ethernet UNI"
        ::= { zxGponPptpEthUNIEntry 5 }
        
    zxGponPptpEthUNIOperState OBJECT-TYPE
        SYNTAX      INTEGER{
                    enable(1),
                    disable(2)
                    }
        MAX-ACCESS  read-only
        STATUS      current
        DESCRIPTION
        "This attribute indicates whether or not this managed entity is capable of performing 
        its task. The operational state reflects the perceived ability to receive or to generate 
        a valid signal. Valid values are enabled (0x00) and disabled (0x01).(1 byte)"
        REFERENCE   "G.983.2 section 7.3.2 Physical path termination point Ethernet UNI"
        ::= { zxGponPptpEthUNIEntry 6 }
        
    zxGponPptpEthUNIIfSpeedStatus OBJECT-TYPE
        SYNTAX      INTEGER{
                    auto(1),
                    half10(2),
                    full10(3),
                    half100(4),
                    full100(5),
                    full1000(6)
                    }
        MAX-ACCESS  read-only
        STATUS      current
        DESCRIPTION
        "This attribute indicates the configuration status of the Ethernet UNI. 
        10BaseT (full duplex): 0x01; 
        100BaseT (full duplex): 0x02; 
        Gigabit Ethernet (full duplex): 0x03; 
        10BaseT (half duplex): 0x11; 
        100BaseT (half duplex): 0x12 
        Gigabit Ethernet (half duplex): 0x13; 
        When the configuration status is not detected (e.g., Ethernet link is not 
        established or line card is not yet installed), the value 0x00 is used. 
        Upon autonomous instantiation, the value 0x00 is used.(1 byte)"
        REFERENCE   "G.983.2 section 7.3.2 Physical path termination point Ethernet UNI"
        ::= { zxGponPptpEthUNIEntry 7 }
        
    zxGponPptpEthUNIMaxFrameSize OBJECT-TYPE
        SYNTAX      INTEGER
        MAX-ACCESS  read-write
        STATUS      current
        DESCRIPTION
        "This attribute denotes the maximum allowed frame size to be transmitted across this interface. 
        Upon autonomous instantiation, the value 1518 is used.(2 bytes)"
        REFERENCE   "G.983.2 section 7.3.2 Physical path termination point Ethernet UNI"
        ::= { zxGponPptpEthUNIEntry 8 }
        
    zxGponPptpEthUNIDteOrDceInd OBJECT-TYPE
        SYNTAX      INTEGER{
                    dce(1),
                    dte(2)
                    }
        MAX-ACCESS  read-write
        STATUS      current
        DESCRIPTION
        "This attribute indicates whether the Ethernet interface wiring is DTE or DCE (DCE: 0x00; DTE: 0x01). 
        Upon autonomous instantiation, the value 0x00 is used.(1 byte)"
        REFERENCE   "G.983.2 section 7.3.2 Physical path termination point Ethernet UNI"
        ::= { zxGponPptpEthUNIEntry 9 }
        
    zxGponPptpEthUNIPauseTime OBJECT-TYPE
        SYNTAX      INTEGER
        MAX-ACCESS  read-write
        STATUS      current
        DESCRIPTION
        "This attribute allows the ONT line card to request that the customer terminal temporarily 
        suspend sending data. Units are in 'pause_quanta' (1 pause_quantum equals 512 bits times of 
        the particular implementation). Values: 0x0000 to 0xFFFF. 
        Upon autonomous instantiation, the value 0x0000 is used.(2 bytes)"
        REFERENCE   "G.983.2 section 7.3.2 Physical path termination point Ethernet UNI"
        ::= { zxGponPptpEthUNIEntry 10 }
        
    zxGponPptpEthUNIBridgeOrIpInd OBJECT-TYPE
        SYNTAX      INTEGER{
                    bridged(1),
                    ipRouter(2),
                    either(3)
                    }
        MAX-ACCESS  read-write
        STATUS      current
        DESCRIPTION
        "This attribute indicates whether the Ethernet interface is bridged or derived from an 
        IP router function (Bridged: 0x00; IP router: 0x01; 0x02: depends on Circuit Pack.) 
        0x02 means that the SLC 'BridgedorIPInd' attribute will be either 0x00 or 0x01. 
        Upon autonomous instantiation, the value 0x02 is used.(1 byte)"
        REFERENCE   "G.983.2 section 7.3.2 Physical path termination point Ethernet UNI"
        ::= { zxGponPptpEthUNIEntry 11 }
      
    zxGponPptpEthUNIARC OBJECT-TYPE
        SYNTAX      INTEGER
        MAX-ACCESS  read-write
        STATUS      current
        DESCRIPTION
        "This attribute is used to control alarm reporting from this managed entity. 
        See I.1.8 for a complete description.(1 byte)"
        REFERENCE   "G.983.2 section 7.3.2 Physical path termination point Ethernet UNI"
        ::= { zxGponPptpEthUNIEntry 12 }
        
    zxGponPptpEthUNIARCInterval OBJECT-TYPE
        SYNTAX      INTEGER
        MAX-ACCESS  read-write
        STATUS      current
        DESCRIPTION
        "This attribute provides a provisionable length of time. See I.1.8 for a complete description.(1 byte)"
        REFERENCE   "G.983.2 section 7.3.2 Physical path termination point Ethernet UNI"
        ::= { zxGponPptpEthUNIEntry 13 }
        
    zxGponPptpEthUNIPPPoEFilter OBJECT-TYPE
        SYNTAX      INTEGER{
                    filterDisable(1),
                    filterEnable(2)
                    }
        MAX-ACCESS  read-write
        STATUS      current
        DESCRIPTION
        "This attribute may be used to control filtering of PPPoE packets on this Ethernet port. 
        The value 0x00 is used to disable filtering. The value 0x01 is used to enable filtering. 
        When filtering is enabled, all packets other than PPPoE packets will be discarded. 
        Default value is 0x00.(1 byte)"
        REFERENCE   "G.983.2 section 7.3.2 Physical path termination point Ethernet UNI"
        ::= { zxGponPptpEthUNIEntry 14 }
        
    zxGponPptpEthUNIPowerControl OBJECT-TYPE
        SYNTAX      INTEGER{
                    controlDisable(1),
                    controlEnable(2)
                    }
        MAX-ACCESS  read-write
        STATUS      current
        DESCRIPTION
        "This attribute controls whether power is provided to an external equipment over the 
        Ethernet PPTP. Value 0x01 enables power over Ethernet. 
        The default value 0x00 disables power feed.(1 byte)"
        REFERENCE   "G.983.2 section 7.3.2 Physical path termination point Ethernet UNI"
        ::= { zxGponPptpEthUNIEntry 15 }

--Physical path termination point POTS UNI
    zxGponPptpPOTSUNITable    OBJECT-TYPE
        SYNTAX      SEQUENCE OF ZxGponPptpPOTSUNIEntry
        MAX-ACCESS  not-accessible
        STATUS      current
        DESCRIPTION
            "This managed entity represents the point at the POTS UNI in the ONT where physical paths 
            terminate and physical path level functions (e.g., analog telephony, facsimile function) 
            are performed.
            One or more instances of this managed entity shall be contained in an instance of the 
            ONTB-PON or a Circuit Pack managed entity classified as POTS type."
        REFERENCE   "G.983.2 section 7.3.26 Physical path termination point POTS UNI"
        ::= { zxGponL2Mgmt 3 }
        
    zxGponPptpPOTSUNIEntry OBJECT-TYPE
        SYNTAX      ZxGponPptpPOTSUNIEntry
        MAX-ACCESS  not-accessible
        STATUS      current
        DESCRIPTION
            "It is entry in the zxGponPptpPOTSUNITable."
        INDEX   { zxGponOltIndex, zxGponONTIndex, zxGponUNIIndex }
        ::= { zxGponPptpPOTSUNITable 1 }
        
    ZxGponPptpPOTSUNIEntry ::=
        SEQUENCE {
            zxGponPptpPOTSUNIAdminState              INTEGER,
            zxGponPptpPOTSUNIIwVCCPtr                INTEGER,
            zxGponPptpPOTSUNIARC                     INTEGER,
            zxGponPptpPOTSUNIARCInterval             INTEGER,
            zxGponPptpPOTSUNIImpedance               INTEGER,
            zxGponPptpPOTSUNITxPath                  INTEGER,
            zxGponPptpPOTSUNIRxGain                  INTEGER,
            zxGponPptpPOTSUNITxGain                  INTEGER,
            zxGponPptpPOTSUNIOperState               INTEGER,
            zxGponPptpPOTSUNIHookState               INTEGER
        }

   zxGponPptpPOTSUNIAdminState OBJECT-TYPE
        SYNTAX      INTEGER{
                    unlock(1),
                    lock(2)
                    }
        MAX-ACCESS  read-write
        STATUS      current
        DESCRIPTION
        "This attribute is used to activate (unlock: value 0x00) and deactivate (lock: value 0x01) 
        the functions performed by instances of this managed entity.(1 byte)"
        REFERENCE   "G.983.2 section 7.3.26 Physical path termination point POTS UNI"
        ::= { zxGponPptpPOTSUNIEntry 1 }
        
    zxGponPptpPOTSUNIIwVCCPtr OBJECT-TYPE
        SYNTAX      INTEGER
        MAX-ACCESS  read-only
        STATUS      current
        DESCRIPTION
        "This attribute provides a pointer to the instance of the Interworking VCC managed 
        entity to which this instance is connected. The value 0x0000 is interpreted as a 
        Null pointer.(2 bytes)"
        REFERENCE   "G.983.2 section 7.3.26 Physical path termination point POTS UNI"
        ::= { zxGponPptpPOTSUNIEntry 2 }
    
    zxGponPptpPOTSUNIARC OBJECT-TYPE
        SYNTAX      INTEGER
        MAX-ACCESS  read-write
        STATUS      current
        DESCRIPTION
        "This attribute is used to control alarm reporting from this managed entity. See I.1.8 for a complete description.(1 byte)"
        REFERENCE   "G.983.2 section 7.3.26 Physical path termination point POTS UNI"
        ::= { zxGponPptpPOTSUNIEntry 3 }
        
    zxGponPptpPOTSUNIARCInterval OBJECT-TYPE
        SYNTAX      INTEGER
        MAX-ACCESS  read-write
        STATUS      current
        DESCRIPTION
        "This attribute provides a provisionable length of time. See I.1.8 for a complete description.(1 byte)"
        REFERENCE   "G.983.2 section 7.3.26 Physical path termination point POTS UNI"
        ::= { zxGponPptpPOTSUNIEntry 4 }
        
    zxGponPptpPOTSUNIImpedance OBJECT-TYPE
        SYNTAX      INTEGER
        MAX-ACCESS  read-write
        STATUS      current
        DESCRIPTION
        "This attribute allows the impedance for the Physical Path Termination Point 
        POTS UNI to be configured by the user. 
        Valid values include 600 Ohm Impedance (value 0x00) and 900 Ohm Impedance (value 0x01). 
        In addition, the following parameter sets from ETSI TS 101 270-1 (1999 10), Annex C, 
        are valid:
        -    value 0x02: C1=150 nF, R1=750 Ohm, R2=270 Ohm;
        -    value 0x03: C1=115 nF, R1=820 Ohm, R2=220 Ohm;
        -    value 0x04: C1=230 nF, R1=1050 Ohm, R2=320 Ohm, 
        where C1, R1, and R2 are related as shown below. Upon autonomous instantiation, the value 0x00 is used. 
        (1 byte)"
        REFERENCE   "G.983.2 section 7.3.26 Physical path termination point POTS UNI"
        ::= { zxGponPptpPOTSUNIEntry 5 }
        
    zxGponPptpPOTSUNITxPath OBJECT-TYPE
        SYNTAX      INTEGER{
                    fulltimeOnHook(1),
                    partimeOnHook(2)
                    }
        MAX-ACCESS  read-write
        STATUS      current
        DESCRIPTION
        "This attribute allows for setting the Physical Path Termination Point POTS UNI 
        to be put in either full-time or part-time on-hook transmission mode. 
        Valid values include full time on-hook transmission (value 0x00) and part-time 
        on-hook transmission (value 0x01) Upon autonomous instantiation, the value 0x00 
        is used.(1 byte)"
        REFERENCE   "G.983.2 section 7.3.26 Physical path termination point POTS UNI"
        ::= { zxGponPptpPOTSUNIEntry 6 }
        
    zxGponPptpPOTSUNIRxGain OBJECT-TYPE
        SYNTAX      INTEGER
        MAX-ACCESS  read-write
        STATUS      current
        DESCRIPTION
        "This attribute provides a gain value for the received signal. 
        Valid values are -12 dB to +6 dB in 0.1 dB increments. 
        (value -120 to +60, 0 = 0 dB gain, -120 = -12.0 dB, etc.) 
        Upon autonomous instantiation, the value 0x00 is used.(1 byte)"
        REFERENCE   "G.983.2 section 7.3.26 Physical path termination point POTS UNI"
        ::= { zxGponPptpPOTSUNIEntry 7 }
        
    zxGponPptpPOTSUNITxGain OBJECT-TYPE
        SYNTAX      INTEGER
        MAX-ACCESS  read-write
        STATUS      current
        DESCRIPTION
        "This attribute provides a gain value for the transmit signal. 
        Valid values are -6 dB to +12 dB in 0.1 dB increments. 
        (value -60 to +120, 0 = 0 dB gain, 60 = +6.0 dB, etc.). 
        Upon autonomous instantiation, the value 0x00 is used.(1 byte)"
        REFERENCE   "G.983.2 section 7.3.26 Physical path termination point POTS UNI"
        ::= { zxGponPptpPOTSUNIEntry 8 }

    zxGponPptpPOTSUNIOperState OBJECT-TYPE
        SYNTAX      INTEGER{
                    enable(1),
                    disable(2)
                    }
        MAX-ACCESS  read-only
        STATUS      current
        DESCRIPTION
        "This attribute indicates whether or not this managed entity is capable of performing 
        its task. The operational state reflects the perceived ability to receive or to generate 
        a valid signal. Valid values are enabled (0x00) and disabled (0x01).(1 byte)"
        REFERENCE   "G.983.2 section 7.3.26 Physical path termination point POTS UNI"
        ::= { zxGponPptpPOTSUNIEntry 9 }
        
    zxGponPptpPOTSUNIHookState OBJECT-TYPE
        SYNTAX      INTEGER{
                    onHook(1),
                    offHook(2)
                    }
        MAX-ACCESS  read-only
        STATUS      current
        DESCRIPTION
        "This attribute indicates the state of the subscriber line: 0x00 = on hook, 0x01 = off hook.(1 byte)"
        REFERENCE   "G.983.2 section 7.3.26 Physical path termination point POTS UNI"
        ::= { zxGponPptpPOTSUNIEntry 10 }

--PPTP Video UNI
    zxGponPptpVideoUNITable    OBJECT-TYPE
        SYNTAX      SEQUENCE OF ZxGponPptpVideoUNIEntry
        MAX-ACCESS  not-accessible
        STATUS      current
        DESCRIPTION
            "This managed entity represents the point at the video UNI in the ONT where physical paths terminate 
            and physical path level functions are performed.
            One or more instances of this managed entity shall be contained in an instance of a Circuit Pack 
            managed entity classified as Video type."
        REFERENCE   "G.983.2 section 7.3.52 Physical path termination point video UNI"
        ::= { zxGponL2Mgmt 4 }

    zxGponPptpVideoUNIEntry OBJECT-TYPE
        SYNTAX      ZxGponPptpVideoUNIEntry
        MAX-ACCESS  not-accessible
        STATUS      current
        DESCRIPTION
            "It is entry in the zxGponPptpVideoUNITable."
        INDEX   { zxGponOltIndex, zxGponONTIndex, zxGponUNIIndex }
        ::= { zxGponPptpVideoUNITable 1 }
        
    ZxGponPptpVideoUNIEntry ::=
        SEQUENCE {
            zxGponPptpVideoUNIAdminState              INTEGER,
            zxGponPptpVideoUNIOperState               INTEGER,
            zxGponPptpVideoUNIARC                     INTEGER,
            zxGponPptpVideoUNIARCInterval             INTEGER,
            zxGponPptpVideoUNIPowerControl            INTEGER
        }

    zxGponPptpVideoUNIAdminState OBJECT-TYPE
        SYNTAX      INTEGER{
                    unlock(1),
                    lock(2)
                    }
        MAX-ACCESS  read-write
        STATUS      current
        DESCRIPTION
        "This attribute is used to activate (unlock: value 0x00) and deactivate (lock: value 0x01) 
        the functions performed by instances of this managed entity.(1 byte)"
        REFERENCE   "G.983.2 section 7.3.52 Physical path termination point video UNI"
        ::= { zxGponPptpVideoUNIEntry 1 }
        
    zxGponPptpVideoUNIOperState OBJECT-TYPE
        SYNTAX      INTEGER{
                    enable(1),
                    disable(2)
                    }
        MAX-ACCESS  read-only
        STATUS      current
        DESCRIPTION
        "This attribute indicates whether or not this managed entity is capable of performing 
        its task. The operational state reflects the perceived ability to receive or to generate 
        a valid signal. Valid values are enabled (0x00) and disabled (0x01).(1 byte)"
        REFERENCE   "G.983.2 section 7.3.52 Physical path termination point video UNI"
        ::= { zxGponPptpVideoUNIEntry 2 }
      
    zxGponPptpVideoUNIARC OBJECT-TYPE
        SYNTAX      INTEGER
        MAX-ACCESS  read-write
        STATUS      current
        DESCRIPTION
        "This attribute is used to control alarm reporting from this managed entity. 
        See I.1.8 for a complete description.(1 byte)"
        REFERENCE   "G.983.2 section 7.3.52 Physical path termination point video UNI"
        ::= { zxGponPptpVideoUNIEntry 3 }
        
    zxGponPptpVideoUNIARCInterval OBJECT-TYPE
        SYNTAX      INTEGER
        MAX-ACCESS  read-write
        STATUS      current
        DESCRIPTION
        "This attribute provides a provisionable length of time. See I.1.8 for a complete description.(1 byte)"
        REFERENCE   "G.983.2 section 7.3.52 Physical path termination point video UNI"
        ::= { zxGponPptpVideoUNIEntry 4 }
        
    zxGponPptpVideoUNIPowerControl OBJECT-TYPE
        SYNTAX      INTEGER{
                    controlDisable(1),
                    controlEnable(2)
                    }
        MAX-ACCESS  read-write
        STATUS      current
        DESCRIPTION
        "This attribute controls whether power is provided to an external equipment over the 
        Ethernet PPTP. Value 0x01 enables power over Ethernet. 
        The default value 0x00 disables power feed.(1 byte)"
        REFERENCE   "G.983.2 section 7.3.52 Physical path termination point video UNI"
        ::= { zxGponPptpVideoUNIEntry 5 }

--G.984.4 9.8.1    Physical path termination point CES UNI
    zxGponPptpCESUNITable    OBJECT-TYPE
        SYNTAX      SEQUENCE OF ZxGponPptpCESUNIEntry
        MAX-ACCESS  not-accessible
        STATUS      current
        DESCRIPTION
            "his managed entity represents the point at a CES UNI in the ONT where the 
            physical path terminates and physical level functions are performed."
        REFERENCE   "G.984.4 9.8.1    Physical path termination point CES UNI"
        ::= { zxGponTDMMgmt 1 }
        
    zxGponPptpCESUNIEntry OBJECT-TYPE
        SYNTAX      ZxGponPptpCESUNIEntry
        MAX-ACCESS  not-accessible
        STATUS      current
        DESCRIPTION
            "It is entry in the zxGponPptpCESUNITable."
        INDEX   { zxGponOltIndex, zxGponONTIndex, zxGponUNIIndex }
        ::= { zxGponPptpCESUNITable 1 }
        
    ZxGponPptpCESUNIEntry ::=
        SEQUENCE {
            zxGponPptpCESUNIExpectedType              INTEGER,
            zxGponPptpCESUNISensedType                INTEGER,
            zxGponPptpCESUNILoopback                  INTEGER,
            zxGponPptpCESUNIAdminState                INTEGER,
            zxGponPptpCESUNIOperState                 INTEGER,
            zxGponPptpCESUNIDs1Framing                INTEGER,
            zxGponPptpCESUNIEncoding                  INTEGER,
            zxGponPptpCESUNILineLength                INTEGER,
            zxGponPptpCESUNIDs1Mode                   INTEGER,
            zxGponPptpCESUNIARC                       INTEGER,
            zxGponPptpCESUNIARCInterval               INTEGER,
            zxGponPptpCESUNILineType                  INTEGER
       }
       
   zxGponPptpCESUNIExpectedType OBJECT-TYPE
        SYNTAX      INTEGER
        MAX-ACCESS  read-write
        STATUS      current
        DESCRIPTION
        "The following coding is used for this attribute:
         0    Autosense
         1 to 254    One of the values from table 9.1.5-1/G.984.4 that is compatible with a CES circuit pack.(1 byte)"
        ::= { zxGponPptpCESUNIEntry 1 }
        
   zxGponPptpCESUNISensedType OBJECT-TYPE
        SYNTAX      INTEGER
        MAX-ACCESS  read-only
        STATUS      current
        DESCRIPTION
        "If the value of expected type is not 0, then the value of sensed type equals the value of 
        expected type. If expected type = 0, then the value of sensed type is one of the compatible 
        values from table 9.1.5-1/G.984.4.(1 byte)"
        ::= { zxGponPptpCESUNIEntry 2 }
      
   zxGponPptpCESUNILoopback OBJECT-TYPE
        SYNTAX      INTEGER{
                    noloop(1),
                    payloadloop(2),
                    lineloop(3),
                    opsloop1(4),
                    opsloop2(5),
                    opsloop3(6),
                    manualloop(7),
                    netloop(8),
                    smartjackloop(9),
                    netlooparmed(10)
                    }
        MAX-ACCESS  read-write
        STATUS      current
        DESCRIPTION
        " This attribute specifies and reports the loopback configuration of the physical interface.(1 byte)"
        ::= { zxGponPptpCESUNIEntry 3 }

   zxGponPptpCESUNIAdminState OBJECT-TYPE
        SYNTAX      INTEGER{
                    unlock(1),
                    lock(2)
                    }
        MAX-ACCESS  read-write
        STATUS      current
        DESCRIPTION
        "This attribute is used to activate (unlock: value 0x00) and deactivate (lock: value 0x01) 
        the functions performed by instances of this managed entity.(1 byte)"
        ::= { zxGponPptpCESUNIEntry 4 }
        
    zxGponPptpCESUNIOperState OBJECT-TYPE
        SYNTAX      INTEGER{
                    enable(1),
                    disable(2)
                    }
        MAX-ACCESS  read-only
        STATUS      current
        DESCRIPTION
        "This attribute indicates whether or not this managed entity is capable of performing 
        its task. The operational state reflects the perceived ability to receive or to generate 
        a valid signal. Valid values are enabled (0x00) and disabled (0x01).(1 byte)"
        ::= { zxGponPptpCESUNIEntry 5 }

    zxGponPptpCESUNIDs1Framing OBJECT-TYPE
        SYNTAX      INTEGER{
                    extendsuper(1),
                    super(2),
                    unframe(3),
                    g704(4),
                    jtg704(5)
                    }
        MAX-ACCESS  read-write
        STATUS      current
        DESCRIPTION
        "This attribute specifies the DS1 framing structure.(1 byte)"
        ::= { zxGponPptpCESUNIEntry 6 }
        
    zxGponPptpCESUNIEncoding OBJECT-TYPE
        SYNTAX      INTEGER{
                    b8zs(1),
                    ami(2),
                    hdb3(3),
                    b3zs(4)
                    }
        MAX-ACCESS  read-write
        STATUS      current
        DESCRIPTION
        "This attribute specifies the line coding scheme.(1 byte)"
        ::= { zxGponPptpCESUNIEntry 7 }
        
    zxGponPptpCESUNILineLength OBJECT-TYPE
        SYNTAX      INTEGER
        MAX-ACCESS  read-write
        STATUS      current
        DESCRIPTION
        "This attribute specifies the length of the twisted pair cable from a DS1 
        physical UNI to the DSX-1 cross-connect point or the length of co-axial 
        cable from a DS3 physical UNI to the DSX-3 cross-connect point. Valid values 
        are given in table 9.8.1-1/G.984.4..(1 byte)"
        ::= { zxGponPptpCESUNIEntry 8 }
        
    zxGponPptpCESUNIDs1Mode OBJECT-TYPE
        SYNTAX      INTEGER{
                    mode1(1),
                    mode2(2),
                    mode3(3),
                    mode4(4)
                    }
        MAX-ACCESS  read-write
        STATUS      current
        DESCRIPTION
        "This attribute specifies the mode of a DS1.(1 byte)"
        ::= { zxGponPptpCESUNIEntry 9 }
    
    zxGponPptpCESUNIARC OBJECT-TYPE
        SYNTAX      INTEGER
        MAX-ACCESS  read-write
        STATUS      current
        DESCRIPTION
        "This attribute is used to control alarm reporting from this managed entity. See clause I.1.8/G.984.4.(1 byte)"
        ::= { zxGponPptpCESUNIEntry 10 }
        
    zxGponPptpCESUNIARCInterval OBJECT-TYPE
        SYNTAX      INTEGER
        MAX-ACCESS  read-write
        STATUS      current
        DESCRIPTION
        "This attribute provides a provisionable length of time. See clause I.1.8/G.984.4.(1 byte)"
        ::= { zxGponPptpCESUNIEntry 11 }
 
    zxGponPptpCESUNILineType OBJECT-TYPE
        SYNTAX      INTEGER{
                    other(1),
                    ds3m23(2),
                    ds3syntran(3),
                    ds3cbitparity(4),
                    ds3clearchannel(5),
                    e3framed(6),
                    e3plcp(7)
                    }
        MAX-ACCESS  read-write
        STATUS      current
        DESCRIPTION
        "This attribute specifies the line type used in a DS3 or E3 application.(1 byte)"
        ::= { zxGponPptpCESUNIEntry 12 }

--MAC service profile
--MAC Bridge service profile
    zxGponMACBridgeServiceProfileTable    OBJECT-TYPE
        SYNTAX      SEQUENCE OF ZxGponMACBridgeServiceProfileEntry
        MAX-ACCESS  not-accessible
        STATUS      current
        DESCRIPTION
            "This managed entity is used to organize data that affects all ports 
            on a MAC Bridge at a bridged LAN Ethernet UNI interface on the ONT.
            Zero or more instances of this managed entity shall be referred to 
            by the Physical Path Termination Point Ethernet UNI managed entity."
        REFERENCE   "G.983.2 section 7.3.29 MAC Bridge service profile"
        ::= { zxGponL2Mgmt 8 }
        
    zxGponMACBridgeServiceProfileEntry OBJECT-TYPE
        SYNTAX      ZxGponMACBridgeServiceProfileEntry
        MAX-ACCESS  not-accessible
        STATUS      current
        DESCRIPTION
            "It is entry in the zxGponMACBridgeServiceProfileTable."
        INDEX   { zxGponOltIndex, zxGponONTIndex, zxGponBridgeIndex }
        ::= { zxGponMACBridgeServiceProfileTable 1 }
        
    ZxGponMACBridgeServiceProfileEntry ::=
        SEQUENCE {
            zxGponMACBridgeServiceProfileSpanTreeInd           TruthValue,
            zxGponMACBridgeServiceProfileLearningInd           TruthValue,
            zxGponMACBridgeServiceProfileATMPortBridgeInd      TruthValue,
            zxGponMACBridgeServiceProfilePriority              INTEGER,
            zxGponMACBridgeServiceProfileMaxAge                INTEGER,
            zxGponMACBridgeServiceProfileHelloTime             INTEGER,
            zxGponMACBridgeServiceProfileForwardDelay          INTEGER,
            zxGponMACBridgeServiceProfileUnknownMACAddrDiscard TruthValue,
            zxGponMACBridgeServiceProfileMACLearningDepth      INTEGER
        }

    zxGponMACBridgeServiceProfileSpanTreeInd OBJECT-TYPE
        SYNTAX      TruthValue
        MAX-ACCESS  read-write
        STATUS      current
        DESCRIPTION
        "This Boolean attribute indicates whether or not a spanning tree algorithm is 
        enabled. The value TRUE means enabled.(1 byte)"
        REFERENCE   "G.983.2 section 7.3.29 MAC Bridge service profile"
        ::= { zxGponMACBridgeServiceProfileEntry 1 }
        
    zxGponMACBridgeServiceProfileLearningInd OBJECT-TYPE
        SYNTAX      TruthValue
        MAX-ACCESS  read-write
        STATUS      current
        DESCRIPTION
        "This Boolean attribute indicates whether or not the learning functions of the 
        bridge are enabled. The value TRUE means enabled.(1 byte)"
        REFERENCE   "G.983.2 section 7.3.29 MAC Bridge service profile"
        ::= { zxGponMACBridgeServiceProfileEntry 2 }

    zxGponMACBridgeServiceProfileATMPortBridgeInd OBJECT-TYPE
        SYNTAX      TruthValue
        MAX-ACCESS  read-write
        STATUS      current
        DESCRIPTION
        "This Boolean attribute indicates whether or not bridging between ATM ports on this 
        bridge service is enabled. The value TRUE means enabled. (1 byte)"
        REFERENCE   "G.983.2 section 7.3.29 MAC Bridge service profile"
        ::= { zxGponMACBridgeServiceProfileEntry 3 }
        
    zxGponMACBridgeServiceProfilePriority OBJECT-TYPE
        SYNTAX      INTEGER
        MAX-ACCESS  read-write
        STATUS      current
        DESCRIPTION
        "This attribute indicates the bridge priority set on the LAN card. The range is 0x00 to 
        0xFFFF (0 to 65535). The value of this attribute is copied to the BridgePriority attribute 
        of the MAC Bridge Configuration Data managed entity.(2 bytes)"
        REFERENCE   "G.983.2 section 7.3.29 MAC Bridge service profile"
        ::= { zxGponMACBridgeServiceProfileEntry 4 }
        
    zxGponMACBridgeServiceProfileMaxAge OBJECT-TYPE
        SYNTAX      INTEGER
        MAX-ACCESS  read-write
        STATUS      current
        DESCRIPTION
        "This attribute indicates the maximum age (in 256ths of a second) for an entry in the 
        spanning tree listing. It indicates the maximum age in 256ths of a second for received 
        protocol information before it is discarded. The range is 0x0600 to 0x2800 (6 s to 40 s) 
        in accordance with IEEE 802.1D [13].(2 bytes)"
        REFERENCE   "G.983.2 section 7.3.29 MAC Bridge service profile"
        ::= { zxGponMACBridgeServiceProfileEntry 5 }
        
    zxGponMACBridgeServiceProfileHelloTime OBJECT-TYPE
        SYNTAX      INTEGER
        MAX-ACCESS  read-write
        STATUS      current
        DESCRIPTION
        "This attribute provides the time interval (in 256ths of a second) between hello packets. 
        It is the time interval, in 256ths of a second, that a bridge advertises its presence 
        while as a root or attempting to become a root. The range is 0x0100 to 0x0a00 (1 s to 10 s) 
        in accordance with IEEE 802.1D [13].(2 bytes)"
        REFERENCE   "G.983.2 section 7.3.29 MAC Bridge service profile"
        ::= { zxGponMACBridgeServiceProfileEntry 6 }
        
    zxGponMACBridgeServiceProfileForwardDelay OBJECT-TYPE
        SYNTAX      INTEGER
        MAX-ACCESS  read-write
        STATUS      current
        DESCRIPTION
        "This attribute gives the time (in 256ths of a second) that the bridge on the Ethernet 
        card in the ONT retains a packet before forwarding it. (It indicates the value in 256ths 
        of a second that the bridge uses for Forward Delay when the bridge acts as the root.) 
        The range is 0x0400 to 0x1e00 (4 s to 30 s) in accordance with IEEE 802.1D [13].(2 bytes)"
        REFERENCE   "G.983.2 section 7.3.29 MAC Bridge service profile"
        ::= { zxGponMACBridgeServiceProfileEntry 7 }
        
    zxGponMACBridgeServiceProfileUnknownMACAddrDiscard OBJECT-TYPE
        SYNTAX      TruthValue
        MAX-ACCESS  read-write
        STATUS      current
        DESCRIPTION
        "This Boolean attribute indicates the treatment of MAC frames with unknown destination 
        addresses.  The value TRUE means that frames with unknown destination addresses will be 
        discarded.  The value FALSE means that such frames will be forwarded to all allowed ports.(1 byte)"
        REFERENCE   "G.983.2 section 7.3.29 MAC Bridge service profile"
        ::= { zxGponMACBridgeServiceProfileEntry 8 }

    zxGponMACBridgeServiceProfileMACLearningDepth OBJECT-TYPE
        SYNTAX      INTEGER(0..255)
        MAX-ACCESS  read-write
        STATUS      current
        DESCRIPTION
        "This attribute specifies the maximum number of UNI MAC addresses to be learned by the bridge. 
         The default value 0 specifies that there is no administratively-imposed limit. 
         (R, W, Set-by-create) (optional) (1 byte)"
        REFERENCE   "G.983.2 section 7.3.29 MAC Bridge service profile"
        ::= { zxGponMACBridgeServiceProfileEntry 9 }

--MAC Bridge configuration data
    zxGponMACBridgeConfigDataTable    OBJECT-TYPE
        SYNTAX      SEQUENCE OF ZxGponMACBridgeConfigDataEntry
        MAX-ACCESS  not-accessible
        STATUS      current
        DESCRIPTION
            "This managed entity is used to organize and record data that is associated with bridged 
            LAN configurations. Some of the data is volatile.
            This managed entity is associated with one instance of a MACBridgeServiceProfile."
        REFERENCE   "G.983.2 section 7.3.30 MAC Bridge configuration data"
        ::= { zxGponL2Mgmt 9 }
        
    zxGponMACBridgeConfigDataEntry OBJECT-TYPE
        SYNTAX      ZxGponMACBridgeConfigDataEntry
        MAX-ACCESS  not-accessible
        STATUS      current
        DESCRIPTION
            "It is entry in the zxGponMACBridgeConfigDataTable."
        INDEX   { zxGponOltIndex, zxGponONTIndex, zxGponBridgeIndex }
        ::= { zxGponMACBridgeConfigDataTable 1 }
        
    ZxGponMACBridgeConfigDataEntry ::=
        SEQUENCE {
            zxGponMACBridgeConfigDataBridgeMACAddr         MacAddress,
            zxGponMACBridgeConfigDataBridgePrio            INTEGER,
            zxGponMACBridgeConfigDataDesignatedRoot        INTEGER,
            zxGponMACBridgeConfigDataRootPathCost          INTEGER,
            zxGponMACBridgeConfigDataBridgePortCount       INTEGER,
            zxGponMACBridgeConfigDataRootPortNum           INTEGER,
            zxGponMACBridgeConfigDataHelloTime             INTEGER,
            zxGponMACBridgeConfigDataForwardDelay          INTEGER
        }

    zxGponMACBridgeConfigDataBridgeMACAddr OBJECT-TYPE
        SYNTAX      MacAddress
        MAX-ACCESS  read-only
        STATUS      current
        DESCRIPTION
        "This attribute indicates the MAC address used by the bridge. 
        Upon autonomous instantiation, this attribute consists of all 0x00.(6 bytes)"
        REFERENCE   "G.983.2 section 7.3.30 MAC Bridge configuration data"
        ::= { zxGponMACBridgeConfigDataEntry 1 }
        
    zxGponMACBridgeConfigDataBridgePrio OBJECT-TYPE
        SYNTAX      INTEGER
        MAX-ACCESS  read-only
        STATUS      current
        DESCRIPTION
        "This attribute denotes the priority of the bridge and is positive integer-valued. 
        Upon autonomous instantiation, the value 0x8000 is used. The value of this attribute 
        follows the value of the associated MAC Bridge Service Profile: Priority attribute, 
        if present.(2 bytes)"
        REFERENCE   "G.983.2 section 7.3.30 MAC Bridge configuration data"
        ::= { zxGponMACBridgeConfigDataEntry 2 }

    zxGponMACBridgeConfigDataDesignatedRoot OBJECT-TYPE
        SYNTAX      INTEGER
        MAX-ACCESS  read-only
        STATUS      current
        DESCRIPTION
        "This attribute provides the bridge identifier for the root of the spanning tree. 
        This attribute consists of Bridge Priority (2 bytes) and MAC address (6 bytes).
        (8 bytes)"
        REFERENCE   "G.983.2 section 7.3.30 MAC Bridge configuration data"
        ::= { zxGponMACBridgeConfigDataEntry 3 }

    zxGponMACBridgeConfigDataRootPathCost OBJECT-TYPE
        SYNTAX      INTEGER
        MAX-ACCESS  read-only
        STATUS      current
        DESCRIPTION
        "This attribute provides the cost of the best path to the root as seen from the 
        bridge. Upon autonomous instantiation, the value 0x00 is used.(4 bytes)"
        REFERENCE   "G.983.2 section 7.3.30 MAC Bridge configuration data"
        ::= { zxGponMACBridgeConfigDataEntry 4 }

    zxGponMACBridgeConfigDataBridgePortCount OBJECT-TYPE
        SYNTAX      INTEGER
        MAX-ACCESS  read-only
        STATUS      current
        DESCRIPTION
        "This attribute provides the number of existing ports controlled by this bridge.(1 byte)"
        REFERENCE   "G.983.2 section 7.3.30 MAC Bridge configuration data"
        ::= { zxGponMACBridgeConfigDataEntry 5 }

    zxGponMACBridgeConfigDataRootPortNum OBJECT-TYPE
        SYNTAX      INTEGER
        MAX-ACCESS  read-only
        STATUS      current
        DESCRIPTION
        "This attribute provides the port number that has the lowest cost from the bridge to 
        the root bridge. The value 0x00 means that the bridge itself is the root. 
        Upon autonomous instantiation, the value 0x00 is used.(2 bytes)"
        REFERENCE   "G.983.2 section 7.3.30 MAC Bridge configuration data"
        ::= { zxGponMACBridgeConfigDataEntry 6 }
        
    zxGponMACBridgeConfigDataHelloTime OBJECT-TYPE
        SYNTAX      INTEGER
        MAX-ACCESS  read-only
        STATUS      current
        DESCRIPTION
        "This attribute provides the time interval (in 256ths of a second) between hello 
        packets. It is the 'HelloTime' received from the designated root. 
        The range is 0x0100 to 0x0a00 (1 s to 10 s) in accordance with IEEE 802.1D [13].(2 bytes)"
        REFERENCE   "G.983.2 section 7.3.30 MAC Bridge configuration data"
        ::= { zxGponMACBridgeConfigDataEntry 7 }
        
    zxGponMACBridgeConfigDataForwardDelay OBJECT-TYPE
        SYNTAX      INTEGER
        MAX-ACCESS  read-only
        STATUS      current
        DESCRIPTION
        "This attribute gives the time (in 256ths of a second) that the bridge on the Ethernet 
        card in the ONT retains a packet before forwarding it. It is the 'ForwardDelay' time 
        received from the designated root. The range is 0x0400 to 0x1e00 (4 s to 30 s) in 
        accordance with IEEE 802.1D [13].(2 bytes)"
        REFERENCE   "G.983.2 section 7.3.30 MAC Bridge configuration data"
        ::= { zxGponMACBridgeConfigDataEntry 8 }

--802.1p mapper service profile
    zxGponUNIDot1pMapServiceProfileTable    OBJECT-TYPE
        SYNTAX      SEQUENCE OF ZxGponUNIDot1pMapServiceProfileEntry
        MAX-ACCESS  not-accessible
        STATUS      current
        DESCRIPTION
            "This managed entity is used to associate the priorities of 802.1P priority tagged 
            frames of a certain Ethernet UNI with a specific connection.
            One instance of this ME may be associated with zero or one instance of the PPTP UNI ME."
        REFERENCE   "G.983.2 section 7.3.95 802.1p mapper service profile"
        ::= { zxGponL2Mgmt 10 }
        
    zxGponUNIDot1pMapServiceProfileEntry OBJECT-TYPE
        SYNTAX      ZxGponUNIDot1pMapServiceProfileEntry
        MAX-ACCESS  not-accessible
        STATUS      current
        DESCRIPTION
            "It is entry in the zxGponUNIDot1pMapServiceProfileTable."
        INDEX   { zxGponOltIndex, zxGponONTIndex, zxGponUNIIndex }
        ::= { zxGponUNIDot1pMapServiceProfileTable 1 }
        
    ZxGponUNIDot1pMapServiceProfileEntry ::=
        SEQUENCE {
            zxGponUNIDot1pMapServiceProfilePrio0GemPortId          INTEGER,
            zxGponUNIDot1pMapServiceProfilePrio1GemPortId          INTEGER,
            zxGponUNIDot1pMapServiceProfilePrio2GemPortId          INTEGER,
            zxGponUNIDot1pMapServiceProfilePrio3GemPortId          INTEGER,
            zxGponUNIDot1pMapServiceProfilePrio4GemPortId          INTEGER,
            zxGponUNIDot1pMapServiceProfilePrio5GemPortId          INTEGER,
            zxGponUNIDot1pMapServiceProfilePrio6GemPortId          INTEGER,
            zxGponUNIDot1pMapServiceProfilePrio7GemPortId          INTEGER,
            zxGponUNIDot1pMapServiceProfileUnmarkedFrameOption     INTEGER,
            zxGponUNIDot1pMapServiceProfileDSCP2PBitMap            OCTET STRING,
            zxGponUNIDot1pMapServiceProfileDefPBitMarking          INTEGER
        }

    zxGponUNIDot1pMapServiceProfilePrio0GemPortId OBJECT-TYPE
        SYNTAX      INTEGER
        MAX-ACCESS  read-only
        STATUS      current
        DESCRIPTION
        "This attribute represents the GEM port id that is 
        associated with P-Bit = 000 tagged frames. The value 0xFFFF is a null pointer.(2 bytes)"
        REFERENCE   "G.983.2 section 7.3.95 802.1p mapper service profile"
        ::= { zxGponUNIDot1pMapServiceProfileEntry 1 }

    zxGponUNIDot1pMapServiceProfilePrio1GemPortId OBJECT-TYPE
        SYNTAX      INTEGER
        MAX-ACCESS  read-only
        STATUS      current
        DESCRIPTION
        "This attribute represents a pointer to the Interworking Termination Point that is 
        associated with P-Bit = 001 tagged frames. The value 0xFFFF is a null pointer.(2 bytes)"
        REFERENCE   "G.983.2 section 7.3.95 802.1p mapper service profile"
        ::= { zxGponUNIDot1pMapServiceProfileEntry 2 }
        
    zxGponUNIDot1pMapServiceProfilePrio2GemPortId OBJECT-TYPE
        SYNTAX      INTEGER
        MAX-ACCESS  read-only
        STATUS      current
        DESCRIPTION
        "This attribute represents a pointer to the Interworking Termination Point that is 
        associated with P-Bit = 010 tagged frames. The value 0xFFFF is a null pointer.(2 bytes)"
        REFERENCE   "G.983.2 section 7.3.95 802.1p mapper service profile"
        ::= { zxGponUNIDot1pMapServiceProfileEntry 3 }
        
    zxGponUNIDot1pMapServiceProfilePrio3GemPortId OBJECT-TYPE
        SYNTAX      INTEGER
        MAX-ACCESS  read-only
        STATUS      current
        DESCRIPTION
        "This attribute represents a pointer to the Interworking Termination Point that is 
        associated with P-Bit = 011 tagged frames. The value 0xFFFF is a null pointer.(2 bytes)"
        REFERENCE   "G.983.2 section 7.3.95 802.1p mapper service profile"
        ::= { zxGponUNIDot1pMapServiceProfileEntry 4 }
        
    zxGponUNIDot1pMapServiceProfilePrio4GemPortId OBJECT-TYPE
        SYNTAX      INTEGER
        MAX-ACCESS  read-only
        STATUS      current
        DESCRIPTION
        "This attribute represents a pointer to the Interworking Termination Point that is 
        associated with P-Bit = 100 tagged frames. The value 0xFFFF is a null pointer.(2 bytes)"
        REFERENCE   "G.983.2 section 7.3.95 802.1p mapper service profile"
        ::= { zxGponUNIDot1pMapServiceProfileEntry 5 }
        
    zxGponUNIDot1pMapServiceProfilePrio5GemPortId OBJECT-TYPE
        SYNTAX      INTEGER
        MAX-ACCESS  read-only
        STATUS      current
        DESCRIPTION
        "This attribute represents a pointer to the Interworking Termination Point that is 
        associated with P-Bit = 101 tagged frames. The value 0xFFFF is a null pointer.(2 bytes)"
        REFERENCE   "G.983.2 section 7.3.95 802.1p mapper service profile"
        ::= { zxGponUNIDot1pMapServiceProfileEntry 6 }
        
    zxGponUNIDot1pMapServiceProfilePrio6GemPortId OBJECT-TYPE
        SYNTAX      INTEGER
        MAX-ACCESS  read-only
        STATUS      current
        DESCRIPTION
        "This attribute represents a pointer to the Interworking Termination Point that is 
        associated with P-Bit = 110 tagged frames. The value 0xFFFF is a null pointer.(2 bytes)"
        REFERENCE   "G.983.2 section 7.3.95 802.1p mapper service profile"
        ::= { zxGponUNIDot1pMapServiceProfileEntry 7 }

    zxGponUNIDot1pMapServiceProfilePrio7GemPortId OBJECT-TYPE
        SYNTAX      INTEGER
        MAX-ACCESS  read-only
        STATUS      current
        DESCRIPTION
        "This attribute represents a pointer to the Interworking Termination Point that is 
        associated with P-Bit = 111 tagged frames. The value 0xFFFF is a null pointer.(2 bytes)"
        REFERENCE   "G.983.2 section 7.3.95 802.1p mapper service profile"
        ::= { zxGponUNIDot1pMapServiceProfileEntry 8 }

    zxGponUNIDot1pMapServiceProfileUnmarkedFrameOption OBJECT-TYPE
        SYNTAX      INTEGER{
                    dscp2Dot1p(1),
                    defaultTag(2)
                    }
        MAX-ACCESS  read-write
        STATUS      current
        DESCRIPTION
        "This attribute indicates how the ONT should handle Untagged Ethernet frames received 
        across the associated Ethernet interface. Valid values include the following:
          0: Convert from DSCP to 802.1p;
          1: Tag frame to a certain value.
        (1 byte)"
        REFERENCE   "G.983.2 section 7.3.95 802.1p mapper service profile"
        ::= { zxGponUNIDot1pMapServiceProfileEntry 9 }
        
    zxGponUNIDot1pMapServiceProfileDSCP2PBitMap OBJECT-TYPE
        SYNTAX      OCTET STRING(SIZE(24))
        MAX-ACCESS  read-write
        STATUS      current
        DESCRIPTION
        "This attribute is used in conjunction with the Unmarked Frame Option attribute. 
        If unmarked frame option is 0, this attribute structure can be considered a bitmap 
        that represents a sequence of 64 '3-bit' groupings. Each of the 64 groupings represents 
        the possible value of the 6-bit DSCP field. Each of the '3-bit' groupings represents 
        the 'P-bit value' to which the associated DSCP value should be mapped. Once marked, 
        the P-Bit marked frame will then be routed to the GEM Interwork Pointer as indicated 
        by the P-Bit to Interwork Pointer mappings above.(24 bytes)"
        REFERENCE   "G.983.2 section 7.3.95 802.1p mapper service profile"
        ::= { zxGponUNIDot1pMapServiceProfileEntry 10 }
        
    zxGponUNIDot1pMapServiceProfileDefPBitMarking OBJECT-TYPE
        SYNTAX      INTEGER
        MAX-ACCESS  read-write
        STATUS      current
        DESCRIPTION
        "This attribute is used in conjunction with the Unmarked Frame Option attribute. 
        If unmarked frame option is 1, this attribute contains the default P-Bit priority 
        setting that will be applied to the frame. The P-Bit marked frame will then be 
        routed to the GEM Interwork Pointer as indicated by the P-Bit to Interwork Pointer 
        mappings above.(1 byte)"
        REFERENCE   "G.983.2 section 7.3.95 802.1p mapper service profile"
        ::= { zxGponUNIDot1pMapServiceProfileEntry 11 }
        
--802.1p mapper service profile associated with uplink
    zxGponUpLinkDot1pMapServiceProfileTable    OBJECT-TYPE
        SYNTAX      SEQUENCE OF ZxGponUpLinkDot1pMapServiceProfileEntry
        MAX-ACCESS  not-accessible
        STATUS      current
        DESCRIPTION
            "This managed entity is used to associate the priorities of 802.1P priority tagged 
            frames of a certain UpLink with a specific connection.
            One instance of this ME may be associated with zero or one instance of the MAC 
            bridge port configuration data ME."
        REFERENCE   "G.983.2 section 7.3.95 802.1p mapper service profile"
        ::= { zxGponL2Mgmt 11 }
        
    zxGponUpLinkDot1pMapServiceProfileEntry OBJECT-TYPE
        SYNTAX      ZxGponUpLinkDot1pMapServiceProfileEntry
        MAX-ACCESS  not-accessible
        STATUS      current
        DESCRIPTION
            "It is entry in the zxGponUpLinkDot1pMapServiceProfileTable."
        INDEX   { zxGponOltIndex, zxGponONTIndex, zxGponUpLinkIndex }
        ::= { zxGponUpLinkDot1pMapServiceProfileTable 1 }
        
    ZxGponUpLinkDot1pMapServiceProfileEntry ::=
        SEQUENCE {
            zxGponUpLinkDot1pMapServiceProfilePrio0GemPortId          INTEGER,
            zxGponUpLinkDot1pMapServiceProfilePrio1GemPortId          INTEGER,
            zxGponUpLinkDot1pMapServiceProfilePrio2GemPortId          INTEGER,
            zxGponUpLinkDot1pMapServiceProfilePrio3GemPortId          INTEGER,
            zxGponUpLinkDot1pMapServiceProfilePrio4GemPortId          INTEGER,
            zxGponUpLinkDot1pMapServiceProfilePrio5GemPortId          INTEGER,
            zxGponUpLinkDot1pMapServiceProfilePrio6GemPortId          INTEGER,
            zxGponUpLinkDot1pMapServiceProfilePrio7GemPortId          INTEGER,
            zxGponUpLinkDot1pMapServiceProfileUnmarkedFrameOption     INTEGER,
            zxGponUpLinkDot1pMapServiceProfileDSCP2PBitMap            OCTET STRING,
            zxGponUpLinkDot1pMapServiceProfileDefPBitMarking          INTEGER
        }

    zxGponUpLinkDot1pMapServiceProfilePrio0GemPortId OBJECT-TYPE
        SYNTAX      INTEGER
        MAX-ACCESS  read-only
        STATUS      current
        DESCRIPTION
        "This attribute represents a pointer to the Interworking Termination Point that is 
        associated with P-Bit = 000 tagged frames. The value 0xFFFF is a null pointer.(2 bytes)"
        REFERENCE   "G.983.2 section 7.3.95 802.1p mapper service profile"
        ::= { zxGponUpLinkDot1pMapServiceProfileEntry 1 }

    zxGponUpLinkDot1pMapServiceProfilePrio1GemPortId OBJECT-TYPE
        SYNTAX      INTEGER
        MAX-ACCESS  read-only
        STATUS      current
        DESCRIPTION
        "This attribute represents a pointer to the Interworking Termination Point that is 
        associated with P-Bit = 001 tagged frames. The value 0xFFFF is a null pointer.(2 bytes)"
        REFERENCE   "G.983.2 section 7.3.95 802.1p mapper service profile"
        ::= { zxGponUpLinkDot1pMapServiceProfileEntry 2 }
        
    zxGponUpLinkDot1pMapServiceProfilePrio2GemPortId OBJECT-TYPE
        SYNTAX      INTEGER
        MAX-ACCESS  read-only
        STATUS      current
        DESCRIPTION
        "This attribute represents a pointer to the Interworking Termination Point that is 
        associated with P-Bit = 010 tagged frames. The value 0xFFFF is a null pointer.(2 bytes)"
        REFERENCE   "G.983.2 section 7.3.95 802.1p mapper service profile"
        ::= { zxGponUpLinkDot1pMapServiceProfileEntry 3 }
        
    zxGponUpLinkDot1pMapServiceProfilePrio3GemPortId OBJECT-TYPE
        SYNTAX      INTEGER
        MAX-ACCESS  read-only
        STATUS      current
        DESCRIPTION
        "This attribute represents a pointer to the Interworking Termination Point that is 
        associated with P-Bit = 011 tagged frames. The value 0xFFFF is a null pointer.(2 bytes)"
        REFERENCE   "G.983.2 section 7.3.95 802.1p mapper service profile"
        ::= { zxGponUpLinkDot1pMapServiceProfileEntry 4 }
        
    zxGponUpLinkDot1pMapServiceProfilePrio4GemPortId OBJECT-TYPE
        SYNTAX      INTEGER
        MAX-ACCESS  read-only
        STATUS      current
        DESCRIPTION
        "This attribute represents a pointer to the Interworking Termination Point that is 
        associated with P-Bit = 100 tagged frames. The value 0xFFFF is a null pointer.(2 bytes)"
        REFERENCE   "G.983.2 section 7.3.95 802.1p mapper service profile"
        ::= { zxGponUpLinkDot1pMapServiceProfileEntry 5 }
        
    zxGponUpLinkDot1pMapServiceProfilePrio5GemPortId OBJECT-TYPE
        SYNTAX      INTEGER
        MAX-ACCESS  read-only
        STATUS      current
        DESCRIPTION
        "This attribute represents a pointer to the Interworking Termination Point that is 
        associated with P-Bit = 101 tagged frames. The value 0xFFFF is a null pointer.(2 bytes)"
        REFERENCE   "G.983.2 section 7.3.95 802.1p mapper service profile"
        ::= { zxGponUpLinkDot1pMapServiceProfileEntry 6 }
        
    zxGponUpLinkDot1pMapServiceProfilePrio6GemPortId OBJECT-TYPE
        SYNTAX      INTEGER
        MAX-ACCESS  read-only
        STATUS      current
        DESCRIPTION
        "This attribute represents a pointer to the Interworking Termination Point that is 
        associated with P-Bit = 110 tagged frames. The value 0xFFFF is a null pointer.(2 bytes)"
        REFERENCE   "G.983.2 section 7.3.95 802.1p mapper service profile"
        ::= { zxGponUpLinkDot1pMapServiceProfileEntry 7 }

    zxGponUpLinkDot1pMapServiceProfilePrio7GemPortId OBJECT-TYPE
        SYNTAX      INTEGER
        MAX-ACCESS  read-only
        STATUS      current
        DESCRIPTION
        "This attribute represents a pointer to the Interworking Termination Point that is 
        associated with P-Bit = 111 tagged frames. The value 0xFFFF is a null pointer.(2 bytes)"
        REFERENCE   "G.983.2 section 7.3.95 802.1p mapper service profile"
        ::= { zxGponUpLinkDot1pMapServiceProfileEntry 8 }

    zxGponUpLinkDot1pMapServiceProfileUnmarkedFrameOption OBJECT-TYPE
        SYNTAX      INTEGER{
                    dscp2Dot1p(1),
                    defaultTag(2)
                    }
        MAX-ACCESS  read-write
        STATUS      current
        DESCRIPTION
        "This attribute indicates how the ONT should handle Untagged Ethernet frames received 
        across the associated Ethernet interface. Valid values include the following:
          0: Convert from DSCP to 802.1p;
          1: Tag frame to a certain value.
        (1 byte)"
        REFERENCE   "G.983.2 section 7.3.95 802.1p mapper service profile"
        ::= { zxGponUpLinkDot1pMapServiceProfileEntry 9 }
        
    zxGponUpLinkDot1pMapServiceProfileDSCP2PBitMap OBJECT-TYPE
        SYNTAX      OCTET STRING(SIZE(24))
        MAX-ACCESS  read-write
        STATUS      current
        DESCRIPTION
        "This attribute is used in conjunction with the Unmarked Frame Option attribute. 
        If unmarked frame option is 0, this attribute structure can be considered a bitmap 
        that represents a sequence of 64 '3-bit' groupings. Each of the 64 groupings represents 
        the possible value of the 6-bit DSCP field. Each of the '3-bit' groupings represents 
        the 'P-bit value' to which the associated DSCP value should be mapped. Once marked, 
        the P-Bit marked frame will then be routed to the GEM Interwork Pointer as indicated 
        by the P-Bit to Interwork Pointer mappings above.(24 bytes)"
        REFERENCE   "G.983.2 section 7.3.95 802.1p mapper service profile"
        ::= { zxGponUpLinkDot1pMapServiceProfileEntry 10 }
        
    zxGponUpLinkDot1pMapServiceProfileDefPBitMarking OBJECT-TYPE
        SYNTAX      INTEGER
        MAX-ACCESS  read-write
        STATUS      current
        DESCRIPTION
        "This attribute is used in conjunction with the Unmarked Frame Option attribute. 
        If unmarked frame option is 1, this attribute contains the default P-Bit priority 
        setting that will be applied to the frame. The P-Bit marked frame will then be 
        routed to the GEM Interwork Pointer as indicated by the P-Bit to Interwork Pointer 
        mappings above.(1 byte)"
        REFERENCE   "G.983.2 section 7.3.95 802.1p mapper service profile"
        ::= { zxGponUpLinkDot1pMapServiceProfileEntry 11 }

--G.984.4 MAC Bridge Port Configuration Data
    zxGponUNIMACBridgePortConfigTable    OBJECT-TYPE
        SYNTAX      SEQUENCE OF ZxGponUNIMACBridgePortConfigEntry
        MAX-ACCESS  not-accessible
        STATUS      current
        DESCRIPTION
            "This managed entity is used to organize and record data that is associated with 
            a bridge port. Some of the data is volatile.
            Zero or more instances of this managed entity shall be contained in an instance of the 
            MACBridgeServiceProfile."
        REFERENCE   "G.984.4 MAC Bridge Port Configuation Data, details in G.983.2"
        ::= { zxGponL2Mgmt 12 }

    zxGponUNIMACBridgePortConfigEntry OBJECT-TYPE
        SYNTAX      ZxGponUNIMACBridgePortConfigEntry
        MAX-ACCESS  not-accessible
        STATUS      current
        DESCRIPTION
            "It is entry in the zxGponUNIMACBridgePortConfigTable."
        INDEX   { zxGponOltIndex, zxGponONTIndex, zxGponUNIIndex }
        ::= { zxGponUNIMACBridgePortConfigTable 1 }
        
    ZxGponUNIMACBridgePortConfigEntry ::=
        SEQUENCE {
            zxGponUNIMACBridgePortConfigBridgeId                INTEGER,
            zxGponUNIMACBridgePortConfigBridgePort              INTEGER,
            zxGponUNIMACBridgePortConfigPortPrio                INTEGER,
            zxGponUNIMACBridgePortConfigPortPathCost            INTEGER,
            zxGponUNIMACBridgePortConfigPortSpanTreeInd         TruthValue,
            zxGponUNIMACBridgePortConfigEncapMethod             INTEGER,
            zxGponUNIMACBridgePortConfigLANFCSInd               INTEGER,
            zxGponUNIMACBridgePortConfigPortMACAddr             MacAddress,
            zxGponUNIMACBridgePortConfigEntryStatus             RowStatus,
            zxGponUNIMACBridgePortConfigOutboundTDPtr           INTEGER,
            zxGponUNIMACBridgePortConfigInboundTDPtr            INTEGER
        }

    zxGponUNIMACBridgePortConfigBridgeId OBJECT-TYPE
        SYNTAX      INTEGER
        MAX-ACCESS  read-write
        STATUS      current
        DESCRIPTION
        "This attribute is set-by-create, indicating the bridge when create an UNI bridge port."
        REFERENCE   "G.984.4 MAC Bridge Port Configuation Data"
        ::= { zxGponUNIMACBridgePortConfigEntry 1 }

    zxGponUNIMACBridgePortConfigBridgePort OBJECT-TYPE
        SYNTAX      INTEGER
        MAX-ACCESS  read-only
        STATUS      current
        DESCRIPTION
        "This attribute identifies the MAC bridge port associated with the port.
        The first 2 bytes stand for the slot and bridge group id;
        The second 2 bytes stand for the bridge port num.(4 bytes)"
        REFERENCE   "G.984.4 MAC Bridge Port Configuation Data"
        ::= { zxGponUNIMACBridgePortConfigEntry 2 }

    zxGponUNIMACBridgePortConfigPortPrio OBJECT-TYPE
        SYNTAX      INTEGER
        MAX-ACCESS  read-write
        STATUS      current
        DESCRIPTION
        "This attribute denotes the priority of the port. 
        The range is 0x00 to 0x00FF (0 to 255).(2 bytes)"
        REFERENCE   "G.984.4 MAC Bridge Port Configuation Data"
        ::= { zxGponUNIMACBridgePortConfigEntry 3 }
        
    zxGponUNIMACBridgePortConfigPortPathCost OBJECT-TYPE
        SYNTAX      INTEGER
        MAX-ACCESS  read-write
        STATUS      current
        DESCRIPTION
        "This attribute provides the cost contribution of the port to the path cost 
        towards the spanning tree root bridge. The range is 0x0001 to 0xFFFF (1 to 65535).(2 bytes)"
        REFERENCE   "G.984.4 MAC Bridge Port Configuation Data"
        ::= { zxGponUNIMACBridgePortConfigEntry 4 }
        
    zxGponUNIMACBridgePortConfigPortSpanTreeInd OBJECT-TYPE
        SYNTAX      TruthValue
        MAX-ACCESS  read-write
        STATUS      current
        DESCRIPTION
        "This Boolean attribute indicates whether or not STP LAN topology change detection 
        is enabled at this port. The value TRUE means enabled.(1 byte)"
        REFERENCE   "G.984.4 MAC Bridge Port Configuation Data"
        ::= { zxGponUNIMACBridgePortConfigEntry 5 }
        
    zxGponUNIMACBridgePortConfigEncapMethod OBJECT-TYPE
        SYNTAX      INTEGER{
                    atmvc(1),
                    llc(2)
                    }
        MAX-ACCESS  read-write
        STATUS      current
        DESCRIPTION
        "This attribute identifies the frame encapsulation method that is used.
        0x00: identification by ATM VC;
        0x01: LLC encapsulation;
        This attribute is effective only for ports towards the ANI side of the MAC bridge. 
        Upon autonomous instantiation, the value 0x00 is used.
        (1 byte)"
        REFERENCE   "G.984.4 MAC Bridge Port Configuation Data"
        ::= { zxGponUNIMACBridgePortConfigEntry 6 }
        
    zxGponUNIMACBridgePortConfigLANFCSInd OBJECT-TYPE
        SYNTAX      INTEGER{
                    forward(1),
                    discard(2)
                    }
        MAX-ACCESS  read-write
        STATUS      current
        DESCRIPTION
        "This attribute indicates whether LAN FCS (Frame Check Sequence) bytes are 
        forwarded (value 0x00) or discarded (value 0x01). This applies in both directions of 
        transmission, and applies regardless of EncapsulationMethod. 
        This attribute is effective only for ports towards the ANI side of the MAC bridge. 
        Upon autonomous instantiation, the value 0x00 is used.(1 byte)"
        REFERENCE   "G.984.4 MAC Bridge Port Configuation Data"
        ::= { zxGponUNIMACBridgePortConfigEntry 7 }

    zxGponUNIMACBridgePortConfigPortMACAddr OBJECT-TYPE
        SYNTAX      MacAddress
        MAX-ACCESS  read-only
        STATUS      current
        DESCRIPTION
        "This attribute indicates the Physical MAC address used by the Port as defined by 
        the TPPointer when the TPType is set to LAN.(6 bytes)"
        REFERENCE   "G.984.4 MAC Bridge Port Configuation Data"
        ::= { zxGponUNIMACBridgePortConfigEntry 8 }
        
    zxGponUNIMACBridgePortConfigEntryStatus OBJECT-TYPE
        SYNTAX      RowStatus
        MAX-ACCESS  read-write
        STATUS      current
        DESCRIPTION
        "This attribute indicates the Physical MAC address used by the Port as defined by 
        the TPPointer when the TPType is set to LAN.(6 bytes)"
        REFERENCE   "G.984.4 MAC Bridge Port Configuation Data"
        ::= { zxGponUNIMACBridgePortConfigEntry 9 }

    zxGponUNIMACBridgePortConfigOutboundTDPtr OBJECT-TYPE
        SYNTAX      INTEGER
        MAX-ACCESS  read-write
        STATUS      current
        DESCRIPTION
        "This attribute points to a GEM traffic descriptor that limits the traffic rate 
         leaving the MAC bridge(2 byte)"
        REFERENCE   "G.984.4 MAC Bridge Port Configuation Data"
        ::= { zxGponUNIMACBridgePortConfigEntry 10 }

    zxGponUNIMACBridgePortConfigInboundTDPtr OBJECT-TYPE
        SYNTAX      INTEGER
        MAX-ACCESS  read-write
        STATUS      current
        DESCRIPTION
        "This attribute points to a GEM traffic descriptor that limits the traffic rate 
         entering the MAC bridge(2 byte)"
        REFERENCE   "G.984.4 MAC Bridge Port Configuation Data"
        ::= { zxGponUNIMACBridgePortConfigEntry 11 }

--MAC bridge port configuration for uplink
    zxGponUpLinkMACBridgePortConfigTable    OBJECT-TYPE
        SYNTAX      SEQUENCE OF ZxGponUpLinkMACBridgePortConfigEntry
        MAX-ACCESS  not-accessible
        STATUS      current
        DESCRIPTION
            "This managed entity is used to organize and record data that is associated with 
            a bridge port. Some of the data is volatile.
            Zero or more instances of this managed entity shall be contained in an instance of the 
            MACBridgeServiceProfile."
        REFERENCE   "G.984.4 section 9.3.9 MAC Bridge Port Configuation Data, details in G.983.2"
        ::= { zxGponL2Mgmt 13 }

    zxGponUpLinkMACBridgePortConfigEntry OBJECT-TYPE
        SYNTAX      ZxGponUpLinkMACBridgePortConfigEntry
        MAX-ACCESS  not-accessible
        STATUS      current
        DESCRIPTION
            "It is entry in the zxGponUpLinkMACBridgePortConfigTable."
        INDEX   { zxGponOltIndex, zxGponONTIndex, zxGponUpLinkIndex }
        ::= { zxGponUpLinkMACBridgePortConfigTable 1 }
        
    ZxGponUpLinkMACBridgePortConfigEntry ::=
        SEQUENCE {
            zxGponUpLinkMACBridgePortConfigBridgePort              INTEGER,
            zxGponUpLinkMACBridgePortConfigPortPrio                INTEGER,
            zxGponUpLinkMACBridgePortConfigPortPathCost            INTEGER,
            zxGponUpLinkMACBridgePortConfigPortSpanTreeInd         TruthValue,
            zxGponUpLinkMACBridgePortConfigEncapMethod             INTEGER,
            zxGponUpLinkMACBridgePortConfigLANFCSInd               INTEGER,
            zxGponUpLinkMACBridgePortConfigPortMACAddr             MacAddress
        }

    zxGponUpLinkMACBridgePortConfigBridgePort OBJECT-TYPE
        SYNTAX      INTEGER
        MAX-ACCESS  read-only
        STATUS      current
        DESCRIPTION
        "This attribute identifies the MAC bridge port associated with the port.
        The first 2 bytes stand for the slot and bridge group id;
        The second 2 bytes stand for the bridge port num.(4 bytes)"
        REFERENCE   "G.984.4 section 9.3.9 MAC Bridge Port Configuation Data"
        ::= { zxGponUpLinkMACBridgePortConfigEntry 1 }

    zxGponUpLinkMACBridgePortConfigPortPrio OBJECT-TYPE
        SYNTAX      INTEGER
        MAX-ACCESS  read-write
        STATUS      current
        DESCRIPTION
        "This attribute denotes the priority of the port. 
        The range is 0x00 to 0x00FF (0 to 255).(2 bytes)"
        REFERENCE   "G.984.4 section 9.3.9 MAC Bridge Port Configuation Data"
        ::= { zxGponUpLinkMACBridgePortConfigEntry 2 }

    zxGponUpLinkMACBridgePortConfigPortPathCost OBJECT-TYPE
        SYNTAX      INTEGER
        MAX-ACCESS  read-write
        STATUS      current
        DESCRIPTION
        "This attribute provides the cost contribution of the port to the path cost 
        towards the spanning tree root bridge. The range is 0x0001 to 0xFFFF (1 to 65535).(2 bytes)"
        REFERENCE   "G.984.4 section 9.3.9 MAC Bridge Port Configuation Data"
        ::= { zxGponUpLinkMACBridgePortConfigEntry 3 }
        
    zxGponUpLinkMACBridgePortConfigPortSpanTreeInd OBJECT-TYPE
        SYNTAX      TruthValue
        MAX-ACCESS  read-write
        STATUS      current
        DESCRIPTION
        "This Boolean attribute indicates whether or not STP LAN topology change detection 
        is enabled at this port. The value TRUE means enabled.(1 byte)"
        REFERENCE   "G.984.4 section 9.3.9 MAC Bridge Port Configuation Data"
        ::= { zxGponUpLinkMACBridgePortConfigEntry 4 }
        
    zxGponUpLinkMACBridgePortConfigEncapMethod OBJECT-TYPE
        SYNTAX      INTEGER{
                    atmvc(1),
                    llc(2)
                    }
        MAX-ACCESS  read-write
        STATUS      current
        DESCRIPTION
        "This attribute identifies the frame encapsulation method that is used.
        0x00: identification by ATM VC;
        0x01: LLC encapsulation;
        This attribute is effective only for ports towards the ANI side of the MAC bridge. 
        Upon autonomous instantiation, the value 0x00 is used.
        (1 byte)"
        REFERENCE   "G.984.4 section 9.3.9 MAC Bridge Port Configuation Data"
        ::= { zxGponUpLinkMACBridgePortConfigEntry 5 }
        
    zxGponUpLinkMACBridgePortConfigLANFCSInd OBJECT-TYPE
        SYNTAX      INTEGER{
                    forward(1),
                    discard(2)
                    }
        MAX-ACCESS  read-write
        STATUS      current
        DESCRIPTION
        "This attribute indicates whether LAN FCS (Frame Check Sequence) bytes are 
        forwarded (value 0x00) or discarded (value 0x01). This applies in both directions of 
        transmission, and applies regardless of EncapsulationMethod. 
        This attribute is effective only for ports towards the ANI side of the MAC bridge. 
        Upon autonomous instantiation, the value 0x00 is used.(1 byte)"
        REFERENCE   "G.984.4 section 9.3.9 MAC Bridge Port Configuation Data"
        ::= { zxGponUpLinkMACBridgePortConfigEntry 6 }

    zxGponUpLinkMACBridgePortConfigPortMACAddr OBJECT-TYPE
        SYNTAX      MacAddress
        MAX-ACCESS  read-only
        STATUS      current
        DESCRIPTION
        "This attribute indicates the Physical MAC address used by the Port as defined by 
        the TPPointer when the TPType is set to LAN.(6 bytes)"
        REFERENCE   "G.984.4 section 9.3.9 MAC Bridge Port Configuation Data"
        ::= { zxGponUpLinkMACBridgePortConfigEntry 7 }

--G.983.2 7.3.33 MAC Bridge port filter table data
--for UNI
    zxGponUNIBridgePortMacFilterTable    OBJECT-TYPE
        SYNTAX      SEQUENCE OF ZxGponUNIBridgePortMacFilterEntry
        MAX-ACCESS  not-accessible
        STATUS      current
        DESCRIPTION
            "This managed entity is used to organize and record data that is associated with 
            a bridge port. Some of the data is volatile.
            This managed entity is associated with one instance of a MACBridgePortConfigurationData."
        REFERENCE   "G.983.2 section 7.3.33 MAC Bridge port filter table data"
        ::= { zxGponL2Mgmt 14 }

    zxGponUNIBridgePortMacFilterEntry OBJECT-TYPE
        SYNTAX      ZxGponUNIBridgePortMacFilterEntry
        MAX-ACCESS  not-accessible
        STATUS      current
        DESCRIPTION
            "It is entry in the zxGponUNIBridgePortMacFilterTable."
        INDEX   { zxGponOltIndex, zxGponONTIndex, zxGponUNIIndex, zxGponUNIBridgePortMacFilterAddress }
        ::= { zxGponUNIBridgePortMacFilterTable 1 }

    ZxGponUNIBridgePortMacFilterEntry ::=
        SEQUENCE {
            zxGponUNIBridgePortMacFilterAddress                 MacAddress,
            zxGponUNIBridgePortMacFilterFilterMode              INTEGER,
            zxGponUNIBridgePortMacFilterEntryStatus             RowStatus
        }

    zxGponUNIBridgePortMacFilterAddress OBJECT-TYPE
        SYNTAX      MacAddress
        MAX-ACCESS  read-only
        STATUS      current
        DESCRIPTION
        "This attribute specifies the MAC address being filtered."
        REFERENCE   "G.983.2 section 7.3.33 MAC Bridge port filter table data"
        ::= { zxGponUNIBridgePortMacFilterEntry 1 }
        
    zxGponUNIBridgePortMacFilterFilterMode OBJECT-TYPE
        SYNTAX      INTEGER{
                    forward(1),
                    discard(2)
                    }
        MAX-ACCESS  read-write
        STATUS      current
        DESCRIPTION
        "This attribute specifies the filter action."
        REFERENCE   "G.983.2 section 7.3.33 MAC Bridge port filter table data"
        ::= { zxGponUNIBridgePortMacFilterEntry 2 }
        
    zxGponUNIBridgePortMacFilterEntryStatus OBJECT-TYPE
        SYNTAX      RowStatus
        MAX-ACCESS  read-write
        STATUS      current
        DESCRIPTION
        "This attribute specifies the operation of this entry."
        REFERENCE   "G.983.2 section 7.3.33 MAC Bridge port filter table data"
        ::= { zxGponUNIBridgePortMacFilterEntry 3 }

--for uplink
    zxGponUpLinkBridgePortMacFilterTable    OBJECT-TYPE
        SYNTAX      SEQUENCE OF ZxGponUpLinkBridgePortMacFilterEntry
        MAX-ACCESS  not-accessible
        STATUS      current
        DESCRIPTION
            "This managed entity is used to organize and record data that is associated with 
            a bridge port. Some of the data is volatile.
            This managed entity is associated with one instance of a MACBridgePortConfigurationData."
        REFERENCE   "G.983.2 section 7.3.33 MAC Bridge port filter table data"
        ::= { zxGponL2Mgmt 15 }

    zxGponUpLinkBridgePortMacFilterEntry OBJECT-TYPE
        SYNTAX      ZxGponUpLinkBridgePortMacFilterEntry
        MAX-ACCESS  not-accessible
        STATUS      current
        DESCRIPTION
            "It is entry in the zxGponUpLinkBridgePortMacFilterTable."
        INDEX   { zxGponOltIndex, zxGponONTIndex, zxGponUpLinkIndex, zxGponUpLinkBridgePortMacFilterAddress }
        ::= { zxGponUpLinkBridgePortMacFilterTable 1 }

    ZxGponUpLinkBridgePortMacFilterEntry ::=
        SEQUENCE {
            zxGponUpLinkBridgePortMacFilterAddress                 MacAddress,
            zxGponUpLinkBridgePortMacFilterFilterMode              INTEGER,
            zxGponUpLinkBridgePortMacFilterEntryStatus             RowStatus
        }

    zxGponUpLinkBridgePortMacFilterAddress OBJECT-TYPE
        SYNTAX      MacAddress
        MAX-ACCESS  read-only
        STATUS      current
        DESCRIPTION
        "This attribute specifies the MAC address being filtered."
        REFERENCE   "G.983.2 section 7.3.33 MAC Bridge port filter table data"
        ::= { zxGponUpLinkBridgePortMacFilterEntry 1 }
        
    zxGponUpLinkBridgePortMacFilterFilterMode OBJECT-TYPE
        SYNTAX      INTEGER{
                    forward(1),
                    discard(2)
                    }
        MAX-ACCESS  read-write
        STATUS      current
        DESCRIPTION
        "This attribute specifies the filter action."
        REFERENCE   "G.983.2 section 7.3.33 MAC Bridge port filter table data"
        ::= { zxGponUpLinkBridgePortMacFilterEntry 2 }
        
    zxGponUpLinkBridgePortMacFilterEntryStatus OBJECT-TYPE
        SYNTAX      RowStatus
        MAX-ACCESS  read-write
        STATUS      current
        DESCRIPTION
        "This attribute specifies the operation of this entry."
        REFERENCE   "G.983.2 section 7.3.33 MAC Bridge port filter table data"
        ::= { zxGponUpLinkBridgePortMacFilterEntry 3 }

--Extended 802.1p mapper service profile
    zxGponUNIExDot1pMapServiceProfileTable    OBJECT-TYPE
        SYNTAX      SEQUENCE OF ZxGponUNIExDot1pMapServiceProfileEntry
        MAX-ACCESS  not-accessible
        STATUS      current
        DESCRIPTION
            "This managed entity is used to associate the priorities of 802.1P priority tagged 
            frames of a certain Ethernet UNI with a specific connection.
            One instance of this ME may be associated with zero or one instance of the PPTP UNI ME."
        REFERENCE   ""
        ::= { zxGponL2Mgmt 16 }

    zxGponUNIExDot1pMapServiceProfileEntry OBJECT-TYPE
        SYNTAX      ZxGponUNIExDot1pMapServiceProfileEntry
        MAX-ACCESS  not-accessible
        STATUS      current
        DESCRIPTION
            "It is entry in the zxGponUNIExDot1pMapServiceProfileTable."
        INDEX   { zxGponOltIndex, zxGponONTIndex, zxGponUNIIndex }
        ::= { zxGponUNIExDot1pMapServiceProfileTable 1 }

    ZxGponUNIExDot1pMapServiceProfileEntry ::=
        SEQUENCE {
            zxGponUNIExDot1pMapServiceProfilePrio0QueueId          INTEGER,
            zxGponUNIExDot1pMapServiceProfilePrio1QueueId          INTEGER,
            zxGponUNIExDot1pMapServiceProfilePrio2QueueId          INTEGER,
            zxGponUNIExDot1pMapServiceProfilePrio3QueueId          INTEGER,
            zxGponUNIExDot1pMapServiceProfilePrio4QueueId          INTEGER,
            zxGponUNIExDot1pMapServiceProfilePrio5QueueId          INTEGER,
            zxGponUNIExDot1pMapServiceProfilePrio6QueueId          INTEGER,
            zxGponUNIExDot1pMapServiceProfilePrio7QueueId          INTEGER
        }

    zxGponUNIExDot1pMapServiceProfilePrio0QueueId OBJECT-TYPE
        SYNTAX      INTEGER
        MAX-ACCESS  read-write
        STATUS      current
        DESCRIPTION
        "This attribute represents the upstream queue id that is 
        associated with P-Bit = 000 tagged frames. The value 0x0000 is a null pointer.(2 bytes)"
        REFERENCE   ""
        ::= { zxGponUNIExDot1pMapServiceProfileEntry 1 }

    zxGponUNIExDot1pMapServiceProfilePrio1QueueId OBJECT-TYPE
        SYNTAX      INTEGER
        MAX-ACCESS  read-write
        STATUS      current
        DESCRIPTION
        "This attribute represents the upstream queue id that is 
        associated with P-Bit = 001 tagged frames. The value 0x0000 is a null pointer.(2 bytes)"
        REFERENCE   ""
        ::= { zxGponUNIExDot1pMapServiceProfileEntry 2 }
        
    zxGponUNIExDot1pMapServiceProfilePrio2QueueId OBJECT-TYPE
        SYNTAX      INTEGER
        MAX-ACCESS  read-write
        STATUS      current
        DESCRIPTION
        "This attribute represents the upstream queue id that is 
        associated with P-Bit = 010 tagged frames. The value 0x0000 is a null pointer.(2 bytes)"
        REFERENCE   ""
        ::= { zxGponUNIExDot1pMapServiceProfileEntry 3 }
        
    zxGponUNIExDot1pMapServiceProfilePrio3QueueId OBJECT-TYPE
        SYNTAX      INTEGER
        MAX-ACCESS  read-write
        STATUS      current
        DESCRIPTION
        "This attribute represents the upstream queue id that is 
        associated with P-Bit = 011 tagged frames. The value 0x0000 is a null pointer.(2 bytes)"
        REFERENCE   ""
        ::= { zxGponUNIExDot1pMapServiceProfileEntry 4 }
        
    zxGponUNIExDot1pMapServiceProfilePrio4QueueId OBJECT-TYPE
        SYNTAX      INTEGER
        MAX-ACCESS  read-write
        STATUS      current
        DESCRIPTION
        "This attribute represents the upstream queue id that is 
        associated with P-Bit = 100 tagged frames. The value 0x0000 is a null pointer.(2 bytes)"
        REFERENCE   ""
        ::= { zxGponUNIExDot1pMapServiceProfileEntry 5 }
        
    zxGponUNIExDot1pMapServiceProfilePrio5QueueId OBJECT-TYPE
        SYNTAX      INTEGER
        MAX-ACCESS  read-write
        STATUS      current
        DESCRIPTION
        "This attribute represents the upstream queue id that is 
        associated with P-Bit = 101 tagged frames. The value 0x0000 is a null pointer.(2 bytes)"
        REFERENCE   ""
        ::= { zxGponUNIExDot1pMapServiceProfileEntry 6 }
        
    zxGponUNIExDot1pMapServiceProfilePrio6QueueId OBJECT-TYPE
        SYNTAX      INTEGER
        MAX-ACCESS  read-write
        STATUS      current
        DESCRIPTION
        "This attribute represents the upstream queue id that is 
        associated with P-Bit = 110 tagged frames. The value 0x0000 is a null pointer.(2 bytes)"
        REFERENCE   ""
        ::= { zxGponUNIExDot1pMapServiceProfileEntry 7 }

    zxGponUNIExDot1pMapServiceProfilePrio7QueueId OBJECT-TYPE
        SYNTAX      INTEGER
        MAX-ACCESS  read-write
        STATUS      current
        DESCRIPTION
        "This attribute represents the upstream queue id that is 
        associated with P-Bit = 111 tagged frames. The value 0x0000 is a null pointer.(2 bytes)"
        REFERENCE   ""
        ::= { zxGponUNIExDot1pMapServiceProfileEntry 8 }

--Extended 802.1p mapper service profile associated with uplink
    zxGponUpLinkExDot1pMapServiceProfileTable    OBJECT-TYPE
        SYNTAX      SEQUENCE OF ZxGponUpLinkExDot1pMapServiceProfileEntry
        MAX-ACCESS  not-accessible
        STATUS      current
        DESCRIPTION
            "This managed entity is used to associate the priorities of 802.1P priority tagged 
            frames of a certain UpLink with a specific connection.
            One instance of this ME may be associated with zero or one instance of the MAC 
            bridge port configuration data ME."
        REFERENCE   ""
        ::= { zxGponL2Mgmt 17 }
        
    zxGponUpLinkExDot1pMapServiceProfileEntry OBJECT-TYPE
        SYNTAX      ZxGponUpLinkExDot1pMapServiceProfileEntry
        MAX-ACCESS  not-accessible
        STATUS      current
        DESCRIPTION
            "It is entry in the zxGponUpLinkExDot1pMapServiceProfileTable."
        INDEX   { zxGponOltIndex, zxGponONTIndex, zxGponUpLinkIndex }
        ::= { zxGponUpLinkExDot1pMapServiceProfileTable 1 }
        
    ZxGponUpLinkExDot1pMapServiceProfileEntry ::=
        SEQUENCE {
            zxGponUpLinkExDot1pMapServiceProfilePrio0QueueId          INTEGER,
            zxGponUpLinkExDot1pMapServiceProfilePrio1QueueId          INTEGER,
            zxGponUpLinkExDot1pMapServiceProfilePrio2QueueId          INTEGER,
            zxGponUpLinkExDot1pMapServiceProfilePrio3QueueId          INTEGER,
            zxGponUpLinkExDot1pMapServiceProfilePrio4QueueId          INTEGER,
            zxGponUpLinkExDot1pMapServiceProfilePrio5QueueId          INTEGER,
            zxGponUpLinkExDot1pMapServiceProfilePrio6QueueId          INTEGER,
            zxGponUpLinkExDot1pMapServiceProfilePrio7QueueId          INTEGER
        }

    zxGponUpLinkExDot1pMapServiceProfilePrio0QueueId OBJECT-TYPE
        SYNTAX      INTEGER
        MAX-ACCESS  read-write
        STATUS      current
        DESCRIPTION
        "This attribute represents the upstream queue id that is 
        associated with P-Bit = 000 tagged frames. The value 0x0000 is a null pointer.(2 bytes)"
        REFERENCE   ""
        ::= { zxGponUpLinkExDot1pMapServiceProfileEntry 1 }

    zxGponUpLinkExDot1pMapServiceProfilePrio1QueueId OBJECT-TYPE
        SYNTAX      INTEGER
        MAX-ACCESS  read-write
        STATUS      current
        DESCRIPTION
        "This attribute represents the upstream queue id that is 
        associated with P-Bit = 001 tagged frames. The value 0x0000 is a null pointer.(2 bytes)"
        REFERENCE   ""
        ::= { zxGponUpLinkExDot1pMapServiceProfileEntry 2 }
        
    zxGponUpLinkExDot1pMapServiceProfilePrio2QueueId OBJECT-TYPE
        SYNTAX      INTEGER
        MAX-ACCESS  read-write
        STATUS      current
        DESCRIPTION
        "This attribute represents the upstream queue id that is 
        associated with P-Bit = 010 tagged frames. The value 0x0000 is a null pointer.(2 bytes)"
        REFERENCE   ""
        ::= { zxGponUpLinkExDot1pMapServiceProfileEntry 3 }
        
    zxGponUpLinkExDot1pMapServiceProfilePrio3QueueId OBJECT-TYPE
        SYNTAX      INTEGER
        MAX-ACCESS  read-write
        STATUS      current
        DESCRIPTION
        "This attribute represents the upstream queue id that is 
        associated with P-Bit = 011 tagged frames. The value 0x0000 is a null pointer.(2 bytes)"
        REFERENCE   ""
        ::= { zxGponUpLinkExDot1pMapServiceProfileEntry 4 }
        
    zxGponUpLinkExDot1pMapServiceProfilePrio4QueueId OBJECT-TYPE
        SYNTAX      INTEGER
        MAX-ACCESS  read-write
        STATUS      current
        DESCRIPTION
        "This attribute represents the upstream queue id that is 
        associated with P-Bit = 100 tagged frames. The value 0x0000 is a null pointer.(2 bytes)"
        REFERENCE   ""
        ::= { zxGponUpLinkExDot1pMapServiceProfileEntry 5 }
        
    zxGponUpLinkExDot1pMapServiceProfilePrio5QueueId OBJECT-TYPE
        SYNTAX      INTEGER
        MAX-ACCESS  read-write
        STATUS      current
        DESCRIPTION
        "This attribute represents the upstream queue id that is 
        associated with P-Bit = 101 tagged frames. The value 0x0000 is a null pointer.(2 bytes)"
        REFERENCE   ""
        ::= { zxGponUpLinkExDot1pMapServiceProfileEntry 6 }
        
    zxGponUpLinkExDot1pMapServiceProfilePrio6QueueId OBJECT-TYPE
        SYNTAX      INTEGER
        MAX-ACCESS  read-write
        STATUS      current
        DESCRIPTION
        "This attribute represents the upstream queue id that is 
        associated with P-Bit = 110 tagged frames. The value 0x0000 is a null pointer.(2 bytes)"
        REFERENCE   ""
        ::= { zxGponUpLinkExDot1pMapServiceProfileEntry 7 }

    zxGponUpLinkExDot1pMapServiceProfilePrio7QueueId OBJECT-TYPE
        SYNTAX      INTEGER
        MAX-ACCESS  read-write
        STATUS      current
        DESCRIPTION
        "This attribute represents the upstream queue id that is 
        associated with P-Bit = 111 tagged frames. The value 0x0000 is a null pointer.(2 bytes)"
        REFERENCE   ""
        ::= { zxGponUpLinkExDot1pMapServiceProfileEntry 8 }

--G.983.2 7.3.51 MAC Bridge port filter preassign table
--for UNI
    zxGponUNIMACBridgePortEthFrameFilterTable    OBJECT-TYPE
        SYNTAX      SEQUENCE OF ZxGponUNIMACBridgePortEthFrameFilterEntry
        MAX-ACCESS  not-accessible
        STATUS      current
        DESCRIPTION
            "This managed entity provides an alternate approach to address filtering than that 
            supported through MACBridgePortFilterTableData.
            This managed entity is associated with one instance of a MACBridgePortConfigurationData managed entity."
        REFERENCE   "G.983.2 section 7.3.51 MAC Bridge port filter preassign table"
        ::= { zxGponL2Mgmt 18 }

    zxGponUNIMACBridgePortEthFrameFilterEntry OBJECT-TYPE
        SYNTAX      ZxGponUNIMACBridgePortEthFrameFilterEntry
        MAX-ACCESS  not-accessible
        STATUS      current
        DESCRIPTION
            "It is entry in the zxGponUNIMACBridgePortEthFrameFilterTable."
        INDEX   { zxGponOltIndex, zxGponONTIndex, zxGponUNIIndex }
        ::= { zxGponUNIMACBridgePortEthFrameFilterTable 1 }
        
    ZxGponUNIMACBridgePortEthFrameFilterEntry ::=
        SEQUENCE {
            zxGponUNIMACBridgePortEthFrameFilterIPv4MCFilter            INTEGER,
            zxGponUNIMACBridgePortEthFrameFilterIPv6MCFilter            INTEGER,
            zxGponUNIMACBridgePortEthFrameFilterIPv4BCFilter            INTEGER,
            zxGponUNIMACBridgePortEthFrameFilterRARPFilter              INTEGER,
            zxGponUNIMACBridgePortEthFrameFilterIPXFilter               INTEGER,
            zxGponUNIMACBridgePortEthFrameFilterNetBEUIFilter           INTEGER,
            zxGponUNIMACBridgePortEthFrameFilterAppleTalkFilter         INTEGER,
            zxGponUNIMACBridgePortEthFrameFilterBPDUFilter              INTEGER,
            zxGponUNIMACBridgePortEthFrameFilterARPFilter               INTEGER,
            zxGponUNIMACBridgePortEthFrameFilterPPPoEFilter             INTEGER
        }

    zxGponUNIMACBridgePortEthFrameFilterIPv4MCFilter OBJECT-TYPE
        SYNTAX      INTEGER{
                    forward(1),
                    discard(2)
                    }
        MAX-ACCESS  read-write
        STATUS      current
        DESCRIPTION
        "This attribute indicates whether IPv4Multicast Ether types are forwarded (value 0x00) 
        or filtered (value 0x01). Initial value is 0x00.(1 byte)"
        REFERENCE   "G.983.2 section 7.3.51 MAC Bridge port filter preassign table"
        ::= { zxGponUNIMACBridgePortEthFrameFilterEntry 1 }
        
    zxGponUNIMACBridgePortEthFrameFilterIPv6MCFilter OBJECT-TYPE
        SYNTAX      INTEGER{
                    forward(1),
                    discard(2)
                    }
        MAX-ACCESS  read-write
        STATUS      current
        DESCRIPTION
        "This attribute indicates whether Ipv6Multicast Ether types are forwarded (value 0x00) 
        or filtered (value 0x01). Initial value is 0x00.(1 byte)"
        REFERENCE   "G.983.2 section 7.3.51 MAC Bridge port filter preassign table"
        ::= { zxGponUNIMACBridgePortEthFrameFilterEntry 2 }
        
    zxGponUNIMACBridgePortEthFrameFilterIPv4BCFilter OBJECT-TYPE
        SYNTAX      INTEGER{
                    forward(1),
                    discard(2)
                    }
        MAX-ACCESS  read-write
        STATUS      current
        DESCRIPTION
        "This attribute indicates whether IPv4Broadcast Ether types are forwarded (value 0x00) 
        or filtered (value 0x01). Initial value is 0x00.(1 byte)"
        REFERENCE   "G.983.2 section 7.3.51 MAC Bridge port filter preassign table"
        ::= { zxGponUNIMACBridgePortEthFrameFilterEntry 3 }

    zxGponUNIMACBridgePortEthFrameFilterRARPFilter OBJECT-TYPE
        SYNTAX      INTEGER{
                    forward(1),
                    discard(2)
                    }
        MAX-ACCESS  read-write
        STATUS      current
        DESCRIPTION
        "This attribute indicates whether RARP Ether types are forwarded (value 0x00) 
        or filtered (value 0x01). Initial value is 0x00.(1 byte)"
        REFERENCE   "G.983.2 section 7.3.51 MAC Bridge port filter preassign table"
        ::= { zxGponUNIMACBridgePortEthFrameFilterEntry 4 }

    zxGponUNIMACBridgePortEthFrameFilterIPXFilter OBJECT-TYPE
        SYNTAX      INTEGER{
                    forward(1),
                    discard(2)
                    }
        MAX-ACCESS  read-write
        STATUS      current
        DESCRIPTION
        "This attribute indicates whether IPX Ether types are forwarded (value 0x00) 
        or filtered (value 0x01). Initial value is 0x00.(1 byte)"
        REFERENCE   "G.983.2 section 7.3.51 MAC Bridge port filter preassign table"
        ::= { zxGponUNIMACBridgePortEthFrameFilterEntry 5 }

    zxGponUNIMACBridgePortEthFrameFilterNetBEUIFilter OBJECT-TYPE
        SYNTAX      INTEGER{
                    forward(1),
                    discard(2)
                    }
        MAX-ACCESS  read-write
        STATUS      current
        DESCRIPTION
        "This attribute indicates whether NetBEUI Ether types are forwarded (value 0x00) 
        or filtered (value 0x01). Initial value is 0x00.(1 byte)"
        REFERENCE   "G.983.2 section 7.3.51 MAC Bridge port filter preassign table"
        ::= { zxGponUNIMACBridgePortEthFrameFilterEntry 6 }

    zxGponUNIMACBridgePortEthFrameFilterAppleTalkFilter OBJECT-TYPE
        SYNTAX      INTEGER{
                    forward(1),
                    discard(2)
                    }
        MAX-ACCESS  read-write
        STATUS      current
        DESCRIPTION
        "This attribute indicates whether AppleTalk Ether types are forwarded (value 0x00) 
        or filtered (value 0x01). Initial value is 0x00.(1 byte)"
        REFERENCE   "G.983.2 section 7.3.51 MAC Bridge port filter preassign table"
        ::= { zxGponUNIMACBridgePortEthFrameFilterEntry 7 }

    zxGponUNIMACBridgePortEthFrameFilterBPDUFilter OBJECT-TYPE
        SYNTAX      INTEGER{
                    forward(1),
                    discard(2)
                    }
        MAX-ACCESS  read-write
        STATUS      current
        DESCRIPTION
        "This attribute indicates whether BridgeManagementInformation Ether types are 
        forwarded (value 0x00) or filtered (value 0x01). Initial value is 0x00.(1 byte)"
        REFERENCE   "G.983.2 section 7.3.51 MAC Bridge port filter preassign table"
        ::= { zxGponUNIMACBridgePortEthFrameFilterEntry 8 }

    zxGponUNIMACBridgePortEthFrameFilterARPFilter OBJECT-TYPE
        SYNTAX      INTEGER{
                    forward(1),
                    discard(2)
                    }
        MAX-ACCESS  read-write
        STATUS      current
        DESCRIPTION
        "This attribute indicates whether ARP Ether types are forwarded (value 0x00) 
        or filtered (value 0x01). Initial value is 0x00.(1 byte)"
        REFERENCE   "G.983.2 section 7.3.51 MAC Bridge port filter preassign table"
        ::= { zxGponUNIMACBridgePortEthFrameFilterEntry 9 }
        
    zxGponUNIMACBridgePortEthFrameFilterPPPoEFilter OBJECT-TYPE
        SYNTAX      INTEGER{
                    forward(1),
                    discard(2)
                    }
        MAX-ACCESS  read-write
        STATUS      current
        DESCRIPTION
        "This attribute indicates whether PPPoE Ether types are forwarded (value 0x00) 
        or filtered (value 0x01). Initial value is 0x00.(1 byte)"
        REFERENCE   "G.983.2 section 7.3.51 MAC Bridge port filter preassign table"
        ::= { zxGponUNIMACBridgePortEthFrameFilterEntry 10 }

--for uplink
    zxGponUpLinkMACBridgePortEthFrameFilterTable    OBJECT-TYPE
        SYNTAX      SEQUENCE OF ZxGponUpLinkMACBridgePortEthFrameFilterEntry
        MAX-ACCESS  not-accessible
        STATUS      current
        DESCRIPTION
            "This managed entity provides an alternate approach to address filtering than that 
            supported through MACBridgePortFilterTableData.
            This managed entity is associated with one instance of a MACBridgePortConfigurationData managed entity."
        REFERENCE   "G.983.2 section 7.3.51 MAC Bridge port filter preassign table"
        ::= { zxGponL2Mgmt 19 }

    zxGponUpLinkMACBridgePortEthFrameFilterEntry OBJECT-TYPE
        SYNTAX      ZxGponUpLinkMACBridgePortEthFrameFilterEntry
        MAX-ACCESS  not-accessible
        STATUS      current
        DESCRIPTION
            "It is entry in the zxGponUpLinkMACBridgePortEthFrameFilterTable."
        INDEX   { zxGponOltIndex, zxGponONTIndex, zxGponUpLinkIndex }
        ::= { zxGponUpLinkMACBridgePortEthFrameFilterTable 1 }
        
    ZxGponUpLinkMACBridgePortEthFrameFilterEntry ::=
        SEQUENCE {
            zxGponUpLinkMACBridgePortEthFrameFilterIPv4MCFilter            INTEGER,
            zxGponUpLinkMACBridgePortEthFrameFilterIPv6MCFilter            INTEGER,
            zxGponUpLinkMACBridgePortEthFrameFilterIPv4BCFilter            INTEGER,
            zxGponUpLinkMACBridgePortEthFrameFilterRARPFilter              INTEGER,
            zxGponUpLinkMACBridgePortEthFrameFilterIPXFilter               INTEGER,
            zxGponUpLinkMACBridgePortEthFrameFilterNetBEUIFilter           INTEGER,
            zxGponUpLinkMACBridgePortEthFrameFilterAppleTalkFilter         INTEGER,
            zxGponUpLinkMACBridgePortEthFrameFilterBPDUFilter              INTEGER,
            zxGponUpLinkMACBridgePortEthFrameFilterARPFilter               INTEGER,
            zxGponUpLinkMACBridgePortEthFrameFilterPPPoEFilter             INTEGER
        }

    zxGponUpLinkMACBridgePortEthFrameFilterIPv4MCFilter OBJECT-TYPE
        SYNTAX      INTEGER{
                    forward(1),
                    discard(2)
                    }
        MAX-ACCESS  read-write
        STATUS      current
        DESCRIPTION
        "This attribute indicates whether IPv4Multicast Ether types are forwarded (value 0x00) 
        or filtered (value 0x01). Initial value is 0x00.(1 byte)"
        REFERENCE   "G.983.2 section 7.3.51 MAC Bridge port filter preassign table"
        ::= { zxGponUpLinkMACBridgePortEthFrameFilterEntry 1 }
        
    zxGponUpLinkMACBridgePortEthFrameFilterIPv6MCFilter OBJECT-TYPE
        SYNTAX      INTEGER{
                    forward(1),
                    discard(2)
                    }
        MAX-ACCESS  read-write
        STATUS      current
        DESCRIPTION
        "This attribute indicates whether Ipv6Multicast Ether types are forwarded (value 0x00) 
        or filtered (value 0x01). Initial value is 0x00.(1 byte)"
        REFERENCE   "G.983.2 section 7.3.51 MAC Bridge port filter preassign table"
        ::= { zxGponUpLinkMACBridgePortEthFrameFilterEntry 2 }
        
    zxGponUpLinkMACBridgePortEthFrameFilterIPv4BCFilter OBJECT-TYPE
        SYNTAX      INTEGER{
                    forward(1),
                    discard(2)
                    }
        MAX-ACCESS  read-write
        STATUS      current
        DESCRIPTION
        "This attribute indicates whether IPv4Broadcast Ether types are forwarded (value 0x00) 
        or filtered (value 0x01). Initial value is 0x00.(1 byte)"
        REFERENCE   "G.983.2 section 7.3.51 MAC Bridge port filter preassign table"
        ::= { zxGponUpLinkMACBridgePortEthFrameFilterEntry 3 }

    zxGponUpLinkMACBridgePortEthFrameFilterRARPFilter OBJECT-TYPE
        SYNTAX      INTEGER{
                    forward(1),
                    discard(2)
                    }
        MAX-ACCESS  read-write
        STATUS      current
        DESCRIPTION
        "This attribute indicates whether RARP Ether types are forwarded (value 0x00) 
        or filtered (value 0x01). Initial value is 0x00.(1 byte)"
        REFERENCE   "G.983.2 section 7.3.51 MAC Bridge port filter preassign table"
        ::= { zxGponUpLinkMACBridgePortEthFrameFilterEntry 4 }

    zxGponUpLinkMACBridgePortEthFrameFilterIPXFilter OBJECT-TYPE
        SYNTAX      INTEGER{
                    forward(1),
                    discard(2)
                    }
        MAX-ACCESS  read-write
        STATUS      current
        DESCRIPTION
        "This attribute indicates whether IPX Ether types are forwarded (value 0x00) 
        or filtered (value 0x01). Initial value is 0x00.(1 byte)"
        REFERENCE   "G.983.2 section 7.3.51 MAC Bridge port filter preassign table"
        ::= { zxGponUpLinkMACBridgePortEthFrameFilterEntry 5 }

    zxGponUpLinkMACBridgePortEthFrameFilterNetBEUIFilter OBJECT-TYPE
        SYNTAX      INTEGER{
                    forward(1),
                    discard(2)
                    }
        MAX-ACCESS  read-write
        STATUS      current
        DESCRIPTION
        "This attribute indicates whether NetBEUI Ether types are forwarded (value 0x00) 
        or filtered (value 0x01). Initial value is 0x00.(1 byte)"
        REFERENCE   "G.983.2 section 7.3.51 MAC Bridge port filter preassign table"
        ::= { zxGponUpLinkMACBridgePortEthFrameFilterEntry 6 }

    zxGponUpLinkMACBridgePortEthFrameFilterAppleTalkFilter OBJECT-TYPE
        SYNTAX      INTEGER{
                    forward(1),
                    discard(2)
                    }
        MAX-ACCESS  read-write
        STATUS      current
        DESCRIPTION
        "This attribute indicates whether AppleTalk Ether types are forwarded (value 0x00) 
        or filtered (value 0x01). Initial value is 0x00.(1 byte)"
        REFERENCE   "G.983.2 section 7.3.51 MAC Bridge port filter preassign table"
        ::= { zxGponUpLinkMACBridgePortEthFrameFilterEntry 7 }

    zxGponUpLinkMACBridgePortEthFrameFilterBPDUFilter OBJECT-TYPE
        SYNTAX      INTEGER{
                    forward(1),
                    discard(2)
                    }
        MAX-ACCESS  read-write
        STATUS      current
        DESCRIPTION
        "This attribute indicates whether BridgeManagementInformation Ether types are 
        forwarded (value 0x00) or filtered (value 0x01). Initial value is 0x00.(1 byte)"
        REFERENCE   "G.983.2 section 7.3.51 MAC Bridge port filter preassign table"
        ::= { zxGponUpLinkMACBridgePortEthFrameFilterEntry 8 }

    zxGponUpLinkMACBridgePortEthFrameFilterARPFilter OBJECT-TYPE
        SYNTAX      INTEGER{
                    forward(1),
                    discard(2)
                    }
        MAX-ACCESS  read-write
        STATUS      current
        DESCRIPTION
        "This attribute indicates whether ARP Ether types are forwarded (value 0x00) 
        or filtered (value 0x01). Initial value is 0x00.(1 byte)"
        REFERENCE   "G.983.2 section 7.3.51 MAC Bridge port filter preassign table"
        ::= { zxGponUpLinkMACBridgePortEthFrameFilterEntry 9 }
        
    zxGponUpLinkMACBridgePortEthFrameFilterPPPoEFilter OBJECT-TYPE
        SYNTAX      INTEGER{
                    forward(1),
                    discard(2)
                    }
        MAX-ACCESS  read-write
        STATUS      current
        DESCRIPTION
        "This attribute indicates whether PPPoE Ether types are forwarded (value 0x00) 
        or filtered (value 0x01). Initial value is 0x00.(1 byte)"
        REFERENCE   "G.983.2 section 7.3.51 MAC Bridge port filter preassign table"
        ::= { zxGponUpLinkMACBridgePortEthFrameFilterEntry 10 }


--G.983.2 7.3.49 VLAN tagging operation configuration data
    zxGponVLANTagOperConfigTable    OBJECT-TYPE
        SYNTAX      SEQUENCE OF ZxGponVLANTagOperConfigEntry
        MAX-ACCESS  not-accessible
        STATUS      current
        DESCRIPTION
            "This managed entity is used to organize data associated with VLAN tagging. 
            Instances of this managed entity are created/deleted at the request of the OLT.
            Zero or one instance of this managed entity may exist for each instance of 
            Physical Path Termination Point Ethernet UNI."
        REFERENCE   "G.983.2 section 7.3.49 VLAN tagging operation configuration data"
        ::= { zxGponL2Mgmt 20 }

    zxGponVLANTagOperConfigEntry OBJECT-TYPE
        SYNTAX      ZxGponVLANTagOperConfigEntry
        MAX-ACCESS  not-accessible
        STATUS      current
        DESCRIPTION
            "It is entry in the zxGponVLANTagOperConfigTable."
        INDEX   { zxGponOltIndex, zxGponONTIndex, zxGponUNIIndex }
        ::= { zxGponVLANTagOperConfigTable 1 }
        
    ZxGponVLANTagOperConfigEntry ::=
        SEQUENCE {
            zxGponVLANTagOperConfigUpTagOperMode           INTEGER,
            zxGponVLANTagOperConfigUpTagTCIVal             INTEGER,
            zxGponVLANTagOperConfigDownTagOperMode         INTEGER,
            zxGponVLANTagOperConfigEntryStatus             RowStatus
        }

    zxGponVLANTagOperConfigUpTagOperMode OBJECT-TYPE
        SYNTAX      INTEGER{
                    transparent(1),
                    overwrite(2),
                    add(3),
                    addPvid(4)
                    }
        MAX-ACCESS  read-write
        STATUS      current
        DESCRIPTION
        "This attribute selects how upstream VLAN tagging is sent.  
        Valid values are as follows:
        0x01 (upstream frame is sent 'as is,' regardless of whether or not the received frame is tagged)  
        0x02 (The upstream frame is sent as tagged whether or not the received frame is tagged.  TCI, consisting of VID, CFI and user priority, is attached or overwritten by using the Upstream VLAN Tag TCI Value.). 
        0x03 (The upstream frame is sent as tagged whether or not the received frame is tagged.  If the received frame is tagged, a second tag (Q-n-Q) is added to the frame. If the received frame is not tagged a tag is attached to the frame. TCI, consisting of VID, CFI and user priority, is attached or added by using the Upstream VLAN Tag TCI Value.).
        0x04 (The upstream untagged frame is attached with the defined VLAN tag TCI value. The upstream tagged frame is forwarded unchanged).
       (1 byte)"
        REFERENCE   "G.983.2 section 7.3.49 VLAN tagging operation configuration data"
        ::= { zxGponVLANTagOperConfigEntry 1 }
        
    zxGponVLANTagOperConfigUpTagTCIVal OBJECT-TYPE
        SYNTAX      INTEGER
        MAX-ACCESS  read-write
        STATUS      current
        DESCRIPTION
        "This attribute indicates the TCI value for upstream VLAN tagging. It is used when the Upstream VLAN Tagging Operation Mode is 0x02, 0x03, or 0x04. Any 2-byte value is acceptable.(2 bytes)"
        REFERENCE   "G.983.2 section 7.3.49 VLAN tagging operation configuration data"
        ::= { zxGponVLANTagOperConfigEntry 2 }
        
    zxGponVLANTagOperConfigDownTagOperMode OBJECT-TYPE
        SYNTAX      INTEGER{
                    transparent(1),
                    untag(2),
                    deletePvid(3)
                    }
        MAX-ACCESS  read-write
        STATUS      current
        DESCRIPTION
        "This attribute selects whether or not downstream VLAN tagging is sent. 
        Valid values are as follows:
        0x01 (downstream frame is sent 'as is', regardless of whether or not the received frame is tagged) 
        0x02 (The downstream frame is sent as untagged whether or not the received frame is tagged).
        0x03 (If the received frame is tagged with defined VLAN tag TCI value, the outer tag is stripped. 
              Otherwise, the tagged frame is forwarded unchanged)(1 byte)"
        REFERENCE   "G.983.2 section 7.3.49 VLAN tagging operation configuration data"
        ::= { zxGponVLANTagOperConfigEntry 3 }
        
    zxGponVLANTagOperConfigEntryStatus OBJECT-TYPE
        SYNTAX      RowStatus
        MAX-ACCESS  read-write
        STATUS      current
        DESCRIPTION
        ""
        REFERENCE   "G.983.2 section 7.3.49 VLAN tagging operation configuration data"
        ::= { zxGponVLANTagOperConfigEntry 4 }

--Filter...
--G.983.2 7.3.50 VLAN tagging filter data
--for UNI
    zxGponUNIVLANTagFilterModeTable    OBJECT-TYPE
        SYNTAX      SEQUENCE OF ZxGponUNIVLANTagFilterModeEntry
        MAX-ACCESS  not-accessible
        STATUS      current
        DESCRIPTION
            "This managed entity is used to organize data associated with VLAN tagging. 
            Instances of this managed entity are created/deleted at the request of the OLT.
            Zero or one instance of this managed entity may exist for each instance of MAC 
            Bridge Port Configuration Data which is associated with Interworking VCC Termination 
            Point (PON side) or Physical Path Termination Point Ethernet UNI."
        REFERENCE   "G.983.2 section 7.3.50 VLAN tagging filter data"
        ::= { zxGponL2Mgmt 21 }

    zxGponUNIVLANTagFilterModeEntry OBJECT-TYPE
        SYNTAX      ZxGponUNIVLANTagFilterModeEntry
        MAX-ACCESS  not-accessible
        STATUS      current
        DESCRIPTION
            "It is entry in the zxGponUNIVLANTagFilterModeTable."
        INDEX   { zxGponOltIndex, zxGponONTIndex, zxGponUNIIndex }
        ::= { zxGponUNIVLANTagFilterModeTable 1 }
        
    ZxGponUNIVLANTagFilterModeEntry ::=
        SEQUENCE {
            zxGponUNIVLANTagFilterModeForwardOper             INTEGER,
            zxGponUNIVLANTagFilterModeEntryStatus             RowStatus
        }

    zxGponUNIVLANTagFilterModeForwardOper OBJECT-TYPE
        SYNTAX      INTEGER{
                    mode0(1),
                    mode1(2),
                    mode2(3),
                    mode3(4),
                    mode4(5),
                    mode5(6),
                    mode6(7),
                    mode7(8),
                    mode8(9),
                    mode9(10),
                    mode10(11),
                    mode11(12),
                    mode12(13),
                    mode13(14),
                    mode14(15)
                    }
        MAX-ACCESS  read-write
        STATUS      current
        DESCRIPTION
        "When a frame is received, the frame is processed according to the following Forward 
        Operations. The operations are invoked based on the value of VID, user priority, or 
        the entire TCI or whether or not the TCI field exists. This attribute indicates the 
        received frame is treated as indicated below.(1 byte)
        !!!!!!mode5/6/9/10 is no used currently!!!!!!! 
        tag-filter-action      untag-filter-action      forward-mode
        'transparent'          'transparent'            'mode0'
        'discard'              'transparent'            'mode1'
        'transparent'          'discard'                'mode2'
        'vid-filter'           'transparent'            'mode3'
        'vid-filter'           'discard'                'mode4'
        'prio-filter'          'transparent'            'mode7'
        'prio-filter'          'discard'                'mode8'
        'prio-vid-filter'      'transparent'            'mode11'
        'prio-vid-filter'      'discard'                'mode12'
        "
        REFERENCE   "G.983.2 section 7.3.50 VLAN tagging filter data"
        ::= { zxGponUNIVLANTagFilterModeEntry 1 }
        
    zxGponUNIVLANTagFilterModeEntryStatus OBJECT-TYPE
        SYNTAX      RowStatus
        MAX-ACCESS  read-write
        STATUS      current
        DESCRIPTION
        "This attribute provides the number of entries in the VLAN Filter Table that are valid.(1 byte)"
        REFERENCE   "G.983.2 section 7.3.50 VLAN tagging filter data"
        ::= { zxGponUNIVLANTagFilterModeEntry 2 }

    zxGponUNIVLANTagFilterTable    OBJECT-TYPE
        SYNTAX      SEQUENCE OF ZxGponUNIVLANTagFilterEntry
        MAX-ACCESS  not-accessible
        STATUS      current
        DESCRIPTION
            "This managed entity is used to organize data associated with VLAN tagging. 
            Instances of this managed entity are created/deleted at the request of the OLT.
            Zero or one instance of this managed entity may exist for each instance of MAC 
            Bridge Port Configuration Data which is associated with Interworking VCC Termination 
            Point (PON side) or Physical Path Termination Point Ethernet UNI."
        REFERENCE   "G.983.2 section 7.3.50 VLAN tagging filter data"
        ::= { zxGponL2Mgmt 22 }

    zxGponUNIVLANTagFilterEntry OBJECT-TYPE
        SYNTAX      ZxGponUNIVLANTagFilterEntry
        MAX-ACCESS  not-accessible
        STATUS      current
        DESCRIPTION
            "It is entry in the zxGponUNIVLANTagFilterTable."
        INDEX   { zxGponOltIndex, zxGponONTIndex, zxGponUNIIndex, zxGponUNIVLANTagFilterTCI }
        ::= { zxGponUNIVLANTagFilterTable 1 }
        
    ZxGponUNIVLANTagFilterEntry ::=
        SEQUENCE {
            zxGponUNIVLANTagFilterTCI                     INTEGER,
            zxGponUNIVLANTagFilterEntryStatus             RowStatus
        }

    zxGponUNIVLANTagFilterTCI OBJECT-TYPE
        SYNTAX      INTEGER
        MAX-ACCESS  read-write
        STATUS      current
        DESCRIPTION
        "This attribute specifies the TCI value which is provisioned at a bridging port.(2 bytes)"
        REFERENCE   "G.983.2 section 7.3.50 VLAN tagging filter data"
        ::= { zxGponUNIVLANTagFilterEntry 1 }
        
    zxGponUNIVLANTagFilterEntryStatus OBJECT-TYPE
        SYNTAX      RowStatus
        MAX-ACCESS  read-write
        STATUS      current
        DESCRIPTION
        "This attribute provides the number of entries in the VLAN Filter Table that are valid.(1 byte)"
        REFERENCE   "G.983.2 section 7.3.50 VLAN tagging filter data"
        ::= { zxGponUNIVLANTagFilterEntry 2 }

--for uplink
    zxGponUpLinkVLANTagFilterModeTable    OBJECT-TYPE
        SYNTAX      SEQUENCE OF ZxGponUpLinkVLANTagFilterModeEntry
        MAX-ACCESS  not-accessible
        STATUS      current
        DESCRIPTION
            "This managed entity is used to organize data associated with VLAN tagging. 
            Instances of this managed entity are created/deleted at the request of the OLT.
            Zero or one instance of this managed entity may exist for each instance of MAC 
            Bridge Port Configuration Data which is associated with Interworking VCC Termination 
            Point (PON side) or Physical Path Termination Point Ethernet UNI."
        REFERENCE   "G.983.2 section 7.3.50 VLAN tagging filter data"
        ::= { zxGponL2Mgmt 23 }

    zxGponUpLinkVLANTagFilterModeEntry OBJECT-TYPE
        SYNTAX      ZxGponUpLinkVLANTagFilterModeEntry
        MAX-ACCESS  not-accessible
        STATUS      current
        DESCRIPTION
            "It is entry in the zxGponUpLinkVLANTagFilterModeTable."
        INDEX   { zxGponOltIndex, zxGponONTIndex, zxGponUpLinkIndex }
        ::= { zxGponUpLinkVLANTagFilterModeTable 1 }
        
    ZxGponUpLinkVLANTagFilterModeEntry ::=
        SEQUENCE {
            zxGponUpLinkVLANTagFilterModeForwardOper            INTEGER,
            zxGponUpLinkVLANTagFilterModeEntryStatus            RowStatus
        }

    zxGponUpLinkVLANTagFilterModeForwardOper OBJECT-TYPE
        SYNTAX      INTEGER{
                    mode0(1),
                    mode1(2),
                    mode2(3),
                    mode3(4),
                    mode4(5),
                    mode5(6),
                    mode6(7),
                    mode7(8),
                    mode8(9),
                    mode9(10),
                    mode10(11),
                    mode11(12),
                    mode12(13),
                    mode13(14),
                    mode14(15)
                    }
        MAX-ACCESS  read-write
        STATUS      current
        DESCRIPTION
        "When a frame is received, the frame is processed according to the following Forward 
        Operations. The operations are invoked based on the value of VID, user priority, or 
        the entire TCI or whether or not the TCI field exists. This attribute indicates the 
        received frame is treated as indicated below.(1 byte)
        !!!!!!mode5/6/9/10 is no used currently!!!!!!!
        tag-filter-action      untag-filter-action      forward-mode
        'transparent'          'transparent'            'mode0'
        'discard'              'transparent'            'mode1'
        'transparent'          'discard'                'mode2'
        'vid-filter'           'transparent'            'mode3'
        'vid-filter'           'discard'                'mode4'
        'prio-filter'          'transparent'            'mode7'
        'prio-filter'          'discard'                'mode8'
        'prio-vid-filter'      'transparent'            'mode11'
        'prio-vid-filter'      'discard'                'mode12'
        "
        REFERENCE   "G.983.2 section 7.3.50 VLAN tagging filter data"
        ::= { zxGponUpLinkVLANTagFilterModeEntry 1 }
        
    zxGponUpLinkVLANTagFilterModeEntryStatus OBJECT-TYPE
        SYNTAX      RowStatus
        MAX-ACCESS  read-write
        STATUS      current
        DESCRIPTION
        "This attribute provides the number of entries in the VLAN Filter Table that are valid.(1 byte)"
        REFERENCE   "G.983.2 section 7.3.50 VLAN tagging filter data"
        ::= { zxGponUpLinkVLANTagFilterModeEntry 2 }

    zxGponUpLinkVLANTagFilterTable    OBJECT-TYPE
        SYNTAX      SEQUENCE OF ZxGponUpLinkVLANTagFilterEntry
        MAX-ACCESS  not-accessible
        STATUS      current
        DESCRIPTION
            "This managed entity is used to organize data associated with VLAN tagging. 
            Instances of this managed entity are created/deleted at the request of the OLT.
            Zero or one instance of this managed entity may exist for each instance of MAC 
            Bridge Port Configuration Data which is associated with Interworking VCC Termination 
            Point (PON side) or Physical Path Termination Point Ethernet UNI."
        REFERENCE   "G.983.2 section 7.3.50 VLAN tagging filter data"
        ::= { zxGponL2Mgmt 24 }

    zxGponUpLinkVLANTagFilterEntry OBJECT-TYPE
        SYNTAX      ZxGponUpLinkVLANTagFilterEntry
        MAX-ACCESS  not-accessible
        STATUS      current
        DESCRIPTION
            "It is entry in the zxGponUpLinkVLANTagFilterTable."
        INDEX   { zxGponOltIndex, zxGponONTIndex, zxGponUpLinkIndex, zxGponUpLinkVLANTagFilterTCI }
        ::= { zxGponUpLinkVLANTagFilterTable 1 }
        
    ZxGponUpLinkVLANTagFilterEntry ::=
        SEQUENCE {
            zxGponUpLinkVLANTagFilterTCI                     INTEGER,
            zxGponUpLinkVLANTagFilterEntryStatus            RowStatus
        }

    zxGponUpLinkVLANTagFilterTCI OBJECT-TYPE
        SYNTAX      INTEGER
        MAX-ACCESS  read-write
        STATUS      current
        DESCRIPTION
        "This attribute specifies the TCI value which is provisioned at a bridging port.(2 bytes)"
        REFERENCE   "G.983.2 section 7.3.50 VLAN tagging filter data"
        ::= { zxGponUpLinkVLANTagFilterEntry 1 }
        
    zxGponUpLinkVLANTagFilterEntryStatus OBJECT-TYPE
        SYNTAX      RowStatus
        MAX-ACCESS  read-write
        STATUS      current
        DESCRIPTION
        "This attribute provides the number of entries in the VLAN Filter Table that are valid.(1 byte)"
        REFERENCE   "G.983.2 section 7.3.50 VLAN tagging filter data"
        ::= { zxGponUpLinkVLANTagFilterEntry 2 }


    zxGponUpLinkVLANRangeTable    OBJECT-TYPE
        SYNTAX      SEQUENCE OF ZxGponUpLinkVLANRangeEntry
        MAX-ACCESS  not-accessible
        STATUS      current
        DESCRIPTION
            "This managed entity is used to organize data associated with VLAN tagging. 
            Instances of this managed entity are created/deleted at the request of the OLT.
            Zero or one instance of this managed entity may exist for each instance of MAC 
            Bridge Port Configuration Data which is associated with Interworking VCC Termination 
            Point (PON side) or Physical Path Termination Point Ethernet UNI."
        REFERENCE   "G.983.2 section 7.3.50 VLAN tagging filter data"
        ::= { zxGponL2Mgmt 25 }

    zxGponUpLinkVLANRangeEntry OBJECT-TYPE
        SYNTAX      ZxGponUpLinkVLANRangeEntry
        MAX-ACCESS  not-accessible
        STATUS      current
        DESCRIPTION
            "It is entry in the zxGponUpLinkVLANRangeTable."
        INDEX   { zxGponOltIndex, zxGponONTIndex, zxGponUpLinkIndex }
        ::= { zxGponUpLinkVLANRangeTable 1 }
        
    ZxGponUpLinkVLANRangeEntry ::=
        SEQUENCE {
            zxGponUpLinkVLANRangeVlanIdStart1           INTEGER,
            zxGponUpLinkVLANRangeVlanIdStop1            INTEGER,
            zxGponUpLinkVLANRangeVlanIdStart2           INTEGER,
            zxGponUpLinkVLANRangeVlanIdStop2            INTEGER,
            zxGponUpLinkVLANRangeVlanIdStart3           INTEGER,
            zxGponUpLinkVLANRangeVlanIdStop3            INTEGER,
            zxGponUpLinkVLANRangeVlanIdStart4           INTEGER,
            zxGponUpLinkVLANRangeVlanIdStop4            INTEGER,
            zxGponUpLinkVLANRangeVlanIdStart5           INTEGER,
            zxGponUpLinkVLANRangeVlanIdStop5            INTEGER,
            zxGponUpLinkVLANRangeVlanIdStart6           INTEGER,
            zxGponUpLinkVLANRangeVlanIdStop6            INTEGER,
            zxGponUpLinkVLANRangeEntryNum               INTEGER,
            zxGponUpLinkVLANRangeEntryStatus            RowStatus
        }

    zxGponUpLinkVLANRangeVlanIdStart1 OBJECT-TYPE
        SYNTAX      INTEGER
        MAX-ACCESS  read-write
        STATUS      current
        DESCRIPTION
        ""
        REFERENCE   "G.983.2 section 7.3.50 VLAN tagging filter data"
        ::= { zxGponUpLinkVLANRangeEntry 1 }
        
    zxGponUpLinkVLANRangeVlanIdStop1 OBJECT-TYPE
        SYNTAX      INTEGER
        MAX-ACCESS  read-write
        STATUS      current
        DESCRIPTION
        ""
        REFERENCE   "G.983.2 section 7.3.50 VLAN tagging filter data"
        ::= { zxGponUpLinkVLANRangeEntry 2 }
        
    zxGponUpLinkVLANRangeVlanIdStart2 OBJECT-TYPE
        SYNTAX      INTEGER
        MAX-ACCESS  read-write
        STATUS      current
        DESCRIPTION
        ""
        REFERENCE   "G.983.2 section 7.3.50 VLAN tagging filter data"
        ::= { zxGponUpLinkVLANRangeEntry 3 }
        
    zxGponUpLinkVLANRangeVlanIdStop2 OBJECT-TYPE
        SYNTAX      INTEGER
        MAX-ACCESS  read-write
        STATUS      current
        DESCRIPTION
        ""
        REFERENCE   "G.983.2 section 7.3.50 VLAN tagging filter data"
        ::= { zxGponUpLinkVLANRangeEntry 4 }
        
    zxGponUpLinkVLANRangeVlanIdStart3 OBJECT-TYPE
        SYNTAX      INTEGER
        MAX-ACCESS  read-write
        STATUS      current
        DESCRIPTION
        ""
        REFERENCE   "G.983.2 section 7.3.50 VLAN tagging filter data"
        ::= { zxGponUpLinkVLANRangeEntry 5 }
        
    zxGponUpLinkVLANRangeVlanIdStop3 OBJECT-TYPE
        SYNTAX      INTEGER
        MAX-ACCESS  read-write
        STATUS      current
        DESCRIPTION
        ""
        REFERENCE   "G.983.2 section 7.3.50 VLAN tagging filter data"
        ::= { zxGponUpLinkVLANRangeEntry 6 }
        
    zxGponUpLinkVLANRangeVlanIdStart4 OBJECT-TYPE
        SYNTAX      INTEGER
        MAX-ACCESS  read-write
        STATUS      current
        DESCRIPTION
        ""
        REFERENCE   "G.983.2 section 7.3.50 VLAN tagging filter data"
        ::= { zxGponUpLinkVLANRangeEntry 7 }
        
    zxGponUpLinkVLANRangeVlanIdStop4 OBJECT-TYPE
        SYNTAX      INTEGER
        MAX-ACCESS  read-write
        STATUS      current
        DESCRIPTION
        ""
        REFERENCE   "G.983.2 section 7.3.50 VLAN tagging filter data"
        ::= { zxGponUpLinkVLANRangeEntry 8 }
        
    zxGponUpLinkVLANRangeVlanIdStart5 OBJECT-TYPE
        SYNTAX      INTEGER
        MAX-ACCESS  read-write
        STATUS      current
        DESCRIPTION
        ""
        REFERENCE   "G.983.2 section 7.3.50 VLAN tagging filter data"
        ::= { zxGponUpLinkVLANRangeEntry 9 }
        
    zxGponUpLinkVLANRangeVlanIdStop5 OBJECT-TYPE
        SYNTAX      INTEGER
        MAX-ACCESS  read-write
        STATUS      current
        DESCRIPTION
        ""
        REFERENCE   "G.983.2 section 7.3.50 VLAN tagging filter data"
        ::= { zxGponUpLinkVLANRangeEntry 10 }
        
    zxGponUpLinkVLANRangeVlanIdStart6 OBJECT-TYPE
        SYNTAX      INTEGER
        MAX-ACCESS  read-write
        STATUS      current
        DESCRIPTION
        ""
        REFERENCE   "G.983.2 section 7.3.50 VLAN tagging filter data"
        ::= { zxGponUpLinkVLANRangeEntry 11 }
        
    zxGponUpLinkVLANRangeVlanIdStop6 OBJECT-TYPE
        SYNTAX      INTEGER
        MAX-ACCESS  read-write
        STATUS      current
        DESCRIPTION
        ""
        REFERENCE   "G.983.2 section 7.3.50 VLAN tagging filter data"
        ::= { zxGponUpLinkVLANRangeEntry 12 }
        
    zxGponUpLinkVLANRangeEntryNum OBJECT-TYPE
        SYNTAX      INTEGER
        MAX-ACCESS  read-write
        STATUS      current
        DESCRIPTION
        ""
        REFERENCE   "G.983.2 section 7.3.50 VLAN tagging filter data"
        ::= { zxGponUpLinkVLANRangeEntry 13 }
    
    zxGponUpLinkVLANRangeEntryStatus OBJECT-TYPE
        SYNTAX      RowStatus
        MAX-ACCESS  read-write
        STATUS      current
        DESCRIPTION
        ""
        REFERENCE   "G.983.2 section 7.3.50 VLAN tagging filter data"
        ::= { zxGponUpLinkVLANRangeEntry 14 }

    zxGponMACBridgePortAddrTable    OBJECT-TYPE
        SYNTAX      SEQUENCE OF ZxGponMACBridgePortAddrEntry
        MAX-ACCESS  not-accessible
        STATUS      current
        DESCRIPTION
            ""
        REFERENCE   "G.984.4 MAC Bridge Port bridge table Data"
        ::= { zxGponL2Mgmt 26 }

    zxGponMACBridgePortAddrEntry OBJECT-TYPE
        SYNTAX      ZxGponMACBridgePortAddrEntry
        MAX-ACCESS  not-accessible
        STATUS      current
        DESCRIPTION
            "It is entry in the zxGponMACBridgePortAddrTable."
        INDEX   { zxGponOltIndex, zxGponONTIndex, zxGponBridgePortType, zxGponBridgePortIndex }
        ::= { zxGponMACBridgePortAddrTable 1 }
        
    ZxGponMACBridgePortAddrEntry ::=
        SEQUENCE {
            zxGponMACBridgePortAddrNum                INTEGER,
            zxGponMACBridgePortAddrList               OCTET STRING
        }

    zxGponMACBridgePortAddrNum OBJECT-TYPE
        SYNTAX      INTEGER
        MAX-ACCESS  read-only
        STATUS      current
        DESCRIPTION
        "Number of addresses learned by this bridge port"
        REFERENCE   "G.984.4 MAC Bridge Port bridge table Data"
        ::= { zxGponMACBridgePortAddrEntry 1 }

    zxGponMACBridgePortAddrList OBJECT-TYPE
        SYNTAX      OCTET STRING
        MAX-ACCESS  read-only
        STATUS      current
        DESCRIPTION
        "This attribute identifies the MAC addresses learned by this bridge port.
         The first N*6 bytes is valid, N is determined by zxGponUNIMACBridgePortAddrNum."
        REFERENCE   "G.984.4 MAC Bridge Port bridge table Data"
        ::= { zxGponMACBridgePortAddrEntry 2 }

    zxGponUniMulticastGroupTable    OBJECT-TYPE
        SYNTAX      SEQUENCE OF ZxGponUniMulticastGroupEntry
        MAX-ACCESS  not-accessible
        STATUS      current
        DESCRIPTION
            ""
        REFERENCE   "G.984.4 Multicast subscriber config info"
        ::= { zxGponL2Mgmt 27 }

    zxGponUniMulticastGroupEntry OBJECT-TYPE
        SYNTAX      ZxGponUniMulticastGroupEntry
        MAX-ACCESS  not-accessible
        STATUS      current
        DESCRIPTION
            "It is entry in the zxGponUniMulticastGroupTable."
        INDEX   { zxGponOltIndex, zxGponONTIndex, zxGponUNIIndex, zxGponUniMulticastGroupIndex }
        ::= { zxGponUniMulticastGroupTable 1 }
        
    ZxGponUniMulticastGroupEntry ::=
        SEQUENCE {
            zxGponUniMulticastGroupIndex                 INTEGER,
            zxGponUniMulticastGroupVlanId                INTEGER,
            zxGponUniMulticastGroupStart                 IpAddress, 
            zxGponUniMulticastGroupStop                  IpAddress,
            zxGponUniMulticastGroupEntryStatus           RowStatus
        }

    zxGponUniMulticastGroupIndex OBJECT-TYPE
        SYNTAX      INTEGER
        MAX-ACCESS  not-accessible
        STATUS      current
        DESCRIPTION
        ""
        REFERENCE   ""
        ::= { zxGponUniMulticastGroupEntry 1 }

    zxGponUniMulticastGroupVlanId OBJECT-TYPE
        SYNTAX      INTEGER
        MAX-ACCESS  read-write
        STATUS      current
        DESCRIPTION
        ""
        REFERENCE   ""
        ::= { zxGponUniMulticastGroupEntry 2 }

    zxGponUniMulticastGroupStart OBJECT-TYPE
        SYNTAX      IpAddress
        MAX-ACCESS  read-write
        STATUS      current
        DESCRIPTION
        ""
        REFERENCE   ""
        ::= { zxGponUniMulticastGroupEntry 3 }

    zxGponUniMulticastGroupStop OBJECT-TYPE
        SYNTAX      IpAddress
        MAX-ACCESS  read-write
        STATUS      current
        DESCRIPTION
        ""
        REFERENCE   ""
        ::= { zxGponUniMulticastGroupEntry 4 }

    zxGponUniMulticastGroupEntryStatus OBJECT-TYPE
        SYNTAX      RowStatus
        MAX-ACCESS  read-write
        STATUS      current
        DESCRIPTION
        ""
        REFERENCE   ""
        ::= { zxGponUniMulticastGroupEntry 15 }

    zxGponBridgePortAddrListTable    OBJECT-TYPE
        SYNTAX      SEQUENCE OF ZxGponBridgePortAddrListEntry
        MAX-ACCESS  not-accessible
        STATUS      current
        DESCRIPTION
            ""
        REFERENCE   "G.984.4 MAC Bridge Port bridge table Data"
        ::= { zxGponL2Mgmt 28 }

    zxGponBridgePortAddrListEntry OBJECT-TYPE
        SYNTAX      ZxGponBridgePortAddrListEntry
        MAX-ACCESS  not-accessible
        STATUS      current
        DESCRIPTION
            "It is entry in the zxGponBridgePortAddrListTable."
        INDEX   { zxGponOltIndex, zxGponONTIndex, zxGponBridgePortType, zxGponBridgePortIndex, zxGponBridgePortAddrListIndex }
        ::= { zxGponBridgePortAddrListTable 1 }
        
    ZxGponBridgePortAddrListEntry ::=
        SEQUENCE {
            zxGponBridgePortAddrListIndex                 INTEGER,
            zxGponBridgePortAddrListTotalNum              INTEGER,
            zxGponBridgePortAddrListCurrentNum            INTEGER,
            zxGponBridgePortAddrListData                  OCTET STRING
        }

    zxGponBridgePortAddrListIndex OBJECT-TYPE
        SYNTAX      INTEGER
        MAX-ACCESS  not-accessible
        STATUS      current
        DESCRIPTION
        "Index for getnext."
        REFERENCE   "G.984.4 MAC Bridge Port bridge table Data"
        ::= { zxGponBridgePortAddrListEntry 1 }
        
    zxGponBridgePortAddrListTotalNum OBJECT-TYPE
        SYNTAX      INTEGER
        MAX-ACCESS  read-only
        STATUS      current
        DESCRIPTION
        "Total number of addresses entries related with this port."
        REFERENCE   "G.984.4 MAC Bridge Port bridge table Data"
        ::= { zxGponBridgePortAddrListEntry 2 }
        
    zxGponBridgePortAddrListCurrentNum OBJECT-TYPE
        SYNTAX      INTEGER
        MAX-ACCESS  read-only
        STATUS      current
        DESCRIPTION
        "The number of addresses entries by current getnext."
        REFERENCE   "G.984.4 MAC Bridge Port bridge table Data"
        ::= { zxGponBridgePortAddrListEntry 3 }

    zxGponBridgePortAddrListData OBJECT-TYPE
        SYNTAX      OCTET STRING(SIZE(32))
        MAX-ACCESS  read-only
        STATUS      current
        DESCRIPTION
        "This attribute identifies the MAC addresses learned by this bridge port.
         The first N*8 bytes is valid, N is determined by zxGponBridgePortAddrListCurrentNum.
         Each 8 bytes contain:
         - Information (2 bytes)
         - MAC address (6 bytes)
         The information bits are assigned as described below.
           Bit      Name              Setting
           1      Filter/forward    0: forward
                                1: filter
           2      Reserved            0
           3      Dynamic/static    0: this entry is statically assigned
                                1: this entry is dynamically learned
           4      Reserved            0
           16..5  Age                    Age in seconds (1..4095)
         "
        REFERENCE   "G.984.4 MAC Bridge Port bridge table Data"
        ::= { zxGponBridgePortAddrListEntry 4 }

    zxGponUNITPInfoTable    OBJECT-TYPE
        SYNTAX      SEQUENCE OF ZxGponUNITPInfoEntry
        MAX-ACCESS  not-accessible
        STATUS      current
        DESCRIPTION
            ""
        REFERENCE   ""
        ::= { zxGponL2Mgmt 30 }

    zxGponUNITPInfoEntry OBJECT-TYPE
        SYNTAX      ZxGponUNITPInfoEntry
        MAX-ACCESS  not-accessible
        STATUS      current
        DESCRIPTION
            "It is entry in the zxGponUNITPInfoTable."
        INDEX   { zxGponOltIndex, zxGponONTIndex, zxGponUNIIndex }
        ::= { zxGponUNITPInfoTable 1 }
        
    ZxGponUNITPInfoEntry ::=
        SEQUENCE {
            zxGponUNITPType                     INTEGER
        }

    zxGponUNITPType OBJECT-TYPE
        SYNTAX      INTEGER{
                    null(1),
                    iwtp(2),
                    mciwtp(3),
                    macbridge(4),
                    dot1p(5),
                    ces(6),
                    vbridge(7)
                    }
        MAX-ACCESS  read-only
        STATUS      current
        DESCRIPTION
        "This attribute indicates the TP type related with this UNI.
        null: no related services;
        iwtp: uni is directly connected with an iwtp;
        mciwtp: uni is directly connected with an multicast iwtp;
        macbridge: uni is connected with a bridge;
        dot1p: uni is connected with an iwtp by 802.1p mapping;
        ces: uni is connected with ces service;
        vbridge: uni is connected with a virtual bridge;  
        "
        REFERENCE   ""
        ::= { zxGponUNITPInfoEntry 1 }


--The capability of the ONT(MAX supported bridge/uplink)
    zxGponOntBridgeCapabilityTable    OBJECT-TYPE
        SYNTAX      SEQUENCE OF ZxGponOntBridgeCapabilityEntry
        MAX-ACCESS  not-accessible
        STATUS      current
        DESCRIPTION
            ""
        REFERENCE   ""
        ::= { zxGponL2Mgmt 31 }

    zxGponOntBridgeCapabilityEntry OBJECT-TYPE
        SYNTAX      ZxGponOntBridgeCapabilityEntry
        MAX-ACCESS  not-accessible
        STATUS      current
        DESCRIPTION
            "It is entry in the zxGponOntBridgeCapabilityTable."
        INDEX   { zxGponOltIndex, zxGponONTIndex }
        ::= { zxGponOntBridgeCapabilityTable 1 }
        
    ZxGponOntBridgeCapabilityEntry ::=
        SEQUENCE {
            zxGponOntBridgeCapabilityMaxBridgeNum                     INTEGER,
            zxGponOntBridgeCapabilityMaxUplinkNumPerBridge            INTEGER
        }

    zxGponOntBridgeCapabilityMaxBridgeNum OBJECT-TYPE
        SYNTAX      INTEGER
        MAX-ACCESS  read-only
        STATUS      current
        DESCRIPTION
        "This attribute indicates the maximum bridge group num supported on this ONT."
        REFERENCE   ""
        ::= { zxGponOntBridgeCapabilityEntry 1 }
        
    zxGponOntBridgeCapabilityMaxUplinkNumPerBridge OBJECT-TYPE
        SYNTAX      INTEGER
        MAX-ACCESS  read-only
        STATUS      current
        DESCRIPTION
        "This attribute indicates the maximum uplink num per bridge supported on this ONT."
        REFERENCE   ""
        ::= { zxGponOntBridgeCapabilityEntry 2 }

--VoIP related

--VoIP global configuration(VoIP Config Data section 7.3.101/G.983.2)
    zxGponVoIPConfigDataTable    OBJECT-TYPE
        SYNTAX      SEQUENCE OF ZxGponVoIPConfigDataEntry
        MAX-ACCESS  not-accessible
        STATUS      current
        DESCRIPTION
            "The VoIP Configuration Data defines the configuration for VoIP in the ONT. 
            The OLT uses this ME to discover the VoIP signaling protocols and configuration 
            methods supported by this ONT. The OLT then uses this ME to select the desired 
            signaling protocol and configuration method. The entity is conditionally required 
            for ONTs that offer VoIP services."
        REFERENCE   "G.983.2 section 7.3.101 VoIP Config Data"
        ::= { zxGponL2Mgmt 40 }

    zxGponVoIPConfigDataEntry OBJECT-TYPE
        SYNTAX      ZxGponVoIPConfigDataEntry
        MAX-ACCESS  not-accessible
        STATUS      current
        DESCRIPTION
            "It is entry in the zxGponVoIPConfigDataTable."
        INDEX   { zxGponOltIndex, zxGponONTIndex }
        ::= { zxGponVoIPConfigDataTable 1 }
        
    ZxGponVoIPConfigDataEntry ::=
        SEQUENCE {
            zxGponVoIPConfigDataAvailableSignalProtocol      INTEGER,
            zxGponVoIPConfigDataSignalProtocolUsed           INTEGER,
            zxGponVoIPConfigDataAvailableConfigMethod        INTEGER,
            zxGponVoIPConfigDataConfigMethodUsed             INTEGER,
            zxGponVoIPConfigDataConfigAddress                OCTET STRING
        }

    zxGponVoIPConfigDataAvailableSignalProtocol OBJECT-TYPE
        SYNTAX      INTEGER
        MAX-ACCESS  read-only
        STATUS      current
        DESCRIPTION
        "This attribute defines, using a bitmap, the VoIP Signaling Protocols supported in the 
        ONT. Valid bitmap values are: 
        0x00 = None, VoIP not supported
        0x01 = SIP
        0x02 = H.248
        0x04 = MGCP
        0xFF = NA
        (1 byte)"
        REFERENCE   "G.983.2 section 7.3.101 VoIP Config Data"
        ::= { zxGponVoIPConfigDataEntry 1 }
        
    zxGponVoIPConfigDataSignalProtocolUsed OBJECT-TYPE
        SYNTAX      INTEGER{
                    none(1),
                    sip(2),
                    h248(3),
                    mgcp(4)
                    }
        MAX-ACCESS  read-write
        STATUS      current
        DESCRIPTION
        "This attribute identifies the type of VoIP signaling protocol used for ONT.  
        Only one type of protocol is allowed. Valid values are: 
        0x00 = None
        0x01 = SIP
        0x02 = H.248
        0x03 = MGCP
        0xFF = Selected by Non-OMCI Management Interface
        (1 byte)"
        REFERENCE   "G.983.2 section 7.3.101 VoIP Config Data"
        ::= { zxGponVoIPConfigDataEntry 2 }
        
    zxGponVoIPConfigDataAvailableConfigMethod OBJECT-TYPE
        SYNTAX      INTEGER
        MAX-ACCESS  read-only
        STATUS      current
        DESCRIPTION
        "This attribute indicates, using a bitmap, the capabilities of the ONT with regard to VoIP service configuration:
        0x0001 indicates that the ONT is capable of using OMCI to configure its VoIP services.
        0x0002 indicates that the ONT is capable of working with configuration file retrieval to configure its VoIP services.
        0x0004 indicates that the ONT is capable of working with TR-69 to configure its VoIP services.
        0x0008 indicates that the ONT is capable of working with IETF sipping config framework to configure its VoIP services.
        Bits 5 - 24 are reserved for future use. 
        Bits 25 - 32 are reserved for proprietary vendor configuration capability indications.
        Default value is 0x0001.(4 bytes)
        "
        REFERENCE   "G.983.2 section 7.3.101 VoIP Config Data"
        ::= { zxGponVoIPConfigDataEntry 3 }
        
    zxGponVoIPConfigDataConfigMethodUsed OBJECT-TYPE
        SYNTAX      INTEGER
        MAX-ACCESS  read-write
        STATUS      current
        DESCRIPTION
        "Indicates to the ONT, which method should be used to configure the VoIP Service of the ONT.
         0x00 the ONT default - do not configure. 
         0x01 indicate use of OMCI for VoIP service configuration of the ONT. 
         0x02 indicate use of configuration file retrieval for VoIP service configuration of the ONT. 
         0x03 indicate use of TR-69 for VoIP service configuration of the ONT. 
         0x04 indicate use of IETF sipping config framework for VoIP service configuration of the ONT. 
         0x05 - 0xF0 are reserved for future use. 
         0xF1 - 0xFF are reserved for proprietary vendor configuration methods.
         Default value is 0x00 (R, W) (mandatory) (1 bytes)
        "
        REFERENCE   "G.983.2 section 7.3.101 VoIP Config Data"
        ::= { zxGponVoIPConfigDataEntry 4 }
        
    zxGponVoIPConfigDataConfigAddress OBJECT-TYPE
        SYNTAX      OCTET STRING(SIZE(0..128))
        MAX-ACCESS  read-write
        STATUS      current
        DESCRIPTION
        "If this attribute is set to any value other than 0xFFFF, it points to a Network Address managed entity. 
        In this case, the Network Address ME indicates the address of the server to contact using the method 
        indicated in the VoIP Configuration Method Used attribute of the VoIP Service ME.
        If this attribute is set to 0xFFFF, an address is not defined by this attribute. 
        However, the address may be defined by other methods such as deriving the address from the ONT Identifier 
        attribute of the IP Host Config Data ME, and using a well-known URI schema. 
        Default value is 0xFFFF (R, W) (mandatory) (2 bytes)
        Attention!! We hide the Network Address ME, using OCTET STRING instead! 
        But now, it may be unused.
        "
        REFERENCE   "G.983.2 section 7.3.101 VoIP Config Data"
        ::= { zxGponVoIPConfigDataEntry 5 }

--IP Host Config Data(section 7.3.98/G.983.2)
    zxGponIPHostConfigDataTable    OBJECT-TYPE
        SYNTAX      SEQUENCE OF ZxGponIPHostConfigDataEntry
        MAX-ACCESS  not-accessible
        STATUS      current
        DESCRIPTION
            "The IP Host Config Data contains the configuration for IP based services that are offered 
            on the ONT.  This entity is conditionally required for ONTs that offer IP services from the 
            ONT itself, and its presence allows additional features to be supported with the ONT.
            Instances of this managed entity are automatically created by the ONT after initialization 
            if IP Host services are available.
            "
        REFERENCE   "G.983.2 section 7.3.98 IP Host Config Data"
        ::= { zxGponL2Mgmt 41 }

    zxGponIPHostConfigDataEntry OBJECT-TYPE
        SYNTAX      ZxGponIPHostConfigDataEntry
        MAX-ACCESS  not-accessible
        STATUS      current
        DESCRIPTION
            "It is entry in the zxGponIPHostConfigDataTable."
        INDEX   { zxGponOltIndex, zxGponONTIndex, zxGponIPHostConfigDataId }
        ::= { zxGponIPHostConfigDataTable 1 }
        
    ZxGponIPHostConfigDataEntry ::=
        SEQUENCE {
            zxGponIPHostConfigDataId                  INTEGER,
            zxGponIPHostConfigDataIPOptions           INTEGER,
            zxGponIPHostConfigDataMACAddress          MacAddress,
            zxGponIPHostConfigDataOntIdentifier       OCTET STRING,
            zxGponIPHostConfigDataIPAddress           IpAddress,
            zxGponIPHostConfigDataIPMask              IpAddress,
            zxGponIPHostConfigDataGateway             IpAddress,
            zxGponIPHostConfigDataPrimaryDNS          IpAddress,
            zxGponIPHostConfigDataSecondaryDNS        IpAddress,
            zxGponIPHostConfigDataCurrentAddress      IpAddress,
            zxGponIPHostConfigDataCurrentMask         IpAddress,
            zxGponIPHostConfigDataCurrentGateway      IpAddress,
            zxGponIPHostConfigDataCurrentPriDNS       IpAddress,
            zxGponIPHostConfigDataCurrentSecDNS       IpAddress,
            zxGponIPHostConfigDataDomainName          OCTET STRING,
            zxGponIPHostConfigDataHostName            OCTET STRING
        }

    zxGponIPHostConfigDataId OBJECT-TYPE
        SYNTAX      INTEGER
        MAX-ACCESS  read-only
        STATUS      current
        DESCRIPTION
        "This attribute provides a unique number for each instance of this managed entity.  
        The ONT creates as many instances as there are independent IP stacks on the ONT.
        (1~n)"
        REFERENCE   "G.983.2 section 7.3.98 IP Host Config Data"
        ::= { zxGponIPHostConfigDataEntry 1 }
        
    zxGponIPHostConfigDataIPOptions OBJECT-TYPE
        SYNTAX      INTEGER
        MAX-ACCESS  read-write
        STATUS      current
        DESCRIPTION
        "This attribute is a bitfield that is used to enable or disable IP related options. 
        A bit value of 1 enables the option and a bit value of 0 disables the option. 
        The options are assigned as follows:
        0x1 = Enable DHCP
        0x2 = Respond to PINGs
        0x4 = Respond to TraceRoute messages.
        0x8 - 0x80 = Reserved for future use.
        (R, W) (mandatory) (1 byte)"
        REFERENCE   "G.983.2 section 7.3.98 IP Host Config Data"
        ::= { zxGponIPHostConfigDataEntry 2 }
        
    zxGponIPHostConfigDataMACAddress OBJECT-TYPE
        SYNTAX      MacAddress
        MAX-ACCESS  read-only
        STATUS      current
        DESCRIPTION
        "This attribute indicates the MAC address used by the IP Node (R) (mandatory) (6 bytes)"
        REFERENCE   "G.983.2 section 7.3.98 IP Host Config Data"
        ::= { zxGponIPHostConfigDataEntry 3 }
        
    zxGponIPHostConfigDataOntIdentifier OBJECT-TYPE
        SYNTAX      OCTET STRING(SIZE(0..25))
        MAX-ACCESS  read-write
        STATUS      current
        DESCRIPTION
        "A unique ONT identifier string. This string, if set is provided as part of the DHCP request 
        to allow an alternative to MAC Address in retrieving the DHCP parameters of the specified ONT. 
        The string may be up to 25 bytes long. If the string length is smaller than 25 bytes, it must 
        be null terminated. Default value is 25 null bytes. (R, W) (mandatory) (25 bytes)
        "
        REFERENCE   "G.983.2 section 7.3.98 IP Host Config Data"
        ::= { zxGponIPHostConfigDataEntry 4 }
        
    zxGponIPHostConfigDataIPAddress OBJECT-TYPE
        SYNTAX      IpAddress
        MAX-ACCESS  read-write
        STATUS      current
        DESCRIPTION
        "Address used for all IP services hosted by the ONT, and has a default value of 0x0 [not set].  
        If this value is set, it will override any values returned in DHCP. (R, W) (mandatory) (4 bytes)"
        REFERENCE   "G.983.2 section 7.3.98 IP Host Config Data"
        ::= { zxGponIPHostConfigDataEntry 5 }
        
    zxGponIPHostConfigDataIPMask OBJECT-TYPE
        SYNTAX      IpAddress
        MAX-ACCESS  read-write
        STATUS      current
        DESCRIPTION
        "Subnet mask for the IP services hosted by the ONT, and has a default value of 0x0 [not set].  
        If this value is set, it will override any values returned in DHCP. (R, W) (mandatory) (4 bytes)"
        REFERENCE   "G.983.2 section 7.3.98 IP Host Config Data"
        ::= { zxGponIPHostConfigDataEntry 6 }
        
    zxGponIPHostConfigDataGateway OBJECT-TYPE
        SYNTAX      IpAddress
        MAX-ACCESS  read-write
        STATUS      current
        DESCRIPTION
        "Default Gateway Address used for all IP services hosted by the ONT, and has a default value of 0x0 [not set].  
        If this value is set, it will override any values returned in DHCP. (R, W) (mandatory) (4 bytes)"
        REFERENCE   "G.983.2 section 7.3.98 IP Host Config Data"
        ::= { zxGponIPHostConfigDataEntry 7 }

    zxGponIPHostConfigDataPrimaryDNS OBJECT-TYPE
        SYNTAX      IpAddress
        MAX-ACCESS  read-write
        STATUS      current
        DESCRIPTION
        "Address used for the Primary DNS server for the IP service, and has a default value of 0x0 [not set].  
        If this value is set, it will override any values returned in DHCP. (R, W) (mandatory) (4 bytes)"
        REFERENCE   "G.983.2 section 7.3.98 IP Host Config Data"
        ::= { zxGponIPHostConfigDataEntry 8 }

    zxGponIPHostConfigDataSecondaryDNS OBJECT-TYPE
        SYNTAX      IpAddress
        MAX-ACCESS  read-write
        STATUS      current
        DESCRIPTION
        "Address used for the Secondary DNS server for the IP service, and has a default value of 0x0 [not set].  
        If this value is set, it will override any values returned in DHCP. (R, W) (mandatory) (4 bytes)"
        REFERENCE   "G.983.2 section 7.3.98 IP Host Config Data"
        ::= { zxGponIPHostConfigDataEntry 9 }

    zxGponIPHostConfigDataCurrentAddress OBJECT-TYPE
        SYNTAX      IpAddress
        MAX-ACCESS  read-only
        STATUS      current
        DESCRIPTION
        "Current address for the IP service hosted by the ONT.  
        This attribute is updated by the ONT if a new address is assigned by DHCP. (R) (optional) (4 bytes)"
        REFERENCE   "G.983.2 section 7.3.98 IP Host Config Data"
        ::= { zxGponIPHostConfigDataEntry 10 }
        
    zxGponIPHostConfigDataCurrentMask OBJECT-TYPE
        SYNTAX      IpAddress
        MAX-ACCESS  read-only
        STATUS      current
        DESCRIPTION
        "Current subnet mask for the IP service.  
        This attribute is updated by the ONT if a new mask is assigned by DHCP. (R) (optional) (4 bytes)"
        REFERENCE   "G.983.2 section 7.3.98 IP Host Config Data"
        ::= { zxGponIPHostConfigDataEntry 11 }

    zxGponIPHostConfigDataCurrentGateway OBJECT-TYPE
        SYNTAX      IpAddress
        MAX-ACCESS  read-only
        STATUS      current
        DESCRIPTION
        "Current default Gateway Address for the IP service.  
        This attribute is updated by the ONT if a new gateway is assigned by DHCP. (R) (optional) (4 bytes)"
        REFERENCE   "G.983.2 section 7.3.98 IP Host Config Data"
        ::= { zxGponIPHostConfigDataEntry 12 }

    zxGponIPHostConfigDataCurrentPriDNS OBJECT-TYPE
        SYNTAX      IpAddress
        MAX-ACCESS  read-only
        STATUS      current
        DESCRIPTION
        "Current address used for the Primary DNS server for the IP service.  
        This attribute is updated by the ONT if a new address is assigned by DHCP. (R) (optional) (4 bytes)"
        REFERENCE   "G.983.2 section 7.3.98 IP Host Config Data"
        ::= { zxGponIPHostConfigDataEntry 13 }

    zxGponIPHostConfigDataCurrentSecDNS OBJECT-TYPE
        SYNTAX      IpAddress
        MAX-ACCESS  read-only
        STATUS      current
        DESCRIPTION
        "Current address used for the Secondary DNS server for the IP service.  
        This attribute is updated by the ONT if a new address is assigned by DHCP. (R) (optional) (4 bytes)"
        REFERENCE   "G.983.2 section 7.3.98 IP Host Config Data"
        ::= { zxGponIPHostConfigDataEntry 14 }

    zxGponIPHostConfigDataDomainName OBJECT-TYPE
        SYNTAX      OCTET STRING(SIZE(0..25))
        MAX-ACCESS  read-only
        STATUS      current
        DESCRIPTION
        "If domain name is indicated by DHCP, it is presented here. If domain name is not indicated, 
        this attribute is set to an empty string. 
        The string may be up to 25 bytes long. If the string length is smaller than 25 bytes, 
        it must be null terminated.  
        Default value is 25 null bytes. (R) (mandatory) (25 bytes)
        "
        REFERENCE   "G.983.2 section 7.3.98 IP Host Config Data"
        ::= { zxGponIPHostConfigDataEntry 15 }

    zxGponIPHostConfigDataHostName OBJECT-TYPE
        SYNTAX      OCTET STRING(SIZE(0..25))
        MAX-ACCESS  read-only
        STATUS      current
        DESCRIPTION
        "If host name is indicated by DHCP, it is presented here. If host name is not indicated, 
        this attribute is set to an empty string. 
        The string may be up to 25 bytes long. If the string length is smaller than 25 bytes, 
        it must be null terminated.  
        Default value is 25 null bytes. (R) (mandatory) (25 bytes)
        "
        REFERENCE   "G.983.2 section 7.3.98 IP Host Config Data"
        ::= { zxGponIPHostConfigDataEntry 16 }

    
--IP Host bind to MAC bridge
    zxGponHostMACBridgePortConfigTable    OBJECT-TYPE
        SYNTAX      SEQUENCE OF ZxGponHostMACBridgePortConfigEntry
        MAX-ACCESS  not-accessible
        STATUS      current
        DESCRIPTION
            "This managed entity is used to organize and record data that is associated with 
            a bridge port. Some of the data is volatile.
            Zero or more instances of this managed entity shall be contained in an instance of the 
            MACBridgeServiceProfile."
        REFERENCE   "G.984.4 section 9.3.9 MAC Bridge Port Configuation Data, details in G.983.2"
        ::= { zxGponL2Mgmt 42 }

    zxGponHostMACBridgePortConfigEntry OBJECT-TYPE
        SYNTAX      ZxGponHostMACBridgePortConfigEntry
        MAX-ACCESS  not-accessible
        STATUS      current
        DESCRIPTION
            "It is entry in the zxGponHostMACBridgePortConfigTable."
        INDEX   { zxGponOltIndex, zxGponONTIndex, zxGponIPHostConfigDataId }
        ::= { zxGponHostMACBridgePortConfigTable 1 }
      
    ZxGponHostMACBridgePortConfigEntry ::=
        SEQUENCE {
            zxGponHostMACBridgePortConfigBridgeId                INTEGER,
            zxGponHostMACBridgePortConfigBridgePort              INTEGER,
            zxGponHostMACBridgePortConfigPortPrio                INTEGER,
            zxGponHostMACBridgePortConfigPortPathCost            INTEGER,
            zxGponHostMACBridgePortConfigPortSpanTreeInd         TruthValue,
            zxGponHostMACBridgePortConfigEncapMethod             INTEGER,
            zxGponHostMACBridgePortConfigLANFCSInd               INTEGER,
            zxGponHostMACBridgePortConfigPortMACAddr             MacAddress,
            zxGponHostMACBridgePortConfigEntryStatus             RowStatus
        }

    zxGponHostMACBridgePortConfigBridgeId OBJECT-TYPE
        SYNTAX      INTEGER
        MAX-ACCESS  read-write
        STATUS      current
        DESCRIPTION
        "This attribute identifies the MAC bridge id associated with the ip host."
        REFERENCE   ""
        ::= { zxGponHostMACBridgePortConfigEntry 1 }

    zxGponHostMACBridgePortConfigBridgePort OBJECT-TYPE
        SYNTAX      INTEGER
        MAX-ACCESS  read-only
        STATUS      current
        DESCRIPTION
        "This attribute identifies the MAC bridge port associated with the port.
        The first 2 bytes stand for the slot and bridge group id;
        The second 2 bytes stand for the bridge port num.(4 bytes)"
        REFERENCE   "G.984.4 section 9.3.9 MAC Bridge Port Configuation Data"
        ::= { zxGponHostMACBridgePortConfigEntry 2 }

    zxGponHostMACBridgePortConfigPortPrio OBJECT-TYPE
        SYNTAX      INTEGER
        MAX-ACCESS  read-write
        STATUS      current
        DESCRIPTION
        "This attribute denotes the priority of the port. 
        The range is 0x00 to 0x00FF (0 to 255).(2 bytes)"
        REFERENCE   "G.984.4 section 9.3.9 MAC Bridge Port Configuation Data"
        ::= { zxGponHostMACBridgePortConfigEntry 3 }
        
    zxGponHostMACBridgePortConfigPortPathCost OBJECT-TYPE
        SYNTAX      INTEGER
        MAX-ACCESS  read-write
        STATUS      current
        DESCRIPTION
        "This attribute provides the cost contribution of the port to the path cost 
        towards the spanning tree root bridge. The range is 0x0001 to 0xFFFF (1 to 65535).(2 bytes)"
        REFERENCE   "G.984.4 section 9.3.9 MAC Bridge Port Configuation Data"
        ::= { zxGponHostMACBridgePortConfigEntry 4 }
        
    zxGponHostMACBridgePortConfigPortSpanTreeInd OBJECT-TYPE
        SYNTAX      TruthValue
        MAX-ACCESS  read-write
        STATUS      current
        DESCRIPTION
        "This Boolean attribute indicates whether or not STP LAN topology change detection 
        is enabled at this port. The value TRUE means enabled.(1 byte)"
        REFERENCE   "G.984.4 section 9.3.9 MAC Bridge Port Configuation Data"
        ::= { zxGponHostMACBridgePortConfigEntry 5 }
        
    zxGponHostMACBridgePortConfigEncapMethod OBJECT-TYPE
        SYNTAX      INTEGER{
                    atmvc(1),
                    llc(2)
                    }
        MAX-ACCESS  read-write
        STATUS      current
        DESCRIPTION
        "This attribute identifies the frame encapsulation method that is used.
        0x00: identification by ATM VC;
        0x01: LLC encapsulation;
        This attribute is effective only for ports towards the ANI side of the MAC bridge. 
        Upon autonomous instantiation, the value 0x00 is used.
        (1 byte)"
        REFERENCE   "G.984.4 section 9.3.9 MAC Bridge Port Configuation Data"
        ::= { zxGponHostMACBridgePortConfigEntry 6 }
        
    zxGponHostMACBridgePortConfigLANFCSInd OBJECT-TYPE
        SYNTAX      INTEGER{
                    forward(1),
                    discard(2)
                    }
        MAX-ACCESS  read-write
        STATUS      current
        DESCRIPTION
        "This attribute indicates whether LAN FCS (Frame Check Sequence) bytes are 
        forwarded (value 0x00) or discarded (value 0x01). This applies in both directions of 
        transmission, and applies regardless of EncapsulationMethod. 
        This attribute is effective only for ports towards the ANI side of the MAC bridge. 
        Upon autonomous instantiation, the value 0x00 is used.(1 byte)"
        REFERENCE   "G.984.4 section 9.3.9 MAC Bridge Port Configuation Data"
        ::= { zxGponHostMACBridgePortConfigEntry 7 }

    zxGponHostMACBridgePortConfigPortMACAddr OBJECT-TYPE
        SYNTAX      MacAddress
        MAX-ACCESS  read-only
        STATUS      current
        DESCRIPTION
        "This attribute indicates the Physical MAC address used by the Port as defined by 
        the TPPointer when the TPType is set to LAN.(6 bytes)"
        REFERENCE   "G.984.4 section 9.3.9 MAC Bridge Port Configuation Data"
        ::= { zxGponHostMACBridgePortConfigEntry 8 }
        
    zxGponHostMACBridgePortConfigEntryStatus OBJECT-TYPE
        SYNTAX      RowStatus
        MAX-ACCESS  read-write
        STATUS      current
        DESCRIPTION
        "This attribute indicates the Physical MAC address used by the Port as defined by 
        the TPPointer when the TPType is set to LAN.(6 bytes)"
        REFERENCE   "G.984.4 section 9.3.9 MAC Bridge Port Configuation Data"
        ::= { zxGponHostMACBridgePortConfigEntry 9 }

--SIP Agent Config Data
    zxGponSIPAgentConfigDataTable    OBJECT-TYPE
        SYNTAX      SEQUENCE OF ZxGponSIPAgentConfigDataEntry
        MAX-ACCESS  not-accessible
        STATUS      current
        DESCRIPTION
            "One instance of this managed entity is related to a TCP/UDP Config Data object.  
            This managed entity may be referenced by one or more SIP User Data managed entities."
        REFERENCE   "G.983.2 section 7.3.103 SIP Agent Config Data"
        ::= { zxGponL2Mgmt 43 }

    zxGponSIPAgentConfigDataEntry OBJECT-TYPE
        SYNTAX      ZxGponSIPAgentConfigDataEntry
        MAX-ACCESS  not-accessible
        STATUS      current
        DESCRIPTION
            "It is entry in the zxGponSIPAgentConfigDataTable."
        INDEX   { zxGponOltIndex, zxGponONTIndex, zxGponSIPAgentConfigDataId }
        ::= { zxGponSIPAgentConfigDataTable 1 }

    ZxGponSIPAgentConfigDataEntry ::=
        SEQUENCE {
            zxGponSIPAgentConfigDataId                       INTEGER,
            zxGponSIPAgentConfigDataProxyServer              OCTET STRING,
            zxGponSIPAgentConfigDataOutboundProxy            OCTET STRING,
            zxGponSIPAgentConfigDataPrimaryDNS               IpAddress,
            zxGponSIPAgentConfigDataSecondaryDNS             IpAddress,
            zxGponSIPAgentConfigDataUDPTCPPort               INTEGER,
            zxGponSIPAgentConfigDataHostId                   INTEGER,
            zxGponSIPAgentConfigDataRegExpTime               INTEGER,
            zxGponSIPAgentConfigDataReRegStartTime           INTEGER,
            zxGponSIPAgentConfigDataHostPartURI              OCTET STRING,
            zxGponSIPAgentConfigDataSIPStatus                INTEGER,
            zxGponSIPAgentConfigDataRegServer                OCTET STRING,
            zxGponSIPAgentConfigDataValidatScheme            INTEGER,
            zxGponSIPAgentConfigDataRegUserName              OCTET STRING,
            zxGponSIPAgentConfigDataRegPassword              OCTET STRING,
            zxGponSIPAgentConfigDataRealm                    OCTET STRING,
            zxGponSIPAgentConfigDataSSVendor                 OCTET STRING,
            zxGponSIPAgentConfigDataEntryStatus              RowStatus
        }

    zxGponSIPAgentConfigDataId OBJECT-TYPE
        SYNTAX      INTEGER
        MAX-ACCESS  read-only
        STATUS      current
        DESCRIPTION
        "This attribute provides a unique number for each instance of this managed entity.
        (1~n)(R, Set-by-create) (mandatory) (2 bytes)"
        REFERENCE   "G.983.2 section 7.3.103 SIP Agent Config Data"
        ::= { zxGponSIPAgentConfigDataEntry 1 }

    zxGponSIPAgentConfigDataProxyServer OBJECT-TYPE
        SYNTAX      OCTET STRING(SIZE(0..128))
        MAX-ACCESS  read-write
        STATUS      current
        DESCRIPTION
        "This attribute provides a pointer to a LargeString ME  that contains the name (IP address or URI) 
        of the SIP Proxy Server for SIP signaling messages. (R, W, Set-by-create) (mandatory) (2 bytes)"
        REFERENCE   "G.983.2 section 7.3.103 SIP Agent Config Data"
        ::= { zxGponSIPAgentConfigDataEntry 2 }
        
    zxGponSIPAgentConfigDataOutboundProxy OBJECT-TYPE
        SYNTAX      OCTET STRING(SIZE(0..128))
        MAX-ACCESS  read-write
        STATUS      current
        DESCRIPTION
        "This attribute provides a pointer to a LargeString ME that contains the name (IP address or URI) 
        of the SIP outbound Proxy Server for SIP signaling messages.  (R, W, Set-by-create) (mandatory) (2 bytes)"
        REFERENCE   "G.983.2 section 7.3.103 SIP Agent Config Data"
        ::= { zxGponSIPAgentConfigDataEntry 3 }
        
    zxGponSIPAgentConfigDataPrimaryDNS OBJECT-TYPE
        SYNTAX      IpAddress
        MAX-ACCESS  read-write
        STATUS      current
        DESCRIPTION
        "This attribute defines the Primary SIP DNS IP Address.  If this value is zero, the Primary SIP DNS should not be used.  
        Default value of 0.  (R, W, Set-by-create) (mandatory) (4 bytes)"
        REFERENCE   "G.983.2 section 7.3.103 SIP Agent Config Data"
        ::= { zxGponSIPAgentConfigDataEntry 4 }
        
    zxGponSIPAgentConfigDataSecondaryDNS OBJECT-TYPE
        SYNTAX      IpAddress
        MAX-ACCESS  read-write
        STATUS      current
        DESCRIPTION
        "This attribute defines the Secondary SIP DNS IP Address. If this value is zero, the Secondary SIP DNS should not be used.  
        Default value of 0.  (R, W, Set-by-create) (mandatory) (4 bytes)"
        REFERENCE   "G.983.2 section 7.3.103 SIP Agent Config Data"
        ::= { zxGponSIPAgentConfigDataEntry 5 }
        
    zxGponSIPAgentConfigDataUDPTCPPort OBJECT-TYPE
        SYNTAX      INTEGER
        MAX-ACCESS  read-write
        STATUS      current
        DESCRIPTION
        "This attribute indicates the UDP/TCP port num.
        This attribute associates the SIP Agent with the TCP/UDP service to be used for communication with the SIP Server.  
        Default value is 0xFFFF.  (R, W) (mandatory) (2 bytes)"
        REFERENCE   "G.983.2 section 7.3.103 SIP Agent Config Data"
        ::= { zxGponSIPAgentConfigDataEntry 6 }
        
    zxGponSIPAgentConfigDataHostId OBJECT-TYPE
        SYNTAX      INTEGER
        MAX-ACCESS  read-write
        STATUS      current
        DESCRIPTION
        "This attribute indicates the UDP/TCP port num.
        This attribute associates the SIP Agent with the TCP/UDP service to be used for communication with the SIP Server.  
        Default value is 0xFFFF.  (R, W) (mandatory) (2 bytes)"
        REFERENCE   "G.983.2 section 7.3.103 SIP Agent Config Data"
        ::= { zxGponSIPAgentConfigDataEntry 7 }

    zxGponSIPAgentConfigDataRegExpTime OBJECT-TYPE
        SYNTAX      INTEGER
        MAX-ACCESS  read-write
        STATUS      current
        DESCRIPTION
        "This attribute defines the SIP Registration Expiration Time in seconds.  If this value is zero, 
        the SIP Agent will not add an expiration time to the registration requests, and will not perform 
        re-registration.  
        The default value used at Create shall be 3600 seconds. (R, W) (mandatory) (4 bytes)"
        REFERENCE   "G.983.2 section 7.3.103 SIP Agent Config Data"
        ::= { zxGponSIPAgentConfigDataEntry 8 }
        
    zxGponSIPAgentConfigDataReRegStartTime OBJECT-TYPE
        SYNTAX      INTEGER
        MAX-ACCESS  read-write
        STATUS      current
        DESCRIPTION
        "This attribute provides the time in seconds prior to timeout that the SIP Agent should start 
        the re-registration process.  The default value used at Create shall be 360 seconds. (R, W) (mandatory) (4 bytes)"
        REFERENCE   "G.983.2 section 7.3.103 SIP Agent Config Data"
        ::= { zxGponSIPAgentConfigDataEntry 9 }

    zxGponSIPAgentConfigDataHostPartURI OBJECT-TYPE
        SYNTAX      OCTET STRING(SIZE(0..128))
        MAX-ACCESS  read-write
        STATUS      current
        DESCRIPTION
        "This attribute provides a pointer to a LargeString ME that contains the host or domain part of 
        the SIP Address of Record for users connected to this ONT. A 0xFFFF indicates the current address 
        in the IP Host Config ME is used. Default value is 0xFFFF. (R, W, Set-by-create) (mandatory) (2 bytes)"
        REFERENCE   "G.983.2 section 7.3.103 SIP Agent Config Data"
        ::= { zxGponSIPAgentConfigDataEntry 10 }

    zxGponSIPAgentConfigDataSIPStatus OBJECT-TYPE
        SYNTAX      INTEGER{
                    ok-initial(1),
                    connected(2),
                    failed-icmpErr(3),
                    failed-malformedRsp(4),
                    failed-inadequateRsp(5),
                    failed-timeout(6)
                    }
        MAX-ACCESS  read-only
        STATUS      current
        DESCRIPTION
        "This attribute is used to show the current status of the SIP Agent.  
        Values are as follows: 
        0: ok/initial, 
        1: Connected, 
        2: Failed-ICMP Error, 
        3: Failed-Malformed-response, 
        4: Failed-Inadequate Info Response, 
        5: Failed-Timeout.  (R) (mandatory) (1 byte)"
        REFERENCE   "G.983.2 section 7.3.103 SIP Agent Config Data"
        ::= { zxGponSIPAgentConfigDataEntry 11 }

    zxGponSIPAgentConfigDataRegServer OBJECT-TYPE
        SYNTAX      OCTET STRING(SIZE(0..128))
        MAX-ACCESS  read-write
        STATUS      current
        DESCRIPTION
        "This attribute provides a pointer to a Network Address ME that contains the name 
        (IP address or resolved name) of the SIP Registrar Server for SIP signaling messages.  
        Examples: '10.10.10.10' and 'proxy.voip.net'.  
        Default value is 0xFFFF. (R, W, Set-by-create) (mandatory) (2 bytes)"
        REFERENCE   "G.983.2 section 7.3.103 SIP Agent Config Data"
        ::= { zxGponSIPAgentConfigDataEntry 12 }
        
    zxGponSIPAgentConfigDataValidatScheme OBJECT-TYPE
        SYNTAX      INTEGER{
                    disable(1),
                    md5(2),
                    basic(3)
                    }
        MAX-ACCESS  read-write
        STATUS      current
        DESCRIPTION
        ""
        REFERENCE   "G.983.2 section 7.3.103 SIP Agent Config Data"
        ::= { zxGponSIPAgentConfigDataEntry 13 }
        
    zxGponSIPAgentConfigDataRegUserName OBJECT-TYPE
        SYNTAX      OCTET STRING(SIZE(0..25))
        MAX-ACCESS  read-write
        STATUS      current
        DESCRIPTION
        ""
        REFERENCE   "G.983.2 section 7.3.103 SIP Agent Config Data"
        ::= { zxGponSIPAgentConfigDataEntry 14 }
        
    zxGponSIPAgentConfigDataRegPassword OBJECT-TYPE
        SYNTAX      OCTET STRING(SIZE(0..25))
        MAX-ACCESS  read-write
        STATUS      current
        DESCRIPTION
        ""
        REFERENCE   "G.983.2 section 7.3.103 SIP Agent Config Data"
        ::= { zxGponSIPAgentConfigDataEntry 15 }
        
    zxGponSIPAgentConfigDataRealm OBJECT-TYPE
        SYNTAX      OCTET STRING(SIZE(0..25))
        MAX-ACCESS  read-write
        STATUS      current
        DESCRIPTION
        ""
        REFERENCE   "G.983.2 section 7.3.103 SIP Agent Config Data"
        ::= { zxGponSIPAgentConfigDataEntry 16 }

    zxGponSIPAgentConfigDataSSVendor OBJECT-TYPE
        SYNTAX      OCTET STRING(SIZE(0..4))
        MAX-ACCESS  read-write
        STATUS      current
        DESCRIPTION
        " This attribute identifies the SIP Gateway softswitch vendor.  
        The format is four ASCII coded alphabetic characters [A - Z] as defined in ANSI T1.220,  
        All NULL characters indicates no particular vendor. (R,W, Set-by-create) (mandatory) (4 byte)"
        REFERENCE   "G.983.2 section 7.3.103 SIP Agent Config Data"
        ::= { zxGponSIPAgentConfigDataEntry 17 }

    zxGponSIPAgentConfigDataEntryStatus OBJECT-TYPE
        SYNTAX      RowStatus
        MAX-ACCESS  read-write
        STATUS      current
        DESCRIPTION
        " "
        REFERENCE   "G.983.2 section 7.3.103 SIP Agent Config Data"
        ::= { zxGponSIPAgentConfigDataEntry 18 }

--SIP User Data
    zxGponSIPUserDataTable    OBJECT-TYPE
        SYNTAX      SEQUENCE OF ZxGponSIPUserDataEntry
        MAX-ACCESS  not-accessible
        STATUS      current
        DESCRIPTION
            "An instance of this managed entity may be referenced by one VoIP Voice CTP managed entity."
        REFERENCE   "G.983.2 section 7.3.106 SIP User Data"
        ::= { zxGponL2Mgmt 44 }

    zxGponSIPUserDataEntry OBJECT-TYPE
        SYNTAX      ZxGponSIPUserDataEntry
        MAX-ACCESS  not-accessible
        STATUS      current
        DESCRIPTION
            "It is entry in the zxGponSIPUserDataTable."
        INDEX   { zxGponOltIndex, zxGponONTIndex, zxGponUNIIndex }
        ::= { zxGponSIPUserDataTable 1 }
        
    ZxGponSIPUserDataEntry ::=
        SEQUENCE {
            zxGponSIPUserDataAgentId                  INTEGER,
            zxGponSIPUserDataUserPartAOR              OCTET STRING,
            zxGponSIPUserDataDisplayName              OCTET STRING,
            zxGponSIPUserDataUserName                 OCTET STRING,
            zxGponSIPUserDataPassword                 OCTET STRING,
            zxGponSIPUserDataVMailServerURI           OCTET STRING,
            zxGponSIPUserDataVMailValidateScheme      INTEGER,
            zxGponSIPUserDataVMailUserName            OCTET STRING,
            zxGponSIPUserDataVMailPassword            OCTET STRING,
            zxGponSIPUserDataVMailRealm               OCTET STRING,
            zxGponSIPUserDataVMailSubsciptExpTime     INTEGER,
            zxGponSIPUserDataNetworkDialPlanPtr       INTEGER,
            zxGponSIPUserDataServiceProfilePtr        INTEGER,
            zxGponSIPUserDataFeatureCodePtr           INTEGER,
            zxGponSIPUserDataReleaseTimer             INTEGER,
            zxGponSIPUserDataROHTimer                 INTEGER,
            zxGponSIPUserDataEntryStatus              RowStatus
        }

    zxGponSIPUserDataAgentId OBJECT-TYPE
        SYNTAX      INTEGER
        MAX-ACCESS  read-write
        STATUS      current
        DESCRIPTION
        "Points to the SIP Agent Config Data ME to be used for signaling.  
        (R, W, Set-by-create) (mandatory) (2 bytes)"
        REFERENCE   "G.983.2 section 7.3.106 SIP User Data"
        ::= { zxGponSIPUserDataEntry 1 }
        
    zxGponSIPUserDataUserPartAOR OBJECT-TYPE
        SYNTAX      OCTET STRING(SIZE(0..128))
        MAX-ACCESS  read-write
        STATUS      current
        DESCRIPTION
        "This attribute provides a pointer to a LargeString ME that contains the user identification 
        part of the Address of Record. This can take the form of  an alphanumeric string or the 
        directory number used to reference the user in the network.  0xFFFF indicates that no user 
        part AOR has been defined. (R, W, Set-by-create) (mandatory) (2 bytes)"
        REFERENCE   "G.983.2 section 7.3.106 SIP User Data"
        ::= { zxGponSIPUserDataEntry 2 }
        
    zxGponSIPUserDataDisplayName OBJECT-TYPE
        SYNTAX      OCTET STRING(SIZE(0..25))
        MAX-ACCESS  read-write
        STATUS      current
        DESCRIPTION
        "This attribute defines the Customer ID used for outgoing SIP messages display attribute in ASCII 
        string format.   Default value shall be null (all zeros).  (R, W) (mandatory) (25 bytes)"
        REFERENCE   "G.983.2 section 7.3.106 SIP User Data"
        ::= { zxGponSIPUserDataEntry 3 }
        
    zxGponSIPUserDataUserName OBJECT-TYPE
        SYNTAX      OCTET STRING(SIZE(0..128))
        MAX-ACCESS  read-write
        STATUS      current
        DESCRIPTION
        "A pointer to an Authentication Security Method ME that contains a SIP user name and password used 
        for authentication.  0xFFFF indicates no username/password. (R, W, Set-by-create) (mandatory) (2 bytes)"
        REFERENCE   "G.983.2 section 7.3.106 SIP User Data"
        ::= { zxGponSIPUserDataEntry 4 }
        
    zxGponSIPUserDataPassword OBJECT-TYPE
        SYNTAX      OCTET STRING(SIZE(0..25))
        MAX-ACCESS  read-write
        STATUS      current
        DESCRIPTION
        "A pointer to an Authentication Security Method ME that contains a SIP user name and password used 
        for authentication.  0xFFFF indicates no username/password. (R, W, Set-by-create) (mandatory) (2 bytes)"
        REFERENCE   "G.983.2 section 7.3.106 SIP User Data"
        ::= { zxGponSIPUserDataEntry 5 }

    zxGponSIPUserDataVMailServerURI OBJECT-TYPE
        SYNTAX      OCTET STRING(SIZE(0..128))
        MAX-ACCESS  read-write
        STATUS      current
        DESCRIPTION
        "This attribute provides a pointer to a Network Address ME that contains the name (IP address or URI) 
        of the SIP Voice Mail Server for SIP signaling messages.  A value of  0xFFFF indicates that no 
        Voice Mail subscription is required. Default value is 0xFFFF. (R, W, Set by Create) (mandatory) (2 bytes)"
        REFERENCE   "G.983.2 section 7.3.106 SIP User Data"
        ::= { zxGponSIPUserDataEntry 6 }
        
    zxGponSIPUserDataVMailValidateScheme OBJECT-TYPE
        SYNTAX      INTEGER{
                    disable(1),
                    md5(2),
                    basic(3)
                    }
        MAX-ACCESS  read-write
        STATUS      current
        DESCRIPTION
        ""
        REFERENCE   "G.983.2 section 7.3.106 SIP User Data"
        ::= { zxGponSIPUserDataEntry 7 }
        
    zxGponSIPUserDataVMailUserName OBJECT-TYPE
        SYNTAX      OCTET STRING(SIZE(0..25))
        MAX-ACCESS  read-write
        STATUS      current
        DESCRIPTION
        ""
        REFERENCE   "G.983.2 section 7.3.106 SIP User Data"
        ::= { zxGponSIPUserDataEntry 8 }
        
    zxGponSIPUserDataVMailPassword OBJECT-TYPE
        SYNTAX      OCTET STRING(SIZE(0..25))
        MAX-ACCESS  read-write
        STATUS      current
        DESCRIPTION
        ""
        REFERENCE   "G.983.2 section 7.3.106 SIP User Data"
        ::= { zxGponSIPUserDataEntry 9 }
        
    zxGponSIPUserDataVMailRealm OBJECT-TYPE
        SYNTAX      OCTET STRING(SIZE(0..25))
        MAX-ACCESS  read-write
        STATUS      current
        DESCRIPTION
        ""
        REFERENCE   "G.983.2 section 7.3.106 SIP User Data"
        ::= { zxGponSIPUserDataEntry 10 }

    zxGponSIPUserDataVMailSubsciptExpTime OBJECT-TYPE
        SYNTAX      INTEGER
        MAX-ACCESS  read-write
        STATUS      current
        DESCRIPTION
        "This attribute defines the Voice Mail server subscription  Expiration Time in seconds. 
        If this value is zero, the SIP Agent will use the implementation specific default for this ONT/ONU. 
        The default value used at Create shall be 3600 seconds. (R, W, Set-by-create) (mandatory) (4 bytes)"
        REFERENCE   "G.983.2 section 7.3.106 SIP User Data"
        ::= { zxGponSIPUserDataEntry 11 }

    zxGponSIPUserDataNetworkDialPlanPtr OBJECT-TYPE
        SYNTAX      INTEGER
        MAX-ACCESS  read-write
        STATUS      current
        DESCRIPTION
        "Pointer to Network Dial Plan ME. A value of 0xFFFF indicates that no network dial plan is available. 
        Default value is 0xFFFF. (R, W, Set-by-create) (mandatory) (2 bytes)"
        REFERENCE   "G.983.2 section 7.3.106 SIP User Data"
        ::= { zxGponSIPUserDataEntry 12 }

    zxGponSIPUserDataServiceProfilePtr OBJECT-TYPE
        SYNTAX      INTEGER
        MAX-ACCESS  read-write
        STATUS      current
        DESCRIPTION
        "Pointer to Application Services Profile ME. A value of 0xFFFF indicates that no Application 
        Services Profile is available. Default value is 0xFFFF. (R, W, Set-by-create) (mandatory) (2 bytes)"
        REFERENCE   "G.983.2 section 7.3.106 SIP User Data"
        ::= { zxGponSIPUserDataEntry 13 }

    zxGponSIPUserDataFeatureCodePtr OBJECT-TYPE
        SYNTAX      INTEGER
        MAX-ACCESS  read-write
        STATUS      current
        DESCRIPTION
        "This attribute contains a pointer to the Feature Access Codes ME for this subscriber. 
        A value of 0xFFFF indicates that no Feature Access Codes ME is available. Default value 
        is 0xFFFF. (R, W, Set-by-create) (mandatory) (2 bytes)"
        REFERENCE   "G.983.2 section 7.3.106 SIP User Data"
        ::= { zxGponSIPUserDataEntry 14 }

    zxGponSIPUserDataReleaseTimer OBJECT-TYPE
        SYNTAX      INTEGER
        MAX-ACCESS  read-write
        STATUS      current
        DESCRIPTION
        "This attribute contains a release timer defined in seconds. 0x0 = Use internal default, 
        Default value is 10 sec. (R, W) (optional)(1 byte)"
        REFERENCE   "G.983.2 section 7.3.106 SIP User Data"
        ::= { zxGponSIPUserDataEntry 15 }
    
    zxGponSIPUserDataROHTimer OBJECT-TYPE
        SYNTAX      INTEGER
        MAX-ACCESS  read-write
        STATUS      current
        DESCRIPTION
        "This attribute defines the length of time in seconds for the receiver off hook condition before 
        ROH tone is applied. 0x0 = ROH is disabled. Default value is 15 seconds. (R,W) (optional) (1 byte)"
        REFERENCE   "G.983.2 section 7.3.106 SIP User Data"
        ::= { zxGponSIPUserDataEntry 16 }
        
    zxGponSIPUserDataEntryStatus OBJECT-TYPE
        SYNTAX      RowStatus
        MAX-ACCESS  read-write
        STATUS      current
        DESCRIPTION
        ""
        REFERENCE   "G.983.2 section 7.3.106 SIP User Data"
        ::= { zxGponSIPUserDataEntry 17 }

--VoIP Voice CTP
    zxGponVoIPVoiceCTPTable    OBJECT-TYPE
        SYNTAX      SEQUENCE OF ZxGponVoIPVoiceCTPEntry
        MAX-ACCESS  not-accessible
        STATUS      current
        DESCRIPTION
            "An instance of this managed entity refers to one PPTP POTS UNI managed entity, one VoIP Media Profile, and one SIP User Data managed entity or MGC Config Data ME."
        REFERENCE   "G.983.2 section 7.3.110 VoIP Voice CTP"
        ::= { zxGponL2Mgmt 45 }

    zxGponVoIPVoiceCTPEntry OBJECT-TYPE
        SYNTAX      ZxGponVoIPVoiceCTPEntry
        MAX-ACCESS  not-accessible
        STATUS      current
        DESCRIPTION
            "It is entry in the zxGponVoIPVoiceCTPTable."
        INDEX   { zxGponOltIndex, zxGponONTIndex, zxGponUNIIndex }
        ::= { zxGponVoIPVoiceCTPTable 1 }
        
    ZxGponVoIPVoiceCTPEntry ::=
        SEQUENCE {
            zxGponVoIPVoiceCTPMediaProfilePtr         INTEGER,
            zxGponVoIPVoiceCTPSignalCode              INTEGER,
            zxGponVoIPVoiceCTPEntryStatus             RowStatus,
            zxGponVoIPVoiceCTPMGCId                   INTEGER
        }

    zxGponVoIPVoiceCTPMediaProfilePtr OBJECT-TYPE
        SYNTAX      INTEGER
        MAX-ACCESS  read-write
        STATUS      current
        DESCRIPTION
        "Pointer to VOIP Media Profile.  (R, W, Set-by-create) (mandatory) (2 bytes)"
        REFERENCE   "G.983.2 section 7.3.110 VoIP Voice CTP"
        ::= { zxGponVoIPVoiceCTPEntry 1 }
        
    zxGponVoIPVoiceCTPSignalCode OBJECT-TYPE
        SYNTAX      INTEGER{
                    loop-start(1),
                    ground-start(2),
                    loop-reverse-battery(3),
                    coin-first(4),
                    dial-tone-first(5),
                    multi-party(6)
                    }
        MAX-ACCESS  read-write
        STATUS      current
        DESCRIPTION
        "This attribute specifies whether 'loop start' (0x01), 'ground start' (0x02), 
        'loop reverse battery' (0x03), 'coin first' (0x04), 'dial tone first' (0x05), 
        or 'multi-party' (0x06) signaling is employed.  (R, Set-by-create) (mandatory) (1 byte)"
        REFERENCE   "G.983.2 section 7.3.110 VoIP Voice CTP"
        ::= { zxGponVoIPVoiceCTPEntry 2 }
        
    zxGponVoIPVoiceCTPEntryStatus OBJECT-TYPE
        SYNTAX      RowStatus
        MAX-ACCESS  read-write
        STATUS      current
        DESCRIPTION
        ""
        REFERENCE   "G.983.2 section 7.3.110 VoIP Voice CTP"
        ::= { zxGponVoIPVoiceCTPEntry 3 }

    zxGponVoIPVoiceCTPMGCId OBJECT-TYPE
        SYNTAX      INTEGER
        MAX-ACCESS  read-write
        STATUS      current
        DESCRIPTION
        "This attribute specifies the id of MGC related with POTS UNI.
        It's used when VoIP protocol is H.248."
        REFERENCE   "G.983.2 section 7.3.110 VoIP Voice CTP"
        ::= { zxGponVoIPVoiceCTPEntry 4 }

--Network Dial Plan Table
    zxGponNetworkDialPlanTable    OBJECT-TYPE
        SYNTAX      SEQUENCE OF ZxGponNetworkDialPlanEntry
        MAX-ACCESS  not-accessible
        STATUS      current
        DESCRIPTION
            "An instance of this managed entity may be associated with one or more instances of the SIP User Data managed entity."
        REFERENCE   "G.983.2 section 7.3.112 Network Dial Plan Table"
        ::= { zxGponL2Mgmt 46 }

    zxGponNetworkDialPlanEntry OBJECT-TYPE
        SYNTAX      ZxGponNetworkDialPlanEntry
        MAX-ACCESS  not-accessible
        STATUS      current
        DESCRIPTION
            "It is entry in the zxGponNetworkDialPlanTable."
        INDEX   { zxGponNetworkDialPlanId }
        ::= { zxGponNetworkDialPlanTable 1 }
        
    ZxGponNetworkDialPlanEntry ::=
        SEQUENCE {
            zxGponNetworkDialPlanId                        INTEGER,
            zxGponNetworkDialPlanName                      OCTET STRING,
            zxGponNetworkDialPlanTableMaxSize              INTEGER,
            zxGponNetworkDialPlanCriticalDialTimeout       INTEGER,
            zxGponNetworkDialPlanParticalDialTimeout       INTEGER,
            zxGponNetworkDialPlanFormat                    INTEGER,
            zxGponNetworkDialPlanRefCnt                    INTEGER,
            zxGponNetworkDialPlanEntryStatus               RowStatus
        }

    zxGponNetworkDialPlanId OBJECT-TYPE
        SYNTAX      INTEGER
        MAX-ACCESS  not-accessible
        STATUS      current
        DESCRIPTION
        "This attribute provides a unique number for each instance of this managed entity.  (R, Set-by-create) (mandatory) (2 bytes)"
        REFERENCE   "G.983.2 section 7.3.112 Network Dial Plan Table"
        ::= { zxGponNetworkDialPlanEntry 1 }
        
    zxGponNetworkDialPlanName OBJECT-TYPE
        SYNTAX      OCTET STRING(SIZE(1..63))
        MAX-ACCESS  read-write
        STATUS      current
        DESCRIPTION
        "This attribute indicates the name of the dial plan table."
        REFERENCE   "G.983.2 section 7.3.112 Network Dial Plan Table"
        ::= { zxGponNetworkDialPlanEntry 2 }
        
    zxGponNetworkDialPlanTableMaxSize OBJECT-TYPE
        SYNTAX      INTEGER
        MAX-ACCESS  read-write
        STATUS      current
        DESCRIPTION
        "    This attribute indicates the maximum number of dial plans that can be stored in the dial 
        plan table.  (R, Set-by-create) (mandatory) (2 bytes)"
        REFERENCE   "G.983.2 section 7.3.112 Network Dial Plan Table"
        ::= { zxGponNetworkDialPlanEntry 3 }
        
    zxGponNetworkDialPlanCriticalDialTimeout OBJECT-TYPE
        SYNTAX      INTEGER
        MAX-ACCESS  read-write
        STATUS      current
        DESCRIPTION
        "This attribute defines the critical dial timeout for digit map processing in milliseconds.  
        Default value is 4000ms.  (R, W, Set-by-create) (mandatory) (2 bytes)"
        REFERENCE   "G.983.2 section 7.3.112 Network Dial Plan Table"
        ::= { zxGponNetworkDialPlanEntry 4 }

    zxGponNetworkDialPlanParticalDialTimeout OBJECT-TYPE
        SYNTAX      INTEGER
        MAX-ACCESS  read-write
        STATUS      current
        DESCRIPTION
        "This attribute defines the partial dial timeout for digit map processing in milliseconds.  
        Default value is 16000ms.  (R, W, Set-by-create) (mandatory) (2 bytes)"
        REFERENCE   "G.983.2 section 7.3.112 Network Dial Plan Table"
        ::= { zxGponNetworkDialPlanEntry 5 }

    zxGponNetworkDialPlanFormat OBJECT-TYPE
        SYNTAX      INTEGER{
                    not-defined(1),
                    h248(2),
                    nsc(3),
                    vendor-specific(4)
                    }
        MAX-ACCESS  read-write
        STATUS      current
        DESCRIPTION
        "This attribute define the dial plan format standard that is supported in the ONT for VoIP.  
        Valid values include 0 = not defined,  1 = H.248 format with specific plan (table entries define 
        the dialing plan) 2=NSC format, 3=Vendor specific format.  Default is 1.  (R, W, Set-by-create) (mandatory) (1 bytes)"
        REFERENCE   "G.983.2 section 7.3.112 Network Dial Plan Table"
        ::= { zxGponNetworkDialPlanEntry 6 }
        
    zxGponNetworkDialPlanRefCnt OBJECT-TYPE
        SYNTAX      INTEGER
        MAX-ACCESS  read-only
        STATUS      current
        DESCRIPTION
        "Forbidden to modify if not equal zero"
        REFERENCE   "G.983.2 section 7.3.112 Network Dial Plan Table"
        ::= { zxGponNetworkDialPlanEntry 7 }
        
    zxGponNetworkDialPlanEntryStatus OBJECT-TYPE
        SYNTAX      RowStatus
        MAX-ACCESS  read-write
        STATUS      current
        DESCRIPTION
        ""
        REFERENCE   "G.983.2 section 7.3.112 Network Dial Plan Table"
        ::= { zxGponNetworkDialPlanEntry 8 }

--Network Dial Plan Table Operation
    zxGponNetworkDialPlanOperationTable    OBJECT-TYPE
        SYNTAX      SEQUENCE OF ZxGponNetworkDialPlanOperationEntry
        MAX-ACCESS  not-accessible
        STATUS      current
        DESCRIPTION
            "An instance of this managed entity may be associated with one or more instances of the SIP User Data managed entity.
            Here, the operations of Dial Plan Table are defined."
        REFERENCE   "G.983.2 section 7.3.112 Network Dial Plan Table"
        ::= { zxGponL2Mgmt 47 }

    zxGponNetworkDialPlanOperationEntry OBJECT-TYPE
        SYNTAX      ZxGponNetworkDialPlanOperationEntry
        MAX-ACCESS  not-accessible
        STATUS      current
        DESCRIPTION
            "It is entry in the zxGponNetworkDialPlanOperationTable."
        INDEX   { zxGponNetworkDialPlanId, zxGponNetworkDialPlanOperationTableId }
        ::= { zxGponNetworkDialPlanOperationTable 1 }
        
    ZxGponNetworkDialPlanOperationEntry ::=
        SEQUENCE {
            zxGponNetworkDialPlanOperationTableId                   INTEGER,
            zxGponNetworkDialPlanOperationToken                     OCTET STRING,
            zxGponNetworkDialPlanOperationEntryStatus               RowStatus
        }

    zxGponNetworkDialPlanOperationTableId OBJECT-TYPE
        SYNTAX      INTEGER
        MAX-ACCESS  not-accessible
        STATUS      current
        DESCRIPTION
        "A unique identifier of a dial plan within the dial plan table (1 byte);"
        REFERENCE   "G.983.2 section 7.3.112 Network Dial Plan Table"
        ::= { zxGponNetworkDialPlanOperationEntry 1 }
        
    zxGponNetworkDialPlanOperationToken OBJECT-TYPE
        SYNTAX      OCTET STRING(SIZE(1..28))
        MAX-ACCESS  read-write
        STATUS      current
        DESCRIPTION
        "Token used by the VoIP service to process dial plans.  This ASCII string is typically 
        delimited by ':'.  (R, W) (conditionally required) (28 bytes)"
        REFERENCE   "G.983.2 section 7.3.112 Network Dial Plan Table"
        ::= { zxGponNetworkDialPlanOperationEntry 2 }
        
    zxGponNetworkDialPlanOperationEntryStatus OBJECT-TYPE
        SYNTAX      RowStatus
        MAX-ACCESS  read-write
        STATUS      current
        DESCRIPTION
        ""
        REFERENCE   "G.983.2 section 7.3.112 Network Dial Plan Table"
        ::= { zxGponNetworkDialPlanOperationEntry 3 }

--VoIP Application Service Profile
    zxGponVoIPAppServiceProfileTable    OBJECT-TYPE
        SYNTAX      SEQUENCE OF ZxGponVoIPAppServiceProfileEntry
        MAX-ACCESS  not-accessible
        STATUS      current
        DESCRIPTION
            "An instance of this managed entity is referenced by the SIP User Data ME."
        REFERENCE   "G.983.2 section 7.3.113 VoIP Application Service Profile"
        ::= { zxGponL2Mgmt 48 }

    zxGponVoIPAppServiceProfileEntry OBJECT-TYPE
        SYNTAX      ZxGponVoIPAppServiceProfileEntry
        MAX-ACCESS  not-accessible
        STATUS      current
        DESCRIPTION
            "It is entry in the zxGponVoIPAppServiceProfileTable."
        INDEX   { zxGponOltIndex, zxGponONTIndex, zxGponVoIPAppServiceProfileId }
        ::= { zxGponVoIPAppServiceProfileTable 1 }
        
    ZxGponVoIPAppServiceProfileEntry ::=
        SEQUENCE {
            zxGponVoIPAppServiceProfileId                           INTEGER,
            zxGponVoIPAppServiceProfileCIDFeature                   INTEGER,
            zxGponVoIPAppServiceProfileCallWaitingFeature           INTEGER,
            zxGponVoIPAppServiceProfileCallProgressFeature          INTEGER,
            zxGponVoIPAppServiceProfileCallPresentationFeature      INTEGER,
            zxGponVoIPAppServiceProfileDirectConnectFeature         INTEGER,
            zxGponVoIPAppServiceProfileDirectConnectURI             OCTET STRING,
            zxGponVoIPAppServiceProfileBridgeLineAgentURI           OCTET STRING,
            zxGponVoIPAppServiceProfileConferenceFactoryURI         OCTET STRING,
            zxGponVoIPAppServiceProfileEntryStatus                  RowStatus
        }

    zxGponVoIPAppServiceProfileId OBJECT-TYPE
        SYNTAX      INTEGER
        MAX-ACCESS  read-only
        STATUS      current
        DESCRIPTION
        "This attribute provides a unique number for each instance of this managed entity.  
        (R, Set-by-create) (mandatory) (2 bytes)"
        REFERENCE   "G.983.2 section 7.3.113 VoIP Application Service Profile"
        ::= { zxGponVoIPAppServiceProfileEntry 1 }
        
    zxGponVoIPAppServiceProfileCIDFeature OBJECT-TYPE
        SYNTAX      INTEGER
        MAX-ACCESS  read-write
        STATUS      current
        DESCRIPTION
        "This attribute contains a bitmap of caller ID features. Bit clear is disabled 
        and bit set is enabled. The bit position values are:
        0x01 Calling Number
        0x02 Calling Name
        0x04 CID blocking (both number and name)
        0x08 CID number- Permanent presentation status for number (0 = Public, 1 = Private)
        0x10 CID name - Permanent presentation status for name (0 = Public, 1 = Private)
        0x20 Anonymous CID blocking (ACR) 
        0x40 - 0x80 not used
        The default value shall be disabled (0).  (R, W, Set-by-create) (mandatory) (1 byte) 
        "
        REFERENCE   "G.983.2 section 7.3.113 VoIP Application Service Profile"
        ::= { zxGponVoIPAppServiceProfileEntry 2 }
        
    zxGponVoIPAppServiceProfileCallWaitingFeature OBJECT-TYPE
        SYNTAX      INTEGER
        MAX-ACCESS  read-write
        STATUS      current
        DESCRIPTION
        "This attribute contains a bitmap of caller waiting features. Bit clear is disabled 
        and bit set is enabled. The bit position values are:
        0x01 call waiting
        0x02 Caller ID Announcement 
        0x04 - 0x80 not used
        The default value shall be disabled (0).  (R, W, Set-by-create) (mandatory) (1 byte)
        "
        REFERENCE   "G.983.2 section 7.3.113 VoIP Application Service Profile"
        ::= { zxGponVoIPAppServiceProfileEntry 3 }
       
     zxGponVoIPAppServiceProfileCallProgressFeature OBJECT-TYPE
        SYNTAX      INTEGER
        MAX-ACCESS  read-write
        STATUS      current
        DESCRIPTION
        "This attribute contains a bitmap of call processing features. Bit clear is disabled 
        and bit set is enabled. The bit position values are:
        0x0001 3way
        0x0002 call transfer
        0x0004 call hold 
        0x0008 call park
        0x0010 do not disturb
        0x0020 Flash on Emergency Service call. (Flash is to be processed during an Emergency Service call)
        0x0040 Emergency Service originating hold (determines if a call clearing is to be performed on an on-hook during an Emergency Service call)
        0x0080 6way
        0x0100 - 0x8000 not used
        The default value shall be disabled (0).  (R, W, Set-by-create) (mandatory) (2 bytes)
        "
        REFERENCE   "G.983.2 section 7.3.113 VoIP Application Service Profile"
        ::= { zxGponVoIPAppServiceProfileEntry 4 } 

    zxGponVoIPAppServiceProfileCallPresentationFeature OBJECT-TYPE
        SYNTAX      INTEGER
        MAX-ACCESS  read-write
        STATUS      current
        DESCRIPTION
        "This attribute contains a bitmap of call presentation features. Bit clear is disabled 
        and bit set is enabled. The bit position values are:
        0x0001 Message Waiting Indication Splash Ring
        0x0002 Message Waiting Indication Special Dial tone
        0x0004 Message Waiting Indication Visual Indication
        0x0008 Call Forwarding Indication
        0x0010 - 0x8000 not used
        The default value shall be disabled (0).  (R, W, Set-by-create) (mandatory) (2 bytes)
        "
        REFERENCE   "G.983.2 section 7.3.113 VoIP Application Service Profile"
        ::= { zxGponVoIPAppServiceProfileEntry 5 }
        
    zxGponVoIPAppServiceProfileDirectConnectFeature OBJECT-TYPE
        SYNTAX      INTEGER
        MAX-ACCESS  read-write
        STATUS      current
        DESCRIPTION
        "This attribute contains a bitmap of characteristics associated with the direct connect 
        feature. Bit clear is disabled and bit set is enabled. The bit position values are:
        0x01 direct connect feature enabled
        0x02 dial tone feature delay option
        The default value shall be disabled (0).  (R, W, Set-by-create) (mandatory) (1 byte)
        "
        REFERENCE   "G.983.2 section 7.3.113 VoIP Application Service Profile"
        ::= { zxGponVoIPAppServiceProfileEntry 6 }

    zxGponVoIPAppServiceProfileDirectConnectURI OBJECT-TYPE
        SYNTAX      OCTET STRING(SIZE(0..375))
        MAX-ACCESS  read-write
        STATUS      current
        DESCRIPTION
        "This attribute points to a Network Address managed entity. 
        If this attribute is set to 0xFFFF, no URI is defined. 
        If this attribute is set to any other value, it should point to a Network Address managed entity. Network Address ME indicates the URI of the Direct Connect.
        Default value is 0xFFFF. (R, W, Set-by-create) (mandatory) (2 bytes)
        "
        REFERENCE   "G.983.2 section 7.3.113 VoIP Application Service Profile"
        ::= { zxGponVoIPAppServiceProfileEntry 7 }
        
    zxGponVoIPAppServiceProfileBridgeLineAgentURI OBJECT-TYPE
        SYNTAX      OCTET STRING(SIZE(0..375))
        MAX-ACCESS  read-write
        STATUS      current
        DESCRIPTION
        "This attribute points to a Network Address managed entity. 
        If this attribute is set to 0xFFFF, no URI is defined. 
        If this attribute is set to any other value, it should point to a Network Address 
        managed entity. Network Address ME indicates the URI of the Bridged Line Agent.
        Default value is 0xFFFF. (R, W, Set-by-create) (mandatory) (2 bytes)
        "
        REFERENCE   "G.983.2 section 7.3.113 VoIP Application Service Profile"
        ::= { zxGponVoIPAppServiceProfileEntry 8 }
        
    zxGponVoIPAppServiceProfileConferenceFactoryURI OBJECT-TYPE
        SYNTAX      OCTET STRING(SIZE(0..375))
        MAX-ACCESS  read-write
        STATUS      current
        DESCRIPTION
        "This attribute points to a Network Address managed entity. 
        If this attribute is set to 0xFFFF, no URI is defined. 
        If this attribute is set to any other value, it should point to a Network Address 
        managed entity. Network Address ME indicates the URI of the Conference Factory.
        Default value is 0xFFFF. (R, W, Set-by-create) (mandatory) (2 bytes)
        "
        REFERENCE   "G.983.2 section 7.3.113 VoIP Application Service Profile"
        ::= { zxGponVoIPAppServiceProfileEntry 9 }

    zxGponVoIPAppServiceProfileEntryStatus OBJECT-TYPE
        SYNTAX      RowStatus
        MAX-ACCESS  read-write
        STATUS      current
        DESCRIPTION
        ""
        REFERENCE   "G.983.2 section 7.3.113 VoIP Application Service Profile"
        ::= { zxGponVoIPAppServiceProfileEntry 10 }

--VoIP Feature Access Codes
    zxGponVoIPFeatureAccessCodeTable    OBJECT-TYPE
        SYNTAX      SEQUENCE OF ZxGponVoIPFeatureAccessCodeEntry
        MAX-ACCESS  not-accessible
        STATUS      current
        DESCRIPTION
            "An instance of this managed entity is referenced by the SIP User Data ME."
        REFERENCE   "G.983.2 section 7.3.115 VoIP Feature Access Codes"
        ::= { zxGponL2Mgmt 49 }

    zxGponVoIPFeatureAccessCodeEntry OBJECT-TYPE
        SYNTAX      ZxGponVoIPFeatureAccessCodeEntry
        MAX-ACCESS  not-accessible
        STATUS      current
        DESCRIPTION
            "It is entry in the zxGponVoIPFeatureAccessCodeTable."
        INDEX   { zxGponOltIndex, zxGponONTIndex, zxGponVoIPFeatureAccessCodeId }
        ::= { zxGponVoIPFeatureAccessCodeTable 1 }
        
    ZxGponVoIPFeatureAccessCodeEntry ::=
        SEQUENCE {
            zxGponVoIPFeatureAccessCodeId                           INTEGER,
            zxGponVoIPFeatureAccessCodeCancelCallWaiting            OCTET STRING,
            zxGponVoIPFeatureAccessCodeCallHold                     OCTET STRING,
            zxGponVoIPFeatureAccessCodeCallPark                     OCTET STRING,
            zxGponVoIPFeatureAccessCodeCIDSActivate                 OCTET STRING,
            zxGponVoIPFeatureAccessCodeCIDSDeactivate               OCTET STRING,
            zxGponVoIPFeatureAccessCodeDoNotDisturbActivation       OCTET STRING,
            zxGponVoIPFeatureAccessCodeDoNotDisturbDeactivation     OCTET STRING,
            zxGponVoIPFeatureAccessCodeDoNotDisturbPINChange        OCTET STRING,
            zxGponVoIPFeatureAccessCodeEmergencyServiceNumber       OCTET STRING,
            zxGponVoIPFeatureAccessCodeIntercomService              OCTET STRING,
            zxGponVoIPFeatureAccessCodeEntryStatus                  RowStatus
        }

    zxGponVoIPFeatureAccessCodeId OBJECT-TYPE
        SYNTAX      INTEGER
        MAX-ACCESS  read-only
        STATUS      current
        DESCRIPTION
        "This attribute provides a unique number for each instance of this managed entity.  
        (R, Set-by-create) (mandatory) (2 bytes)"
        REFERENCE   "G.983.2 section 7.3.115 VoIP Feature Access Codes"
        ::= { zxGponVoIPFeatureAccessCodeEntry 1 }
        
    zxGponVoIPFeatureAccessCodeCancelCallWaiting OBJECT-TYPE
        SYNTAX      OCTET STRING(SIZE(5))
        MAX-ACCESS  read-write
        STATUS      current
        DESCRIPTION
        "This attribute defines the feature access code for cancel call waiting. (R, W) (optional) (5 bytes)"
        REFERENCE   "G.983.2 section 7.3.115 VoIP Feature Access Codes"
        ::= { zxGponVoIPFeatureAccessCodeEntry 2 }
        
    zxGponVoIPFeatureAccessCodeCallHold OBJECT-TYPE
        SYNTAX      OCTET STRING(SIZE(5))
        MAX-ACCESS  read-write
        STATUS      current
        DESCRIPTION
        "This attribute defines the feature access code for call hold. (R, W) (optional) (5 bytes)"
        REFERENCE   "G.983.2 section 7.3.115 VoIP Feature Access Codes"
        ::= { zxGponVoIPFeatureAccessCodeEntry 3 }
        
    zxGponVoIPFeatureAccessCodeCallPark OBJECT-TYPE
        SYNTAX      OCTET STRING(SIZE(5))
        MAX-ACCESS  read-write
        STATUS      current
        DESCRIPTION
        "This attribute defines the feature access code for call park. (R, W) (optional) (5 bytes)"
        REFERENCE   "G.983.2 section 7.3.115 VoIP Feature Access Codes"
        ::= { zxGponVoIPFeatureAccessCodeEntry 4 }

    zxGponVoIPFeatureAccessCodeCIDSActivate OBJECT-TYPE
        SYNTAX      OCTET STRING(SIZE(5))
        MAX-ACCESS  read-write
        STATUS      current
        DESCRIPTION
        "This attribute defines the feature access code for CIDS activate. (R, W) (optional) (5 bytes)"
        REFERENCE   "G.983.2 section 7.3.115 VoIP Feature Access Codes"
        ::= { zxGponVoIPFeatureAccessCodeEntry 5 }

    zxGponVoIPFeatureAccessCodeCIDSDeactivate OBJECT-TYPE
        SYNTAX      OCTET STRING(SIZE(5))
        MAX-ACCESS  read-write
        STATUS      current
        DESCRIPTION
        "This attribute defines the feature access code for CIDS deactivate. (R, W) (optional) (5 bytes)"
        REFERENCE   "G.983.2 section 7.3.115 VoIP Feature Access Codes"
        ::= { zxGponVoIPFeatureAccessCodeEntry 6 }
        
    zxGponVoIPFeatureAccessCodeDoNotDisturbActivation OBJECT-TYPE
        SYNTAX      OCTET STRING(SIZE(5))
        MAX-ACCESS  read-write
        STATUS      current
        DESCRIPTION
        "This attribute defines the feature access code to activate do not disturb. (R, W) (optional) (5 bytes)"
        REFERENCE   "G.983.2 section 7.3.115 VoIP Feature Access Codes"
        ::= { zxGponVoIPFeatureAccessCodeEntry 7 }

    zxGponVoIPFeatureAccessCodeDoNotDisturbDeactivation OBJECT-TYPE
        SYNTAX      OCTET STRING(SIZE(5))
        MAX-ACCESS  read-write
        STATUS      current
        DESCRIPTION
        "This attribute defines the feature access code to deactivate do not disturb. (R, W) (optional) (5 bytes)"
        REFERENCE   "G.983.2 section 7.3.115 VoIP Feature Access Codes"
        ::= { zxGponVoIPFeatureAccessCodeEntry 8 }

    zxGponVoIPFeatureAccessCodeDoNotDisturbPINChange OBJECT-TYPE
        SYNTAX      OCTET STRING(SIZE(5))
        MAX-ACCESS  read-write
        STATUS      current
        DESCRIPTION
        "This attribute defines the feature access code for do not disturb. (R, W) (optional) (5 bytes)"
        REFERENCE   "G.983.2 section 7.3.115 VoIP Feature Access Codes"
        ::= { zxGponVoIPFeatureAccessCodeEntry 9 }

    zxGponVoIPFeatureAccessCodeEmergencyServiceNumber OBJECT-TYPE
        SYNTAX      OCTET STRING(SIZE(5))
        MAX-ACCESS  read-write
        STATUS      current
        DESCRIPTION
        " This attribute defines the emergency service number. Example: 911 (R, W) (optional) (5 bytes)"
        REFERENCE   "G.983.2 section 7.3.115 VoIP Feature Access Codes"
        ::= { zxGponVoIPFeatureAccessCodeEntry 10 }

    zxGponVoIPFeatureAccessCodeIntercomService OBJECT-TYPE
        SYNTAX      OCTET STRING(SIZE(5))
        MAX-ACCESS  read-write
        STATUS      current
        DESCRIPTION
        "This attribute defines the feature access code for in home intercom service. (R, W) (optional) (5 bytes)"
        REFERENCE   "G.983.2 section 7.3.115 VoIP Feature Access Codes"
        ::= { zxGponVoIPFeatureAccessCodeEntry 11 }

    zxGponVoIPFeatureAccessCodeEntryStatus OBJECT-TYPE
        SYNTAX      RowStatus
        MAX-ACCESS  read-write
        STATUS      current
        DESCRIPTION
        ""
        REFERENCE   "G.983.2 section 7.3.115 VoIP Feature Access Codes"
        ::= { zxGponVoIPFeatureAccessCodeEntry 12 }

--VoIP Media Profile
    zxGponVoIPMediaProfileTable    OBJECT-TYPE
        SYNTAX      SEQUENCE OF ZxGponVoIPMediaProfileEntry
        MAX-ACCESS  not-accessible
        STATUS      current
        DESCRIPTION
            "An instance of this managed entity may be referenced by one or more VoIP Voice CTP managed entities."
        REFERENCE   "G.983.2 section 7.3.107 VoIP Media Profile"
        ::= { zxGponL2Mgmt 50 }

    zxGponVoIPMediaProfileEntry OBJECT-TYPE
        SYNTAX      ZxGponVoIPMediaProfileEntry
        MAX-ACCESS  not-accessible
        STATUS      current
        DESCRIPTION
            "It is entry in the zxGponVoIPMediaProfileTable."
        INDEX   { zxGponVoIPMediaProfileId }
        ::= { zxGponVoIPMediaProfileTable 1 }
        
    ZxGponVoIPMediaProfileEntry ::=
        SEQUENCE {
            zxGponVoIPMediaProfileId                                        INTEGER,
            zxGponVoIPMediaProfileName                                      OCTET STRING,
            zxGponVoIPMediaProfileFaxMode                                   INTEGER,
            zxGponVoIPMediaProfileFirstCodecSelection                       INTEGER,
            zxGponVoIPMediaProfileFirstPacketPeriodSelection                INTEGER,
            zxGponVoIPMediaProfileFirstSilenceSelection                     INTEGER,
            zxGponVoIPMediaProfileSecondCodecSelection                      INTEGER,
            zxGponVoIPMediaProfileSecondPacketPeriodSelection               INTEGER,
            zxGponVoIPMediaProfileSecondSilenceSelection                    INTEGER,
            zxGponVoIPMediaProfileThirdCodecSelection                       INTEGER,
            zxGponVoIPMediaProfileThirdPacketPeriodSelection                INTEGER,
            zxGponVoIPMediaProfileThirdSilenceSelection                     INTEGER,
            zxGponVoIPMediaProfileFourthCodecSelection                      INTEGER,
            zxGponVoIPMediaProfileFourthPacketPeriodSelection               INTEGER,
            zxGponVoIPMediaProfileFourthSilenceSelection                    INTEGER,
            zxGponVoIPMediaProfileOOBDTMF                                   INTEGER,
            zxGponVoiceServiceProfileAALAnnouncementType                    INTEGER,
            zxGponVoiceServiceProfileAALJitterTarget                        INTEGER,
            zxGponVoiceServiceProfileAALJitterBufMax                        INTEGER,
            zxGponVoiceServiceProfileAALEchoCancelInd                       TruthValue,
            zxGponVoiceServiceProfileAALPSTNVariant                         INTEGER,
            zxGponRTPProfileLocalPortMin                                    INTEGER,
            zxGponRTPProfileLocalPortMax                                    INTEGER,
            zxGponRTPProfileDSCPMark                                        INTEGER,
            zxGponRTPProfilePiggybackEvents                                 INTEGER,
            zxGponRTPProfileToneEvents                                      INTEGER,
            zxGponRTPProfileDTMFEvents                                      INTEGER,
            zxGponRTPProfileCASEvents                                       INTEGER,
            zxGponVoIPMediaProfileRefCnt                                    INTEGER,
            zxGponVoIPMediaProfileEntryStatus                               RowStatus
        }

    zxGponVoIPMediaProfileId OBJECT-TYPE
        SYNTAX      INTEGER
        MAX-ACCESS  not-accessible
        STATUS      current
        DESCRIPTION
        "This attribute provides a unique number for each instance of this managed entity.  
        (R, Set-by-create) (mandatory) (2 bytes)"
        REFERENCE   "G.983.2 section 7.3.107 VoIP Media Profile"
        ::= { zxGponVoIPMediaProfileEntry 1 }
        
    zxGponVoIPMediaProfileName OBJECT-TYPE
        SYNTAX      OCTET STRING(SIZE(1..63))
        MAX-ACCESS  read-write
        STATUS      current
        DESCRIPTION
        "This attribute provides a unique number for each instance of this managed entity.  
        (R, Set-by-create) (mandatory) (2 bytes)"
        REFERENCE   "G.983.2 section 7.3.107 VoIP Media Profile"
        ::= { zxGponVoIPMediaProfileEntry 2 }
        
    zxGponVoIPMediaProfileFaxMode OBJECT-TYPE
        SYNTAX      INTEGER{
                    passthru(1),
                    itu-t38(2)
                    }
        MAX-ACCESS  read-write
        STATUS      current
        DESCRIPTION
        "Selects the fax mode, values are 0 - passthru, 1 - ITU-T T.38. 
        Default value is 0 (R, W, Set-by-create) (mandatory) (1 byte)"
        REFERENCE   "G.983.2 section 7.3.107 VoIP Media Profile"
        ::= { zxGponVoIPMediaProfileEntry 3 }
        
    zxGponVoIPMediaProfileFirstCodecSelection OBJECT-TYPE
        SYNTAX      INTEGER{
                    pcmu(1),
                    gsm(4),
                    g723(5),
                    dvi4-rate8khz(6),
                    dvi4-rate16khz(7),
                    lpc(8),
                    pcma(9),
                    g722(10),
                    l16-2channel(11),
                    l16-1channel(12),
                    qcelp(13),
                    cn(14),
                    mpa(15),
                    g728(16),
                    dvi4-rate11khz(17),
                    dvi4-rate22khz(18),
                    g729(19)
                    }
        MAX-ACCESS  read-write
        STATUS      current
        DESCRIPTION
        "Specifies the codec selection  as defined by RFC 3551.  Default Value is 0-PCMU. (R,  W, Set-by-create) (mandatory) (1 byte)"
        REFERENCE   "G.983.2 section 7.3.107 VoIP Media Profile"
        ::= { zxGponVoIPMediaProfileEntry 4 }

    zxGponVoIPMediaProfileFirstPacketPeriodSelection OBJECT-TYPE
        SYNTAX      INTEGER
        MAX-ACCESS  read-write
        STATUS      current
        DESCRIPTION
        "This attribute selects the Packet Period Selection interval in milliseconds.  Default value is 10. Valid values are 10 - 30 ms. (R, W, Set-by-create) (mandatory) (1 byte)"
        REFERENCE   "G.983.2 section 7.3.107 VoIP Media Profile"
        ::= { zxGponVoIPMediaProfileEntry 5 }

    zxGponVoIPMediaProfileFirstSilenceSelection OBJECT-TYPE
        SYNTAX      INTEGER{
                    off(1),
                    on(2)
                    }
        MAX-ACCESS  read-write
        STATUS      current
        DESCRIPTION
        "This attribute indicates whether silence suppression is on or off.  Valid values are 0 = off and 1 = on.  (R, Set-by-create) (mandatory) (1 byte)"
        REFERENCE   "G.983.2 section 7.3.107 VoIP Media Profile"
        ::= { zxGponVoIPMediaProfileEntry 6 }
        
    zxGponVoIPMediaProfileSecondCodecSelection OBJECT-TYPE
        SYNTAX      INTEGER{
                    pcmu(1),
                    gsm(4),
                    g723(5),
                    dvi4-rate8khz(6),
                    dvi4-rate16khz(7),
                    lpc(8),
                    pcma(9),
                    g722(10),
                    l16-2channel(11),
                    l16-1channel(12),
                    qcelp(13),
                    cn(14),
                    mpa(15),
                    g728(16),
                    dvi4-rate11khz(17),
                    dvi4-rate22khz(18),
                    g729(19)
                    }
        MAX-ACCESS  read-write
        STATUS      current
        DESCRIPTION
        "Specifies the codec selection as defined by RFC 3551. Default Value is 0-PCMU. (R, W, Set-by-create) (mandatory) (1 byte)"
        REFERENCE   "G.983.2 section 7.3.107 VoIP Media Profile"
        ::= { zxGponVoIPMediaProfileEntry 7 }

    zxGponVoIPMediaProfileSecondPacketPeriodSelection OBJECT-TYPE
        SYNTAX      INTEGER
        MAX-ACCESS  read-write
        STATUS      current
        DESCRIPTION
        "This attribute selects the Packet Period Selection interval in milliseconds.  Default value is 10. Valid values are 10 - 30 ms. (R, W, Set-by-create) (mandatory) (1 byte)"
        REFERENCE   "G.983.2 section 7.3.107 VoIP Media Profile"
        ::= { zxGponVoIPMediaProfileEntry 8 }

    zxGponVoIPMediaProfileSecondSilenceSelection OBJECT-TYPE
        SYNTAX      INTEGER{
                    off(1),
                    on(2)
                    }
        MAX-ACCESS  read-write
        STATUS      current
        DESCRIPTION
        "This attribute indicates whether silence suppression is on or off.  Valid values are 0 = off and 1 = on.  (R, Set-by-create) (mandatory) (1 byte)"
        REFERENCE   "G.983.2 section 7.3.107 VoIP Media Profile"
        ::= { zxGponVoIPMediaProfileEntry 9 }

    zxGponVoIPMediaProfileThirdCodecSelection OBJECT-TYPE
        SYNTAX      INTEGER{
                    pcmu(1),
                    gsm(4),
                    g723(5),
                    dvi4-rate8khz(6),
                    dvi4-rate16khz(7),
                    lpc(8),
                    pcma(9),
                    g722(10),
                    l16-2channel(11),
                    l16-1channel(12),
                    qcelp(13),
                    cn(14),
                    mpa(15),
                    g728(16),
                    dvi4-rate11khz(17),
                    dvi4-rate22khz(18),
                    g729(19)
                    }
        MAX-ACCESS  read-write
        STATUS      current
        DESCRIPTION
        "Specifies the codec selection as defined by RFC 3551. Default Value is 0-PCMU. (R, W, Set-by-create) (mandatory) (1 byte)"
        REFERENCE   "G.983.2 section 7.3.107 VoIP Media Profile"
        ::= { zxGponVoIPMediaProfileEntry 10 }

    zxGponVoIPMediaProfileThirdPacketPeriodSelection OBJECT-TYPE
        SYNTAX      INTEGER
        MAX-ACCESS  read-write
        STATUS      current
        DESCRIPTION
        "This attribute selects the Packet Period Selection interval in milliseconds.  Default value is 10. Valid values are 10 - 30 ms. (R,  W, Set-by-create) (mandatory) (1 byte)"
        REFERENCE   "G.983.2 section 7.3.107 VoIP Media Profile"
        ::= { zxGponVoIPMediaProfileEntry 11 }

    zxGponVoIPMediaProfileThirdSilenceSelection OBJECT-TYPE
        SYNTAX      INTEGER{
                    off(1),
                    on(2)
                    }
        MAX-ACCESS  read-write
        STATUS      current
        DESCRIPTION
        "This attribute indicates whether silence suppression is on or off.  Valid values are 0 = off and 1 = on.  (R, Set-by-create) (mandatory) (1 byte)"
        REFERENCE   "G.983.2 section 7.3.107 VoIP Media Profile"
        ::= { zxGponVoIPMediaProfileEntry 12 }

    zxGponVoIPMediaProfileFourthCodecSelection OBJECT-TYPE
        SYNTAX      INTEGER{
                    pcmu(1),
                    gsm(4),
                    g723(5),
                    dvi4-rate8khz(6),
                    dvi4-rate16khz(7),
                    lpc(8),
                    pcma(9),
                    g722(10),
                    l16-2channel(11),
                    l16-1channel(12),
                    qcelp(13),
                    cn(14),
                    mpa(15),
                    g728(16),
                    dvi4-rate11khz(17),
                    dvi4-rate22khz(18),
                    g729(19)
                    }
        MAX-ACCESS  read-write
        STATUS      current
        DESCRIPTION
        "Specifies the codec selection as defined by RFC 3551. Default Value is 0-PCMU. (R, W, Set-by-create) (mandatory) (1 byte)"
        REFERENCE   "G.983.2 section 7.3.107 VoIP Media Profile"
        ::= { zxGponVoIPMediaProfileEntry 13 }

    zxGponVoIPMediaProfileFourthPacketPeriodSelection OBJECT-TYPE
        SYNTAX      INTEGER
        MAX-ACCESS  read-write
        STATUS      current
        DESCRIPTION
        "This attribute selects the Packet Period Selection interval in milliseconds.  Default value is 10. Valid values are 10 - 30 ms. (R, W, Set-by-create) (mandatory) (1 byte)"
        REFERENCE   "G.983.2 section 7.3.107 VoIP Media Profile"
        ::= { zxGponVoIPMediaProfileEntry 14 }

    zxGponVoIPMediaProfileFourthSilenceSelection OBJECT-TYPE
        SYNTAX      INTEGER{
                    off(1),
                    on(2)
                    }
        MAX-ACCESS  read-write
        STATUS      current
        DESCRIPTION
        "This attribute indicates whether silence suppression is on or off.  Valid values are 0 = off and 1 = on.  (R, Set-by-create) (mandatory) (1 byte)"
        REFERENCE   "G.983.2 section 7.3.107 VoIP Media Profile"
        ::= { zxGponVoIPMediaProfileEntry 15 }

    zxGponVoIPMediaProfileOOBDTMF OBJECT-TYPE
        SYNTAX      INTEGER{
                    disable(1),
                    enable(2)
                    }
        MAX-ACCESS  read-write
        STATUS      current
        DESCRIPTION
        "This attribute defines the Out-of-band DMTF Enable. When enabled (value = 1) , DTMF tones are carried out of band via RTP or the associated signaling protocol. When disabled (value = 0), DTMF tones are carried in the PCM. Default value of 1. (R, W, Set-by-create) (mandatory) (1 byte)"
        REFERENCE   "G.983.2 section 7.3.107 VoIP Media Profile"
        ::= { zxGponVoIPMediaProfileEntry 16 }

    zxGponVoiceServiceProfileAALAnnouncementType OBJECT-TYPE
        SYNTAX      INTEGER{
                    silence(1),
                    reorderTone(2),
                    fastBusy(3),
                    voiceAnnounce(4),
                    na(5)
                    }
        MAX-ACCESS  read-write
        STATUS      current
        DESCRIPTION
        "This attribute provides the announcement to the customer going off-hook when no call has been attempted."
        REFERENCE   "G.983.2 section 7.3.24 Voice service profile AAL"
        ::= { zxGponVoIPMediaProfileEntry 17 }

    zxGponVoiceServiceProfileAALJitterTarget OBJECT-TYPE
        SYNTAX      INTEGER
        MAX-ACCESS  read-write
        STATUS      current
        DESCRIPTION
        "This attribute provides the target value of the jitter buffer. The system will try to maintain the jitter buffer at the target value. 
        Units are in milliseconds. (R, W, Set-by-create) (mandatory for AAL2) (2 bytes)"
        REFERENCE   "G.983.2 section 7.3.24 Voice service profile AAL"
        ::= { zxGponVoIPMediaProfileEntry 18 }

    zxGponVoiceServiceProfileAALJitterBufMax OBJECT-TYPE
        SYNTAX      INTEGER
        MAX-ACCESS  read-write
        STATUS      current
        DESCRIPTION
        "This attribute provides the maximum depth of the jitter buffer associated with this service. 
        Units are in milliseconds. (R, W, Set-by-create) (mandatory for AAL 2) (2 bytes)"
        REFERENCE   "G.983.2 section 7.3.24 Voice service profile AAL"
        ::= { zxGponVoIPMediaProfileEntry 19 }

    zxGponVoiceServiceProfileAALEchoCancelInd OBJECT-TYPE
        SYNTAX      TruthValue
        MAX-ACCESS  read-write
        STATUS      current
        DESCRIPTION
        "This Boolean attribute indicates whether echo cancellation is on or off, 
        where the value TRUE implies that it is on. (R, Set-by-create) (mandatory) (1 byte)"
        REFERENCE   "G.983.2 section 7.3.24 Voice service profile AAL"
        ::= { zxGponVoIPMediaProfileEntry 20 }
        
    zxGponVoiceServiceProfileAALPSTNVariant OBJECT-TYPE
        SYNTAX      INTEGER
        MAX-ACCESS  read-write
        STATUS      current
        DESCRIPTION
        "This attribute controls which variant of POTS signalling shall be used on the associated UNIs. 
        The value used is equal to the 'country code'. (R, Set-by-Create) (optional) (2 bytes)"
        REFERENCE   "G.983.2 section 7.3.24 Voice service profile AAL"
        ::= { zxGponVoIPMediaProfileEntry 21 }
        
    zxGponRTPProfileLocalPortMin OBJECT-TYPE
        SYNTAX      INTEGER
        MAX-ACCESS  read-write
        STATUS      current
        DESCRIPTION
        "This attribute defines the base RTP port that should be used for voice traffic. 
        Default is 50000 (R, W, Set-by-create) (mandatory) (2 bytes)"
        REFERENCE   "G.983.2 section 7.3.108 RTP Profile Data"
        ::= { zxGponVoIPMediaProfileEntry 22 }

    zxGponRTPProfileLocalPortMax OBJECT-TYPE
        SYNTAX      INTEGER
        MAX-ACCESS  read-write
        STATUS      current
        DESCRIPTION
        "This attribute defines the top end range RTP port used for voice traffic. 
        Default must be greater than LocalPortMin but is determined by vendor application. (R, W, Set-by-create) (optional) (2 bytes)"
        REFERENCE   "G.983.2 section 7.3.108 RTP Profile Data"
        ::= { zxGponVoIPMediaProfileEntry 23 }

    zxGponRTPProfileDSCPMark OBJECT-TYPE
        SYNTAX      INTEGER
        MAX-ACCESS  read-write
        STATUS      current
        DESCRIPTION
        "Diffserv code point to be used for outgoing RTP packets for this profile. 
        Default value is Expedited Forwarding (EF) = 0x2E (0b00101110).  (R, W, Set-by-create) (mandatory) (1 byte)"
        REFERENCE   "G.983.2 section 7.3.108 RTP Profile Data"
        ::= { zxGponVoIPMediaProfileEntry 24 }

    zxGponRTPProfilePiggybackEvents OBJECT-TYPE
        SYNTAX      INTEGER{
                    disable(1),
                    enable(2)
                    }
        MAX-ACCESS  read-write
        STATUS      current
        DESCRIPTION
        "Enables or disables RTP piggyback events. 0x0 = Disabled. 0x1 = Enabled. 
        Default value is Disabled (0x0).  (R, W, Set-by-create) (mandatory) (1 byte)"
        REFERENCE   "G.983.2 section 7.3.108 RTP Profile Data"
        ::= { zxGponVoIPMediaProfileEntry 25 }
        
    zxGponRTPProfileToneEvents OBJECT-TYPE
        SYNTAX      INTEGER{
                    disable(1),
                    enable(2)
                    }
        MAX-ACCESS  read-write
        STATUS      current
        DESCRIPTION
        "Enables or disables handling of tones via RTP Tone Events per RFC2833. 0x0 = Disabled. 0x1 = Enabled. 
        Default value is Disabled (0x0).  (R, W, Set-by-create) (mandatory) (1 byte)"
        REFERENCE   "G.983.2 section 7.3.108 RTP Profile Data"
        ::= { zxGponVoIPMediaProfileEntry 26 }

    zxGponRTPProfileDTMFEvents OBJECT-TYPE
        SYNTAX      INTEGER{
                    disable(1),
                    enable(2)
                    }
        MAX-ACCESS  read-write
        STATUS      current
        DESCRIPTION
        "Enables or disables handling of DTMF via RTP DTMF Events per RFC2833. 
        This attribute is ignored unless the OOB DTMF attribute in the VoIP Media Profile ME is set to enabled. 0x0 = Disabled. 0x1 = Enabled. 
        Default value is Disabled (0x0).  (R, W, Set-by-create) (mandatory) (1 byte)"
        REFERENCE   "G.983.2 section 7.3.108 RTP Profile Data"
        ::= { zxGponVoIPMediaProfileEntry 27 }

    zxGponRTPProfileCASEvents OBJECT-TYPE
        SYNTAX      INTEGER{
                    disable(1),
                    enable(2)
                    }
        MAX-ACCESS  read-write
        STATUS      current
        DESCRIPTION
        "Enables or disables handling of CAS via RTP CAS Events per RFC2833. 0x0 = Disabled. 0x1 = Enabled. 
        Default value is Disabled (0x0).  (R, W, Set-by-create) (mandatory) (1 byte)"
        REFERENCE   "G.983.2 section 7.3.108 RTP Profile Data"
        ::= { zxGponVoIPMediaProfileEntry 28 }

    zxGponVoIPMediaProfileRefCnt OBJECT-TYPE
        SYNTAX      INTEGER
        MAX-ACCESS  read-only
        STATUS      current
        DESCRIPTION
        "Forbidden to modify table entry if not equal zero."
        REFERENCE   "G.983.2 section 7.3.108 RTP Profile Data"
        ::= { zxGponVoIPMediaProfileEntry 29 }

    zxGponVoIPMediaProfileEntryStatus OBJECT-TYPE
        SYNTAX      RowStatus
        MAX-ACCESS  read-write
        STATUS      current
        DESCRIPTION
        ""
        REFERENCE   "G.983.2 section 7.3.107 VoIP Media Profile"
        ::= { zxGponVoIPMediaProfileEntry 30 }

--Voice service profile AAL

--RTP Profile Data

--SIP Agent Profile
    zxGponSIPAgentProfileTable    OBJECT-TYPE
        SYNTAX      SEQUENCE OF ZxGponSIPAgentProfileEntry
        MAX-ACCESS  not-accessible
        STATUS      current
        DESCRIPTION
            ""
        REFERENCE   ""
        ::= { zxGponL2Mgmt 51 }

    zxGponSIPAgentProfileEntry OBJECT-TYPE
        SYNTAX      ZxGponSIPAgentProfileEntry
        MAX-ACCESS  not-accessible
        STATUS      current
        DESCRIPTION
            "It is entry in the zxGponSIPAgentProfileTable."
        INDEX   { zxGponSIPAgentProfileId }
        ::= { zxGponSIPAgentProfileTable 1 }
        
    ZxGponSIPAgentProfileEntry ::=
        SEQUENCE {
            zxGponSIPAgentProfileId                                        INTEGER,
            zxGponSIPAgentProfileName                                      OCTET STRING,
            zxGponSIPAgentProfileProxyServer                               OCTET STRING,
            zxGponSIPAgentProfileOutboundProxy                             OCTET STRING,
            zxGponSIPAgentProfileRegServer                                 OCTET STRING,
            zxGponSIPAgentProfilePrimaryDNS                                IpAddress,
            zxGponSIPAgentProfileSecondaryDNS                              IpAddress,
            zxGponSIPAgentProfileTCPUDPPort                                INTEGER,
            zxGponSIPAgentProfileHostId                                    INTEGER,
            zxGponSIPAgentProfileRefCnt                                    INTEGER,
            zxGponSIPAgentProfileEntryStatus                               RowStatus
        }

    zxGponSIPAgentProfileId OBJECT-TYPE
        SYNTAX      INTEGER
        MAX-ACCESS  not-accessible
        STATUS      current
        DESCRIPTION ""
        REFERENCE   ""
        ::= { zxGponSIPAgentProfileEntry 1 }
        
    zxGponSIPAgentProfileName OBJECT-TYPE
        SYNTAX      OCTET STRING(SIZE(1..64))
        MAX-ACCESS  read-write
        STATUS      current
        DESCRIPTION ""
        REFERENCE   ""
        ::= { zxGponSIPAgentProfileEntry 2 }
        
    zxGponSIPAgentProfileProxyServer OBJECT-TYPE
        SYNTAX      OCTET STRING(SIZE(0..128))
        MAX-ACCESS  read-write
        STATUS      current
        DESCRIPTION ""
        REFERENCE   ""
        ::= { zxGponSIPAgentProfileEntry 3 }

    zxGponSIPAgentProfileOutboundProxy OBJECT-TYPE
        SYNTAX      OCTET STRING(SIZE(0..128))
        MAX-ACCESS  read-write
        STATUS      current
        DESCRIPTION ""
        REFERENCE   ""
        ::= { zxGponSIPAgentProfileEntry 4 }

    zxGponSIPAgentProfileRegServer OBJECT-TYPE
        SYNTAX      OCTET STRING(SIZE(0..128))
        MAX-ACCESS  read-write
        STATUS      current
        DESCRIPTION ""
        REFERENCE   ""
        ::= { zxGponSIPAgentProfileEntry 5 }

    zxGponSIPAgentProfilePrimaryDNS OBJECT-TYPE
        SYNTAX      IpAddress
        MAX-ACCESS  read-write
        STATUS      current
        DESCRIPTION ""
        REFERENCE   ""
        ::= { zxGponSIPAgentProfileEntry 6 }

    zxGponSIPAgentProfileSecondaryDNS OBJECT-TYPE
        SYNTAX      IpAddress
        MAX-ACCESS  read-write
        STATUS      current
        DESCRIPTION ""
        REFERENCE   ""
        ::= { zxGponSIPAgentProfileEntry 7 }

    zxGponSIPAgentProfileTCPUDPPort OBJECT-TYPE
        SYNTAX      INTEGER
        MAX-ACCESS  read-write
        STATUS      current
        DESCRIPTION ""
        REFERENCE   ""
        ::= { zxGponSIPAgentProfileEntry 8 }

    zxGponSIPAgentProfileHostId OBJECT-TYPE
        SYNTAX      INTEGER
        MAX-ACCESS  read-write
        STATUS      current
        DESCRIPTION ""
        REFERENCE   ""
        ::= { zxGponSIPAgentProfileEntry 9 }

    zxGponSIPAgentProfileRefCnt OBJECT-TYPE
        SYNTAX      INTEGER
        MAX-ACCESS  read-only
        STATUS      current
        DESCRIPTION ""
        REFERENCE   ""
        ::= { zxGponSIPAgentProfileEntry 10 }

    zxGponSIPAgentProfileEntryStatus OBJECT-TYPE
        SYNTAX      RowStatus
        MAX-ACCESS  read-write
        STATUS      current
        DESCRIPTION ""
        REFERENCE   ""
        ::= { zxGponSIPAgentProfileEntry 30 }

--SIP
    zxGponSIPTable    OBJECT-TYPE
        SYNTAX      SEQUENCE OF ZxGponSIPEntry
        MAX-ACCESS  not-accessible
        STATUS      current
        DESCRIPTION
            ""
        REFERENCE   ""
        ::= { zxGponL2Mgmt 52 }

    zxGponSIPEntry OBJECT-TYPE
        SYNTAX      ZxGponSIPEntry
        MAX-ACCESS  not-accessible
        STATUS      current
        DESCRIPTION
            "It is entry in the zxGponSIPTable."
        INDEX   { zxGponOltIndex, zxGponONTIndex, zxGponUNIIndex }
        ::= { zxGponSIPTable 1 }
        
    ZxGponSIPEntry ::=
        SEQUENCE {
            zxGponSIPAgentProfilePtr                           INTEGER,
            zxGponSIPUserPartAOR                               OCTET STRING,
            zxGponSIPUserName                                  OCTET STRING,
            zxGponSIPPassword                                  OCTET STRING,
            zxGponSIPEntryStatus                               RowStatus
        }

    zxGponSIPAgentProfilePtr OBJECT-TYPE
        SYNTAX      INTEGER
        MAX-ACCESS  read-write
        STATUS      current
        DESCRIPTION ""
        REFERENCE   ""
        ::= { zxGponSIPEntry 1 }
        
    zxGponSIPUserPartAOR OBJECT-TYPE
        SYNTAX      OCTET STRING(SIZE(0..128))
        MAX-ACCESS  read-write
        STATUS      current
        DESCRIPTION ""
        REFERENCE   ""
        ::= { zxGponSIPEntry 2 }

    zxGponSIPUserName OBJECT-TYPE
        SYNTAX      OCTET STRING(SIZE(0..25))
        MAX-ACCESS  read-write
        STATUS      current
        DESCRIPTION ""
        REFERENCE   ""
        ::= { zxGponSIPEntry 3 }

    zxGponSIPPassword OBJECT-TYPE
        SYNTAX      OCTET STRING(SIZE(0..25))
        MAX-ACCESS  read-write
        STATUS      current
        DESCRIPTION ""
        REFERENCE   ""
        ::= { zxGponSIPEntry 4 }

    zxGponSIPEntryStatus OBJECT-TYPE
        SYNTAX      RowStatus
        MAX-ACCESS  read-write
        STATUS      current
        DESCRIPTION ""
        REFERENCE   ""
        ::= { zxGponSIPEntry 30 }
                              
    --G.983.2 7.3.49 VLAN tagging operation configuration data
    zxGponIPHostVLANTagOperConfigTable    OBJECT-TYPE
        SYNTAX      SEQUENCE OF ZxGponIPHostVLANTagOperConfigEntry
        MAX-ACCESS  not-accessible
        STATUS      current
        DESCRIPTION
            "This managed entity is used to organize data associated with VLAN tagging. 
            Instances of this managed entity are created/deleted at the request of the OLT.
            Zero or one instance of this managed entity may exist for each instance of 
            IP Host."
        REFERENCE   "G.983.2 section 7.3.49 VLAN tagging operation configuration data"
        ::= { zxGponL2Mgmt 60 }

    zxGponIPHostVLANTagOperConfigEntry OBJECT-TYPE
        SYNTAX      ZxGponIPHostVLANTagOperConfigEntry
        MAX-ACCESS  not-accessible
        STATUS      current
        DESCRIPTION
            "It is entry in the zxGponIPHostVLANTagOperConfigTable."
        INDEX   { zxGponOltIndex, zxGponONTIndex, zxGponIPHostConfigDataId }
        ::= { zxGponIPHostVLANTagOperConfigTable 1 }
        
    ZxGponIPHostVLANTagOperConfigEntry ::=
        SEQUENCE {
            zxGponIPHostVLANTagOperConfigUpTagOperMode           INTEGER,
            zxGponIPHostVLANTagOperConfigUpTagTCIVal             INTEGER,
            zxGponIPHostVLANTagOperConfigDownTagOperMode         INTEGER,
            zxGponIPHostVLANTagOperConfigEntryStatus             RowStatus
        }

    zxGponIPHostVLANTagOperConfigUpTagOperMode OBJECT-TYPE
        SYNTAX      INTEGER{
                    transparent(1),
                    overwrite(2),
                    add(3)
                    }
        MAX-ACCESS  read-write
        STATUS      current
        DESCRIPTION
        "This attribute selects how upstream VLAN tagging is sent.  
        Valid values are:
        0x00 (upstream frame is sent 'as is,' regardless of whether or not the received frame is tagged)  
        0x01 (The upstream frame is sent as tagged whether or not the received frame is tagged.  TCI, consisting of VID, CFI and user priority, is attached or overwritten by using the Upstream VLAN Tag TCI Value.). 
        0x02 (The upstream frame is sent as tagged whether or not the received frame is tagged.  If the received frame is tagged, a second tag (Q-n-Q) is added to the frame. If the received frame is not tagged a tag is attached to the frame. TCI, consisting of VID, CFI and user priority, is attached or added by using the Upstream VLAN Tag TCI Value.).
       (1 byte)"
        REFERENCE   "G.983.2 section 7.3.49 VLAN tagging operation configuration data"
        ::= { zxGponIPHostVLANTagOperConfigEntry 1 }
        
    zxGponIPHostVLANTagOperConfigUpTagTCIVal OBJECT-TYPE
        SYNTAX      INTEGER
        MAX-ACCESS  read-write
        STATUS      current
        DESCRIPTION
        "This attribute indicates the TCI value for upstream VLAN tagging. It is used when the Upstream VLAN Tagging Operation Mode is 0x01. Any 2-byte value is acceptable.(2 bytes)"
        REFERENCE   "G.983.2 section 7.3.49 VLAN tagging operation configuration data"
        ::= { zxGponIPHostVLANTagOperConfigEntry 2 }
        
    zxGponIPHostVLANTagOperConfigDownTagOperMode OBJECT-TYPE
        SYNTAX      INTEGER{
                    transparent(1),
                    untag(2)
                    }
        MAX-ACCESS  read-write
        STATUS      current
        DESCRIPTION
        "This attribute selects whether or not downstream VLAN tagging is sent. 
        Valid values are 0x00 (downstream frame is sent 'as is', regardless of whether or not the received frame is tagged) 
        and 0x01 (The downstream frame is sent as untagged whether or not the received frame is tagged).(1 byte)"
        REFERENCE   "G.983.2 section 7.3.49 VLAN tagging operation configuration data"
        ::= { zxGponIPHostVLANTagOperConfigEntry 3 }
        
    zxGponIPHostVLANTagOperConfigEntryStatus OBJECT-TYPE
        SYNTAX      RowStatus
        MAX-ACCESS  read-write
        STATUS      current
        DESCRIPTION
        "This attribute selects whether or not downstream VLAN tagging is sent. 
        Valid values are 0x00 (downstream frame is sent 'as is', regardless of whether or not the received frame is tagged) 
        and 0x01 (The downstream frame is sent as untagged whether or not the received frame is tagged).(1 byte)"
        REFERENCE   "G.983.2 section 7.3.49 VLAN tagging operation configuration data"
        ::= { zxGponIPHostVLANTagOperConfigEntry 4 }
        
        
    --G.983.2 7.3.33 MAC Bridge port filter table data
    --for IP Host
    zxGponIPHostBridgePortMacFilterTable    OBJECT-TYPE
        SYNTAX      SEQUENCE OF ZxGponIPHostBridgePortMacFilterEntry
        MAX-ACCESS  not-accessible
        STATUS      current
        DESCRIPTION
            "This managed entity is used to organize and record data that is associated with 
            a bridge port. Some of the data is volatile.
            This managed entity is associated with one instance of a MACBridgePortConfigurationData."
        REFERENCE   "G.983.2 section 7.3.33 MAC Bridge port filter table data"
        ::= { zxGponL2Mgmt 61 }

    zxGponIPHostBridgePortMacFilterEntry OBJECT-TYPE
        SYNTAX      ZxGponIPHostBridgePortMacFilterEntry
        MAX-ACCESS  not-accessible
        STATUS      current
        DESCRIPTION
            "It is entry in the zxGponIPHostBridgePortMacFilterTable."
        INDEX   { zxGponOltIndex, zxGponONTIndex, zxGponIPHostConfigDataId, zxGponIPHostBridgePortMacFilterAddress }
        ::= { zxGponIPHostBridgePortMacFilterTable 1 }

    ZxGponIPHostBridgePortMacFilterEntry ::=
        SEQUENCE {
            zxGponIPHostBridgePortMacFilterAddress                 MacAddress,
            zxGponIPHostBridgePortMacFilterFilterMode              INTEGER,
            zxGponIPHostBridgePortMacFilterEntryStatus             RowStatus
        }

    zxGponIPHostBridgePortMacFilterAddress OBJECT-TYPE
        SYNTAX      MacAddress
        MAX-ACCESS  read-only
        STATUS      current
        DESCRIPTION
        "This attribute specifies the MAC address being filtered."
        REFERENCE   "G.983.2 section 7.3.33 MAC Bridge port filter table data"
        ::= { zxGponIPHostBridgePortMacFilterEntry 1 }
        
    zxGponIPHostBridgePortMacFilterFilterMode OBJECT-TYPE
        SYNTAX      INTEGER{
                    forward(1),
                    discard(2)
                    }
        MAX-ACCESS  read-write
        STATUS      current
        DESCRIPTION
        "This attribute specifies the filter action."
        REFERENCE   "G.983.2 section 7.3.33 MAC Bridge port filter table data"
        ::= { zxGponIPHostBridgePortMacFilterEntry 2 }
        
    zxGponIPHostBridgePortMacFilterEntryStatus OBJECT-TYPE
        SYNTAX      RowStatus
        MAX-ACCESS  read-write
        STATUS      current
        DESCRIPTION
        "This attribute specifies the operation of this entry."
        REFERENCE   "G.983.2 section 7.3.33 MAC Bridge port filter table data"
        ::= { zxGponIPHostBridgePortMacFilterEntry 3 }

--G.983.2 7.3.51 MAC Bridge port filter preassign table
--for IP Host
    zxGponIPHostMACBridgePortEthFrameFilterTable    OBJECT-TYPE
        SYNTAX      SEQUENCE OF ZxGponIPHostMACBridgePortEthFrameFilterEntry
        MAX-ACCESS  not-accessible
        STATUS      current
        DESCRIPTION
            "This managed entity provides an alternate approach to address filtering than that 
            supported through MACBridgePortFilterTableData.
            This managed entity is associated with one instance of a MACBridgePortConfigurationData managed entity."
        REFERENCE   "G.983.2 section 7.3.51 MAC Bridge port filter preassign table"
        ::= { zxGponL2Mgmt 62 }

    zxGponIPHostMACBridgePortEthFrameFilterEntry OBJECT-TYPE
        SYNTAX      ZxGponIPHostMACBridgePortEthFrameFilterEntry
        MAX-ACCESS  not-accessible
        STATUS      current
        DESCRIPTION
            "It is entry in the zxGponIPHostMACBridgePortEthFrameFilterTable."
        INDEX   { zxGponOltIndex, zxGponONTIndex, zxGponIPHostConfigDataId }
        ::= { zxGponIPHostMACBridgePortEthFrameFilterTable 1 }
        
    ZxGponIPHostMACBridgePortEthFrameFilterEntry ::=
        SEQUENCE {
            zxGponIPHostMACBridgePortEthFrameFilterIPv4MCFilter            INTEGER,
            zxGponIPHostMACBridgePortEthFrameFilterIPv6MCFilter            INTEGER,
            zxGponIPHostMACBridgePortEthFrameFilterIPv4BCFilter            INTEGER,
            zxGponIPHostMACBridgePortEthFrameFilterRARPFilter              INTEGER,
            zxGponIPHostMACBridgePortEthFrameFilterIPXFilter               INTEGER,
            zxGponIPHostMACBridgePortEthFrameFilterNetBEUIFilter           INTEGER,
            zxGponIPHostMACBridgePortEthFrameFilterAppleTalkFilter         INTEGER,
            zxGponIPHostMACBridgePortEthFrameFilterBPDUFilter              INTEGER,
            zxGponIPHostMACBridgePortEthFrameFilterARPFilter               INTEGER,
            zxGponIPHostMACBridgePortEthFrameFilterPPPoEFilter             INTEGER
        }

    zxGponIPHostMACBridgePortEthFrameFilterIPv4MCFilter OBJECT-TYPE
        SYNTAX      INTEGER{
                    forward(1),
                    discard(2)
                    }
        MAX-ACCESS  read-write
        STATUS      current
        DESCRIPTION
        "This attribute indicates whether IPv4Multicast Ether types are forwarded (value 0x00) 
        or filtered (value 0x01). Initial value is 0x00.(1 byte)"
        REFERENCE   "G.983.2 section 7.3.51 MAC Bridge port filter preassign table"
        ::= { zxGponIPHostMACBridgePortEthFrameFilterEntry 1 }
        
    zxGponIPHostMACBridgePortEthFrameFilterIPv6MCFilter OBJECT-TYPE
        SYNTAX      INTEGER{
                    forward(1),
                    discard(2)
                    }
        MAX-ACCESS  read-write
        STATUS      current
        DESCRIPTION
        "This attribute indicates whether Ipv6Multicast Ether types are forwarded (value 0x00) 
        or filtered (value 0x01). Initial value is 0x00.(1 byte)"
        REFERENCE   "G.983.2 section 7.3.51 MAC Bridge port filter preassign table"
        ::= { zxGponIPHostMACBridgePortEthFrameFilterEntry 2 }
        
    zxGponIPHostMACBridgePortEthFrameFilterIPv4BCFilter OBJECT-TYPE
        SYNTAX      INTEGER{
                    forward(1),
                    discard(2)
                    }
        MAX-ACCESS  read-write
        STATUS      current
        DESCRIPTION
        "This attribute indicates whether IPv4Broadcast Ether types are forwarded (value 0x00) 
        or filtered (value 0x01). Initial value is 0x00.(1 byte)"
        REFERENCE   "G.983.2 section 7.3.51 MAC Bridge port filter preassign table"
        ::= { zxGponIPHostMACBridgePortEthFrameFilterEntry 3 }

    zxGponIPHostMACBridgePortEthFrameFilterRARPFilter OBJECT-TYPE
        SYNTAX      INTEGER{
                    forward(1),
                    discard(2)
                    }
        MAX-ACCESS  read-write
        STATUS      current
        DESCRIPTION
        "This attribute indicates whether RARP Ether types are forwarded (value 0x00) 
        or filtered (value 0x01). Initial value is 0x00.(1 byte)"
        REFERENCE   "G.983.2 section 7.3.51 MAC Bridge port filter preassign table"
        ::= { zxGponIPHostMACBridgePortEthFrameFilterEntry 4 }

    zxGponIPHostMACBridgePortEthFrameFilterIPXFilter OBJECT-TYPE
        SYNTAX      INTEGER{
                    forward(1),
                    discard(2)
                    }
        MAX-ACCESS  read-write
        STATUS      current
        DESCRIPTION
        "This attribute indicates whether IPX Ether types are forwarded (value 0x00) 
        or filtered (value 0x01). Initial value is 0x00.(1 byte)"
        REFERENCE   "G.983.2 section 7.3.51 MAC Bridge port filter preassign table"
        ::= { zxGponIPHostMACBridgePortEthFrameFilterEntry 5 }

    zxGponIPHostMACBridgePortEthFrameFilterNetBEUIFilter OBJECT-TYPE
        SYNTAX      INTEGER{
                    forward(1),
                    discard(2)
                    }
        MAX-ACCESS  read-write
        STATUS      current
        DESCRIPTION
        "This attribute indicates whether NetBEUI Ether types are forwarded (value 0x00) 
        or filtered (value 0x01). Initial value is 0x00.(1 byte)"
        REFERENCE   "G.983.2 section 7.3.51 MAC Bridge port filter preassign table"
        ::= { zxGponIPHostMACBridgePortEthFrameFilterEntry 6 }

    zxGponIPHostMACBridgePortEthFrameFilterAppleTalkFilter OBJECT-TYPE
        SYNTAX      INTEGER{
                    forward(1),
                    discard(2)
                    }
        MAX-ACCESS  read-write
        STATUS      current
        DESCRIPTION
        "This attribute indicates whether AppleTalk Ether types are forwarded (value 0x00) 
        or filtered (value 0x01). Initial value is 0x00.(1 byte)"
        REFERENCE   "G.983.2 section 7.3.51 MAC Bridge port filter preassign table"
        ::= { zxGponIPHostMACBridgePortEthFrameFilterEntry 7 }

    zxGponIPHostMACBridgePortEthFrameFilterBPDUFilter OBJECT-TYPE
        SYNTAX      INTEGER{
                    forward(1),
                    discard(2)
                    }
        MAX-ACCESS  read-write
        STATUS      current
        DESCRIPTION
        "This attribute indicates whether BridgeManagementInformation Ether types are 
        forwarded (value 0x00) or filtered (value 0x01). Initial value is 0x00.(1 byte)"
        REFERENCE   "G.983.2 section 7.3.51 MAC Bridge port filter preassign table"
        ::= { zxGponIPHostMACBridgePortEthFrameFilterEntry 8 }

    zxGponIPHostMACBridgePortEthFrameFilterARPFilter OBJECT-TYPE
        SYNTAX      INTEGER{
                    forward(1),
                    discard(2)
                    }
        MAX-ACCESS  read-write
        STATUS      current
        DESCRIPTION
        "This attribute indicates whether ARP Ether types are forwarded (value 0x00) 
        or filtered (value 0x01). Initial value is 0x00.(1 byte)"
        REFERENCE   "G.983.2 section 7.3.51 MAC Bridge port filter preassign table"
        ::= { zxGponIPHostMACBridgePortEthFrameFilterEntry 9 }
        
    zxGponIPHostMACBridgePortEthFrameFilterPPPoEFilter OBJECT-TYPE
        SYNTAX      INTEGER{
                    forward(1),
                    discard(2)
                    }
        MAX-ACCESS  read-write
        STATUS      current
        DESCRIPTION
        "This attribute indicates whether PPPoE Ether types are forwarded (value 0x00) 
        or filtered (value 0x01). Initial value is 0x00.(1 byte)"
        REFERENCE   "G.983.2 section 7.3.51 MAC Bridge port filter preassign table"
        ::= { zxGponIPHostMACBridgePortEthFrameFilterEntry 10 }

--Filter...
--G.983.2 7.3.50 VLAN tagging filter data
--for IP Host
    zxGponIPHostVLANTagFilterModeTable    OBJECT-TYPE
        SYNTAX      SEQUENCE OF ZxGponIPHostVLANTagFilterModeEntry
        MAX-ACCESS  not-accessible
        STATUS      current
        DESCRIPTION
            "This managed entity is used to organize data associated with VLAN tagging. 
            Instances of this managed entity are created/deleted at the request of the OLT.
            Zero or one instance of this managed entity may exist for each instance of MAC 
            Bridge Port Configuration Data which is associated with Interworking VCC Termination 
            Point (PON side) or Physical Path Termination Point Ethernet UNI."
        REFERENCE   "G.983.2 section 7.3.50 VLAN tagging filter data"
        ::= { zxGponL2Mgmt 63 }

    zxGponIPHostVLANTagFilterModeEntry OBJECT-TYPE
        SYNTAX      ZxGponIPHostVLANTagFilterModeEntry
        MAX-ACCESS  not-accessible
        STATUS      current
        DESCRIPTION
            "It is entry in the zxGponIPHostVLANTagFilterModeTable."
        INDEX   { zxGponOltIndex, zxGponONTIndex, zxGponIPHostConfigDataId }
        ::= { zxGponIPHostVLANTagFilterModeTable 1 }
        
    ZxGponIPHostVLANTagFilterModeEntry ::=
        SEQUENCE {
            zxGponIPHostVLANTagFilterModeForwardOper             INTEGER,
            zxGponIPHostVLANTagFilterModeEntryStatus             RowStatus
        }

    zxGponIPHostVLANTagFilterModeForwardOper OBJECT-TYPE
        SYNTAX      INTEGER{
                    mode0(1),
                    mode1(2),
                    mode2(3),
                    mode3(4),
                    mode4(5),
                    mode5(6),
                    mode6(7),
                    mode7(8),
                    mode8(9),
                    mode9(10),
                    mode10(11),
                    mode11(12),
                    mode12(13),
                    mode13(14),
                    mode14(15)
                    }
        MAX-ACCESS  read-write
        STATUS      current
        DESCRIPTION
        "When a frame is received, the frame is processed according to the following Forward 
        Operations. The operations are invoked based on the value of VID, user priority, or 
        the entire TCI or whether or not the TCI field exists. This attribute indicates the 
        received frame is treated as indicated below.(1 byte)
        !!!!!!mode5/6/9/10 is no used currently!!!!!!! 
        tag-filter-action      untag-filter-action      forward-mode
        'transparent'          'transparent'            'mode0'
        'discard'              'transparent'            'mode1'
        'transparent'          'discard'                'mode2'
        'vid-filter'           'transparent'            'mode3'
        'vid-filter'           'discard'                'mode4'
        'prio-filter'          'transparent'            'mode7'
        'prio-filter'          'discard'                'mode8'
        'prio-vid-filter'      'transparent'            'mode11'
        'prio-vid-filter'      'discard'                'mode12'
        "
        REFERENCE   "G.983.2 section 7.3.50 VLAN tagging filter data"
        ::= { zxGponIPHostVLANTagFilterModeEntry 1 }
        
    zxGponIPHostVLANTagFilterModeEntryStatus OBJECT-TYPE
        SYNTAX      RowStatus
        MAX-ACCESS  read-write
        STATUS      current
        DESCRIPTION
        "This attribute provides the number of entries in the VLAN Filter Table that are valid.(1 byte)"
        REFERENCE   "G.983.2 section 7.3.50 VLAN tagging filter data"
        ::= { zxGponIPHostVLANTagFilterModeEntry 2 }

    zxGponIPHostVLANTagFilterTable    OBJECT-TYPE
        SYNTAX      SEQUENCE OF ZxGponIPHostVLANTagFilterEntry
        MAX-ACCESS  not-accessible
        STATUS      current
        DESCRIPTION
            "This managed entity is used to organize data associated with VLAN tagging. 
            Instances of this managed entity are created/deleted at the request of the OLT.
            Zero or one instance of this managed entity may exist for each instance of MAC 
            Bridge Port Configuration Data which is associated with Interworking VCC Termination 
            Point (PON side) or Physical Path Termination Point Ethernet UNI."
        REFERENCE   "G.983.2 section 7.3.50 VLAN tagging filter data"
        ::= { zxGponL2Mgmt 64 }

    zxGponIPHostVLANTagFilterEntry OBJECT-TYPE
        SYNTAX      ZxGponIPHostVLANTagFilterEntry
        MAX-ACCESS  not-accessible
        STATUS      current
        DESCRIPTION
            "It is entry in the zxGponIPHostVLANTagFilterTable."
        INDEX   { zxGponOltIndex, zxGponONTIndex, zxGponIPHostConfigDataId, zxGponIPHostVLANTagFilterTCI }
        ::= { zxGponIPHostVLANTagFilterTable 1 }
        
    ZxGponIPHostVLANTagFilterEntry ::=
        SEQUENCE {
            zxGponIPHostVLANTagFilterTCI                     INTEGER,
            zxGponIPHostVLANTagFilterEntryStatus             RowStatus
        }

    zxGponIPHostVLANTagFilterTCI OBJECT-TYPE
        SYNTAX      INTEGER
        MAX-ACCESS  read-write
        STATUS      current
        DESCRIPTION
        "This attribute specifies the TCI value which is provisioned at a bridging port.(2 bytes)"
        REFERENCE   "G.983.2 section 7.3.50 VLAN tagging filter data"
        ::= { zxGponIPHostVLANTagFilterEntry 1 }
        
    zxGponIPHostVLANTagFilterEntryStatus OBJECT-TYPE
        SYNTAX      RowStatus
        MAX-ACCESS  read-write
        STATUS      current
        DESCRIPTION
        "This attribute provides the number of entries in the VLAN Filter Table that are valid.(1 byte)"
        REFERENCE   "G.983.2 section 7.3.50 VLAN tagging filter data"
        ::= { zxGponIPHostVLANTagFilterEntry 2 }

                              
    zxGponDot1xTable    OBJECT-TYPE
        SYNTAX      SEQUENCE OF ZxGponDot1xEntry
        MAX-ACCESS  not-accessible
        STATUS      current
        DESCRIPTION
        "An instance of this managed entity represents a set of attributes that control 
        an ONT's IEEE 802.1X operation with regard to IEEE 802 services."
        REFERENCE   "G.984.4 9.3.15    Dot1X configuration profile"
        ::= { zxGponL2Mgmt 70 }

    zxGponDot1xEntry OBJECT-TYPE
        SYNTAX      ZxGponDot1xEntry
        MAX-ACCESS  not-accessible
        STATUS      current
        DESCRIPTION
            "It is entry in the zxGponDot1xTable."
        INDEX   { zxGponOltIndex, zxGponONTIndex }
        ::= { zxGponDot1xTable 1 }
        
    ZxGponDot1xEntry ::=
        SEQUENCE {
            zxGponDot1xCIDPrefix                 OCTET STRING,
            zxGponDot1xFallbackPolicy            INTEGER,
            zxGponDot1xAuthServer1               OCTET STRING,
            zxGponDot1xSharedSecretAuth1         OCTET STRING,
            zxGponDot1xAuthServer2               OCTET STRING,
            zxGponDot1xSharedSecretAuth2         OCTET STRING,
            zxGponDot1xAuthServer3               OCTET STRING,
            zxGponDot1xSharedSecretAuth3         OCTET STRING,
            zxGponDot1xOLTProxyAddress           IpAddress
        }

    zxGponDot1xCIDPrefix OBJECT-TYPE
        SYNTAX      OCTET STRING(SIZE(0..128))
        MAX-ACCESS  read-write
        STATUS      current
        DESCRIPTION
        "This attribute is a large string whose content appears as the prefix of the NAS port ID in radius access-request messages."
        REFERENCE   ""
        ::= { zxGponDot1xEntry 1 }
        
    zxGponDot1xFallbackPolicy OBJECT-TYPE
        SYNTAX      INTEGER{
                    succeed(1),
                    deny(2)
                    }
        MAX-ACCESS  read-write
        STATUS      current
        DESCRIPTION
        "When set to 2 (deny), this attribute causes 802.1X conversations to fail when no external authentication server is accessible, 
         such that no Ethernet service is provided. 
         The default value 1 (succeed) causes 802.1X conversations to succeed when no external authentication server is accessible."
        REFERENCE   ""
        ::= { zxGponDot1xEntry 2 }
        
    zxGponDot1xAuthServer1 OBJECT-TYPE
        SYNTAX      OCTET STRING(SIZE(0..128))
        MAX-ACCESS  read-write
        STATUS      current
        DESCRIPTION
        "This attribute is a large string that contains the URI of the first choice radius authentication server.
         The null string indicates that no radius authentication server is specified."
        REFERENCE   ""
        ::= { zxGponDot1xEntry 3 }

    zxGponDot1xSharedSecretAuth1 OBJECT-TYPE
        SYNTAX      OCTET STRING(SIZE(0..25))
        MAX-ACCESS  read-write
        STATUS      current
        DESCRIPTION
        "This attribute is the shared secret for the first radius authentication server. It is a null-terminated character string."
        REFERENCE   ""
        ::= { zxGponDot1xEntry 4 }

    zxGponDot1xAuthServer2 OBJECT-TYPE
        SYNTAX      OCTET STRING(SIZE(0..128))
        MAX-ACCESS  read-write
        STATUS      current
        DESCRIPTION
        "This attribute is a large string that contains the URI of the second choice radius authentication server.
         The null string indicates that no radius authentication server is specified."
        REFERENCE   ""
        ::= { zxGponDot1xEntry 5 }

    zxGponDot1xSharedSecretAuth2 OBJECT-TYPE
        SYNTAX      OCTET STRING(SIZE(0..25))
        MAX-ACCESS  read-write
        STATUS      current
        DESCRIPTION
        "This attribute is the shared secret for the second radius authentication server. It is a null-terminated character string."
        REFERENCE   ""
        ::= { zxGponDot1xEntry 6 }

    zxGponDot1xAuthServer3 OBJECT-TYPE
        SYNTAX      OCTET STRING(SIZE(0..128))
        MAX-ACCESS  read-write
        STATUS      current
        DESCRIPTION
        "This attribute is a large string that contains the URI of the third choice radius authentication server.
         The null string indicates that no radius authentication server is specified."
        REFERENCE   ""
        ::= { zxGponDot1xEntry 7 }

    zxGponDot1xSharedSecretAuth3 OBJECT-TYPE
        SYNTAX      OCTET STRING(SIZE(0..25))
        MAX-ACCESS  read-write
        STATUS      current
        DESCRIPTION
        "This attribute is the shared secret for the third radius authentication server. It is a null-terminated character string."
        REFERENCE   ""
        ::= { zxGponDot1xEntry 8 }

    zxGponDot1xOLTProxyAddress OBJECT-TYPE
        SYNTAX      IpAddress
        MAX-ACCESS  read-write
        STATUS      current
        DESCRIPTION
        "This attribute indicates the IP address of a possible proxy at the OLT for 802.1X radius messages. The default value 0.0.0.0 indicates that no proxy is required."
        REFERENCE   ""
        ::= { zxGponDot1xEntry 9 }

    zxGponPortDot1xTable    OBJECT-TYPE
        SYNTAX      SEQUENCE OF ZxGponPortDot1xEntry
        MAX-ACCESS  not-accessible
        STATUS      current
        DESCRIPTION
        "An instance of this managed entity represents a set of attributes that control a port's IEEE 802.1X operation.
         An instance of this managed entity is associated with a physical path termination point that performs IEEE 802 
         authentication (ie Ethernet or DSL)."
        REFERENCE   "9.3.14    Dot1X port extension package"
        ::= { zxGponL2Mgmt 71 }

    zxGponPortDot1xEntry OBJECT-TYPE
        SYNTAX      ZxGponPortDot1xEntry
        MAX-ACCESS  not-accessible
        STATUS      current
        DESCRIPTION
            "It is entry in the zxGponPortDot1xTable."
        INDEX   { zxGponOltIndex, zxGponONTIndex, zxGponPortDot1xUniType, zxGponUNIIndex }
        ::= { zxGponPortDot1xTable 1 }
        
    ZxGponPortDot1xEntry ::=
        SEQUENCE {
            zxGponPortDot1xUniType                     INTEGER,
            zxGponPortDot1xEnable                      TruthValue,
            zxGponPortDot1xAuthPAEState                INTEGER,
            zxGponPortDot1xBackendAuthState            INTEGER,
            zxGponPortDot1xAdminCtrlDirection          INTEGER,
            zxGponPortDot1xOperCtrlDirection           INTEGER,
            zxGponPortDot1xAuthCtrlPortStatus          INTEGER,
            zxGponPortDot1xQuietPeriod                 INTEGER,
            zxGponPortDot1xServerTimeoutPeriod         INTEGER,
            zxGponPortDot1xReAuthPeriod                INTEGER,
            zxGponPortDot1xReAuthEnable                TruthValue,
            zxGponPortDot1xKeyTxEnable                 TruthValue
        }

    zxGponPortDot1xUniType OBJECT-TYPE
        SYNTAX      INTEGER
        MAX-ACCESS  not-accessible
        STATUS      current
        DESCRIPTION
        "This index indicates the type of interface.
            1 eth uni
            2 dsl uni
         Currently, only ethuni is supported."
        REFERENCE   ""
        ::= { zxGponPortDot1xEntry 1 }
        
    zxGponPortDot1xEnable OBJECT-TYPE
        SYNTAX      TruthValue
        MAX-ACCESS  read-write
        STATUS      current
        DESCRIPTION
        "If set true, this boolean attribute forces the associated port to authenticate via 802.1X as a precondition of normal service. 
         The default value false does not impose 802.1X authentication on the associated port."
        REFERENCE   ""
        ::= { zxGponPortDot1xEntry 2 }
        
    zxGponPortDot1xAuthPAEState OBJECT-TYPE
        SYNTAX      INTEGER{
                    initialize(1),
                    disconnected(2),
                    connecting(3),
                    authenticating(4),
                    authenticated(5),
                    aborting(6),
                    held(7),
                    forceauth(8),
                    forceunauth(9),
                    restart(10)
                    }
        MAX-ACCESS  read-only
        STATUS      current
        DESCRIPTION
        "This attribute returns the value of the port's PAE state. States are further described in IEEE 802.1X.
         0xFFFF means NA"
        REFERENCE   ""
        ::= { zxGponPortDot1xEntry 3 }

    zxGponPortDot1xBackendAuthState OBJECT-TYPE
        SYNTAX      INTEGER{
                    request(1),
                    response(2),
                    success(3),
                    fail(4),
                    timeout(5),
                    idle(6),
                    initialize(7),
                    ignore(8)
                    }
        MAX-ACCESS  read-only
        STATUS      current
        DESCRIPTION
        "This attribute returns the value of the port's back-end authentication state. States are further described in IEEE 802.1X.
         0xFFFF means NA"
        REFERENCE   ""
        ::= { zxGponPortDot1xEntry 4 }

    zxGponPortDot1xAdminCtrlDirection OBJECT-TYPE
        SYNTAX      INTEGER{
                    both(1),
                    upstream(2)
                    }
        MAX-ACCESS  read-write
        STATUS      current
        DESCRIPTION
        "This attribute controls the directionality of the port's authentication requirement. 
         The default value 1 (both) indicates that control is imposed in both directions. 
         The value 2 (upstream) indicates that control is imposed only on traffic from the subscriber toward the network."
        REFERENCE   ""
        ::= { zxGponPortDot1xEntry 5 }

    zxGponPortDot1xOperCtrlDirection OBJECT-TYPE
        SYNTAX      INTEGER{
                    both(1),
                    upstream(2)
                    }
        MAX-ACCESS  read-only
        STATUS      current
        DESCRIPTION
        "This attribute indicates the actual directionality of the port's authentication. 
         The value 1 (both) indicates that control is imposed in both directions. 
         The value 2 (upstream) indicates that control is imposed only on traffic from the subscriber toward the network. 
         0xFFFF means NA"
        REFERENCE   ""
        ::= { zxGponPortDot1xEntry 6 }

    zxGponPortDot1xAuthCtrlPortStatus OBJECT-TYPE
        SYNTAX      INTEGER{
                    authorized(1),
                    unauthorized(2)
                    }
        MAX-ACCESS  read-only
        STATUS      current
        DESCRIPTION
        "This read-only attribute indicates whether the controlled port is currently authorized (1) or unauthorized (2).
         0xFFFF means NA"
        REFERENCE   ""
        ::= { zxGponPortDot1xEntry 7 }

    zxGponPortDot1xQuietPeriod OBJECT-TYPE
        SYNTAX      INTEGER(0..65535)
        MAX-ACCESS  read-write
        STATUS      current
        DESCRIPTION
        "This attribute specifies the interval between EAP request/identity invitations sent to the peer. 
         Other events such as carrier present or EAPOL start frames from the peer may trigger an EAP request/identity frame from the ONT at any time; 
         this attribute controls the ONT's periodic behaviour in the absence of these other inputs. It is expressed in seconds."
        REFERENCE   ""
        ::= { zxGponPortDot1xEntry 8 }

    zxGponPortDot1xServerTimeoutPeriod OBJECT-TYPE
        SYNTAX      INTEGER(0..65535)
        MAX-ACCESS  read-write
        STATUS      current
        DESCRIPTION
        "This attribute specifies the time the ONT will wait for a response from the radius server before timing out. 
         Within this maximum interval, the ONT may initiate several retransmissions with exponentially increasing delay. 
         Upon timeout, the ONT may try another radius server if there is one, or invoke the fallback policy, if no alternate radius servers are available. 
         Server timeout is expressed in seconds, with a default value of 30 and a maximum value of 65535 seconds."
        REFERENCE   ""
        ::= { zxGponPortDot1xEntry 9 }

    zxGponPortDot1xReAuthPeriod OBJECT-TYPE
        SYNTAX      INTEGER(0..65535)
        MAX-ACCESS  read-only
        STATUS      current
        DESCRIPTION
        "This attribute records the reauthentication interval specified by the radius authentication server. 
         It is expressed in seconds. The attribute is only meaningful after a port has been authenticated. "
        REFERENCE   ""
        ::= { zxGponPortDot1xEntry 10 }

    zxGponPortDot1xReAuthEnable OBJECT-TYPE
        SYNTAX      TruthValue
        MAX-ACCESS  read-only
        STATUS      current
        DESCRIPTION
        "This boolean attribute records whether the radius authentication server has enabled reauthentication on this service (true) or not (false). 
         The attribute is only meaningful after a port has been authenticated."
        REFERENCE   ""
        ::= { zxGponPortDot1xEntry 11 }

    zxGponPortDot1xKeyTxEnable OBJECT-TYPE
        SYNTAX      TruthValue
        MAX-ACCESS  read-write
        STATUS      current
        DESCRIPTION
        "This boolean attribute indicates whether key transmission is enabled (true) or not (false). 
         This feature is not required; the parameter is listed here for completeness vis-a-vis 802.1X."
        REFERENCE   ""
        ::= { zxGponPortDot1xEntry 12 }

    zxGponPortDot1xRegisterActionTable    OBJECT-TYPE
        SYNTAX      SEQUENCE OF ZxGponPortDot1xRegisterActionEntry
        MAX-ACCESS  not-accessible
        STATUS      current
        DESCRIPTION
        "This table defines a set of actions that can be performed on the port
         associated with a physical path termination point that performs IEEE 802 authentication (ie Ethernet or DSL)."
        REFERENCE   "9.3.14    Dot1X port extension package"
        ::= { zxGponL2Mgmt 72 }

    zxGponPortDot1xRegisterActionEntry OBJECT-TYPE
        SYNTAX      ZxGponPortDot1xRegisterActionEntry
        MAX-ACCESS  not-accessible
        STATUS      current
        DESCRIPTION
            "It is entry in the zxGponPortDot1xRegisterActionTable."
        INDEX   { zxGponOltIndex, zxGponONTIndex, zxGponPortDot1xUniType, zxGponUNIIndex }
        ::= { zxGponPortDot1xRegisterActionTable 1 }
        
    ZxGponPortDot1xRegisterActionEntry ::=
        SEQUENCE {
            zxGponPortDot1xRegisterAction              INTEGER
        }

    zxGponPortDot1xRegisterAction OBJECT-TYPE
        SYNTAX      INTEGER{
                    force-reauth(1),
                    force-unauth(2),
                    force-auth(3)
                    }
        MAX-ACCESS  read-write
        STATUS      current
        DESCRIPTION
        "This attribute defines a set of actions that can be performed on the associated port. 
         The act of writing to the register causes the specified action.
         1 Force reauthentication - this opcode initiates an 802.1X reauthentication conversation with the associated port. 
           The port remains in its currently authorized state until the conversation concludes.
         2 Force unauthenticated - this opcode initiates an 802.1X authentication conversation whose outcome is predestined to fail, 
           thereby disabling normal Ethernet service on the port. The port's provisioning is not changed, such that upon reinitialization, a new 802.1X conversation may restore service without prejudice.
         3 Force authenticated - this opcode initiates an 802.1X authentication conversation whose outcome is predestined to succeed, 
           thereby unconditionally enabling normal Ethernet service on the port. The port's provisioning is not changed, such that upon reinitialization, a new 802.1X conversation is required."
        REFERENCE   ""
        ::= { zxGponPortDot1xRegisterActionEntry 1 }



  zxGponDscp2CosProfileTable    OBJECT-TYPE
        SYNTAX      SEQUENCE OF ZxGponDscp2CosProfileEntry
        MAX-ACCESS  not-accessible
        STATUS      current
        DESCRIPTION
            "This attribute specifies the profile that mapping from DSCP to P-bits."
        REFERENCE   "G.984.4 9.3.13 Extended VLAN tagging operation configuration data"
        ::= {zxGponL2Mgmt 73}
        
    zxGponDscp2CosProfileEntry OBJECT-TYPE
        SYNTAX      ZxGponDscp2CosProfileEntry
        MAX-ACCESS  not-accessible
        STATUS      current
        DESCRIPTION
            "It is entry in the zxGponDscp2CosProfileEntry."
        INDEX   {zxGponDscp2CosProfileId }
        ::= { zxGponDscp2CosProfileTable 1 }
    
    ZxGponDscp2CosProfileEntry ::=
        SEQUENCE {
            zxGponDscp2CosProfileId              INTEGER,
            zxGponDscp2CosProfileName            DisplayString,
            zxGponDscp2CosMapping                OCTET STRING,
            zxGponDscp2CosProfileRefCnt          INTEGER,
            zxGponDscp2CosProfileEntryStatus     RowStatus
        }
        
    zxGponDscp2CosProfileId OBJECT-TYPE
        SYNTAX      INTEGER
        MAX-ACCESS  not-accessible
        STATUS      current
        DESCRIPTION
        "This attribute provides a unique number for each instance of this managed entity.  
        (R, Set-by-create) (mandatory) (4 bytes)"
        ::= { zxGponDscp2CosProfileEntry 1 }
        
    zxGponDscp2CosProfileName OBJECT-TYPE
        SYNTAX      DisplayString(SIZE(1..63))
        MAX-ACCESS  read-create
        STATUS      current
        DESCRIPTION
        "This attribute provides a unique name for each instance of this managed entity.  
        (R, Set-by-create) (mandatory) (2 bytes)"       
        ::= { zxGponDscp2CosProfileEntry 2}   
        
    zxGponDscp2CosMapping OBJECT-TYPE 
        SYNTAX      OCTET STRING(SIZE(1..24))
        MAX-ACCESS  read-create
        STATUS      current
        DESCRIPTION
        "This attribute specifies mapping from DSCP to P-bits. 
        The attribute can be considered a bit string sequence of 64 3-bit groups. 
        The 64 sequence entries represent the possible values of the 6-bit DSCP field. 
        Each 3-bit group specifies the P-bit value to which the associated DSCP value should be mapped."
        REFERENCE   "G.984.4 9.3.13 Extended VLAN tagging operation configuration data"
        ::= { zxGponDscp2CosProfileEntry 3 }    
          
    zxGponDscp2CosProfileRefCnt OBJECT-TYPE
        SYNTAX      INTEGER
        MAX-ACCESS  read-only
        STATUS      current
        DESCRIPTION
        "Forbidden to delete table entry if not equal zero."
        ::= { zxGponDscp2CosProfileEntry 4 }
             
    zxGponDscp2CosProfileEntryStatus OBJECT-TYPE
        SYNTAX      RowStatus
        MAX-ACCESS  read-create
        STATUS      current
        DESCRIPTION
        "This attribute specifies the action of this entry."
        REFERENCE   "G.984.4 9.3.13 Extended VLAN tagging operation configuration data"
        ::= { zxGponDscp2CosProfileEntry 10 }
        
   
--connection management

--unicast interworking
    zxGponInterworkTable    OBJECT-TYPE
        SYNTAX      SEQUENCE OF ZxGponInterworkEntry
        MAX-ACCESS  not-accessible
        STATUS      current
        DESCRIPTION
            ""
        REFERENCE   "G.984.4 & G.983.2"
        ::= { zxGponConnectMgmt 2 }
        
    zxGponInterworkEntry OBJECT-TYPE
        SYNTAX      ZxGponInterworkEntry
        MAX-ACCESS  not-accessible
        STATUS      current
        DESCRIPTION
            "It is entry in the zxGponInterworkTable."
        INDEX   { zxGponOltIndex, zxGponONTIndex, zxGponGemPortIndex }
        ::= { zxGponInterworkTable 1 }

    ZxGponInterworkEntry ::=
        SEQUENCE {
            zxGponInterworkOption                        INTEGER,
            zxGponInterworkIfId                          INTEGER,
            zxGponInterworkIfType                        INTEGER,
            zxGponInterworkUniList                       OCTET STRING,
            zxGponInterworkUniNum                        INTEGER,
            zxGponInterworkPrioBitMap                    INTEGER,
            zxGponInterworkMaxPayloadSize                INTEGER,
            zxGponInterworkFrameLossIntPeriod            INTEGER,
            zxGponInterworkCesBufCDVTolerance            INTEGER,
            zxGponInterworkChannelSignal                 INTEGER,
            zxGponInterworkPptpCounter                   INTEGER,
            zxGponInterworkOperState                     INTEGER,
            zxGponInterworkEntryStatus                   RowStatus
        }

    zxGponInterworkOption OBJECT-TYPE
        SYNTAX      INTEGER{
                    unstructuredTdm(1),
                    bridge(2),
                    ipData(3),
                    videoReturnPath(4),
                    dot1p(5),
                    dot1pBridge(6),
                    uni(7)
                    }
        MAX-ACCESS  read-write
        STATUS      current
        DESCRIPTION
        "This attribute specifies the interworking option.
        'bridge', 'dot1p', 'dot1pBridge' are supported at present."
        REFERENCE   "G.984.4 & G.983.2"
        ::= { zxGponInterworkEntry 1 }

    zxGponInterworkIfId OBJECT-TYPE
        SYNTAX      INTEGER
        MAX-ACCESS  read-write
        STATUS      current
        DESCRIPTION
        "This attribute provides the interface id associated with this interworking.
        It stands for the  UNI index(slot/port) or the uplink index(slot/bridge/port).
        (4 bytes)"
        REFERENCE   "G.984.4 & G.983.2"
        ::= { zxGponInterworkEntry 2 }

    zxGponInterworkIfType OBJECT-TYPE
        SYNTAX      INTEGER{
                    ethUni(1),
                    potsUni(2),
                    cesUni(3),
                    uplink(5)
                    }
        MAX-ACCESS  read-write
        STATUS      current
        DESCRIPTION
        "This attribute specifies the interface type associated with this interworking.(2 bytes)"
        REFERENCE   "G.984.4 & G.983.2"
        ::= { zxGponInterworkEntry 3 }
        
    zxGponInterworkUniList OBJECT-TYPE
        SYNTAX      OCTET STRING(SIZE(64))
        MAX-ACCESS  read-write
        STATUS      current
        DESCRIPTION
        "This attribute provides the uni list(each four bytes stand for a certain uni index) associated with 
        this interworking when 'zxGponInterworkOption' equals uni(7).
        (4 bytes)"
        REFERENCE   "G.984.4 & G.983.2"
        ::= { zxGponInterworkEntry 4 }

    zxGponInterworkUniNum OBJECT-TYPE
        SYNTAX      INTEGER
        MAX-ACCESS  read-write
        STATUS      current
        DESCRIPTION
        "This attribute specifies the uni number in the uni list."
        REFERENCE   "G.984.4 & G.983.2"
        ::= { zxGponInterworkEntry 5 }

    zxGponInterworkPrioBitMap OBJECT-TYPE
        SYNTAX      INTEGER
        MAX-ACCESS  read-write
        STATUS      current
        DESCRIPTION
        "This bitmap specifies the priorities used by this connection when using 802.1p mapping.
        Each bit from bit0(LSB) to bit7(MSB) indicates whether priority0~priority7 is occupied.(1 byte)"
        REFERENCE   "G.984.4 & G.983.2"
        ::= { zxGponInterworkEntry 6 }

    zxGponInterworkMaxPayloadSize OBJECT-TYPE
        SYNTAX      INTEGER
        MAX-ACCESS  read-write
        STATUS      current
        DESCRIPTION
        "This attribute specifies the maximum GEM payload size associated with GAL Eth profile.(2 bytes)"
        REFERENCE   "G.984.4 & G.983.2"
        ::= { zxGponInterworkEntry 7 }

    zxGponInterworkFrameLossIntPeriod OBJECT-TYPE
        SYNTAX      INTEGER
        MAX-ACCESS  read-write
        STATUS      current
        DESCRIPTION
        "This attribute specifies the maximum GEM frame loss intergration period associated with GAL TDM profile.(2 bytes)"
        REFERENCE   "G.984.4 & G.983.2"
        ::= { zxGponInterworkEntry 8 }

    zxGponInterworkCesBufCDVTolerance OBJECT-TYPE
        SYNTAX      INTEGER
        MAX-ACCESS  read-write
        STATUS      current
        DESCRIPTION
        "This attribute specifies the CES buffer CDV tolerance of CES service profile.(2 bytes)"
        REFERENCE   "G.984.4 & G.983.2"
        ::= { zxGponInterworkEntry 9 }

    zxGponInterworkChannelSignal OBJECT-TYPE
        SYNTAX      INTEGER{
                    basic(1),
                    e1Cas(2),
                    sfCas(3),
                    ds1EsfCas(4),
                    j2Cas(5)
                    }
        MAX-ACCESS  read-write
        STATUS      current
        DESCRIPTION
        "This attribute specifies the channel signal of CES service profile.(2 bytes)"
        REFERENCE   "G.984.4 & G.983.2"
        ::= { zxGponInterworkEntry 10 }
        
    zxGponInterworkPptpCounter OBJECT-TYPE
        SYNTAX      INTEGER
        MAX-ACCESS  read-only
        STATUS      current
        DESCRIPTION
        "This attribute indicates the PPTP counter associated with this interworking.(1 byte)"
        REFERENCE   "G.984.4 & G.983.2"
        ::= { zxGponInterworkEntry 11 }
        
    zxGponInterworkOperState OBJECT-TYPE
        SYNTAX      INTEGER{
                    enable(1),
                    disable(2)
                    }
        MAX-ACCESS  read-only
        STATUS      current
        DESCRIPTION
        "This attribute indicates the operation state of this interworking.(1 byte)"
        REFERENCE   "G.984.4 & G.983.2"
        ::= { zxGponInterworkEntry 12 }

    zxGponInterworkEntryStatus OBJECT-TYPE
        SYNTAX      RowStatus
        MAX-ACCESS  read-write
        STATUS      current
        DESCRIPTION
        "This attribute specifies the action of this interworking."
        REFERENCE   "G.984.4 & G.983.2"
        ::= { zxGponInterworkEntry 13 }


--multicast interworking
    zxGponMcInterworkTable    OBJECT-TYPE
        SYNTAX      SEQUENCE OF ZxGponMcInterworkEntry
        MAX-ACCESS  not-accessible
        STATUS      current
        DESCRIPTION
            ""
        REFERENCE   "G.984.4 & G.983.2"
        ::= { zxGponConnectMgmt 3 }
        
    zxGponMcInterworkEntry OBJECT-TYPE
        SYNTAX      ZxGponMcInterworkEntry
        MAX-ACCESS  not-accessible
        STATUS      current
        DESCRIPTION
            "It is entry in the zxGponMcInterworkTable."
        INDEX   { zxGponOltIndex, zxGponONTIndex, zxGponGemPortIndex }
        ::= { zxGponMcInterworkTable 1 }

    ZxGponMcInterworkEntry ::=
        SEQUENCE {
            zxGponMcInterworkOption                        INTEGER,
            zxGponMcInterworkIfId                          INTEGER,
            zxGponMcInterworkIfType                        INTEGER,
            zxGponMcInterworkMaxPayloadSize                INTEGER,
            zxGponMcInterworkPptpCounter                   INTEGER,
            zxGponMcInterworkOperState                     INTEGER,
            zxGponMcInterworkEntryStatus                   RowStatus
        }

    zxGponMcInterworkOption OBJECT-TYPE
        SYNTAX      INTEGER{
                    bridge(2)
                    }
        MAX-ACCESS  read-write
        STATUS      current
        DESCRIPTION
        "This attribute specifies the multicast interworking option.
        Only 'bridge' is supported at present."
        REFERENCE   "G.984.4 & G.983.2"
        ::= { zxGponMcInterworkEntry 1 }

    zxGponMcInterworkIfId OBJECT-TYPE
        SYNTAX      INTEGER
        MAX-ACCESS  read-write
        STATUS      current
        DESCRIPTION
        "This attribute provides the interface id associated with this interworking.
        It stands for the uplink index(slot/bridge/port).
        (4 bytes)"
        REFERENCE   "G.984.4 & G.983.2"
        ::= { zxGponMcInterworkEntry 2 }

    zxGponMcInterworkIfType OBJECT-TYPE
        SYNTAX      INTEGER{
                    uplink(5)
                    }
        MAX-ACCESS  read-write
        STATUS      current
        DESCRIPTION
        "This attribute specifies the interface type associated with this interworking.(2 bytes)"
        REFERENCE   "G.984.4 & G.983.2"
        ::= { zxGponMcInterworkEntry 3 }

    zxGponMcInterworkMaxPayloadSize OBJECT-TYPE
        SYNTAX      INTEGER
        MAX-ACCESS  read-write
        STATUS      current
        DESCRIPTION
        "This attribute specifies the maximum GEM payload size associated with GAL Eth profile.(2 bytes)"
        REFERENCE   "G.984.4 & G.983.2"
        ::= { zxGponMcInterworkEntry 4 }

    zxGponMcInterworkPptpCounter OBJECT-TYPE
        SYNTAX      INTEGER
        MAX-ACCESS  read-only
        STATUS      current
        DESCRIPTION
        "This attribute indicates the PPTP counter associated with this interworking.(1 byte)"
        REFERENCE   "G.984.4 & G.983.2"
        ::= { zxGponMcInterworkEntry 5 }
        
    zxGponMcInterworkOperState OBJECT-TYPE
        SYNTAX      INTEGER{
                    enable(1),
                    disable(2)
                    }
        MAX-ACCESS  read-only
        STATUS      current
        DESCRIPTION
        "This attribute indicates the operation state of this interworking.(1 byte)"
        REFERENCE   "G.984.4 & G.983.2"
        ::= { zxGponMcInterworkEntry 6 }

    zxGponMcInterworkEntryStatus OBJECT-TYPE
        SYNTAX      RowStatus
        MAX-ACCESS  read-write
        STATUS      current
        DESCRIPTION
        "This attribute specifies the action of this interworking."
        REFERENCE   "G.984.4 & G.983.2"
        ::= { zxGponMcInterworkEntry 7 }


    zxGponMcAddrTable    OBJECT-TYPE
        SYNTAX      SEQUENCE OF ZxGponMcAddrEntry
        MAX-ACCESS  not-accessible
        STATUS      current
        DESCRIPTION
            ""
        REFERENCE   "G.984.4 & G.983.2"
        ::= { zxGponConnectMgmt 4 }
        
    zxGponMcAddrEntry OBJECT-TYPE
        SYNTAX      ZxGponMcAddrEntry
        MAX-ACCESS  not-accessible
        STATUS      current
        DESCRIPTION
            "It is entry in the zxGponMCAddrTable."
        INDEX   { zxGponOltIndex, zxGponONTIndex, zxGponGemPortIndex, zxGponMcAddrEntryIndex }
        ::= { zxGponMcAddrTable 1 }

    ZxGponMcAddrEntry ::=
        SEQUENCE {
            zxGponMcAddrEntryIndex                         INTEGER,
            zxGponMcAddrIpStart                            IpAddress,
            zxGponMcAddrIpStop                             IpAddress,
            zxGponMcAddrEntryStatus                        RowStatus
        }

    zxGponMcAddrEntryIndex OBJECT-TYPE
        SYNTAX      INTEGER
        MAX-ACCESS  read-only
        STATUS      current
        DESCRIPTION
        "This attribute provides a unique number for each instance of this managed entity.(2 bytes)"
        REFERENCE   "G.984.4 & G.983.2"
        ::= { zxGponMcAddrEntry 1 }

    zxGponMcAddrIpStart OBJECT-TYPE
        SYNTAX      IpAddress
        MAX-ACCESS  read-write
        STATUS      current
        DESCRIPTION
        "This attribute provides the start multicast IP.(4 bytes)"
        REFERENCE   "G.984.4 & G.983.2"
        ::= { zxGponMcAddrEntry 2 }
        
    zxGponMcAddrIpStop OBJECT-TYPE
        SYNTAX      IpAddress
        MAX-ACCESS  read-write
        STATUS      current
        DESCRIPTION
        "This attribute provides the stop multicast IP.(4 bytes)"
        REFERENCE   "G.984.4 & G.983.2"
        ::= { zxGponMcAddrEntry 3 }

    zxGponMcAddrEntryStatus OBJECT-TYPE
        SYNTAX      RowStatus
        MAX-ACCESS  read-write
        STATUS      current
        DESCRIPTION
        "This attribute specifies the action of this multicast address entry."
        REFERENCE   "G.984.4 & G.983.2"
        ::= { zxGponMcAddrEntry 4 }

--Service
    zxGponServiceTable    OBJECT-TYPE
        SYNTAX      SEQUENCE OF ZxGponServiceEntry
        MAX-ACCESS  not-accessible
        STATUS      current
        DESCRIPTION
            ""
        REFERENCE   "G.984.4 & G.983.2"
        ::= { zxGponConnectMgmt 10 }
        
    zxGponServiceEntry OBJECT-TYPE
        SYNTAX      ZxGponServiceEntry
        MAX-ACCESS  not-accessible
        STATUS      current
        DESCRIPTION
            "It is entry in the zxGponServiceTable."
        INDEX   { zxGponOltIndex, zxGponONTIndex, zxGponServiceIndex }
        ::= { zxGponServiceTable 1 }

    ZxGponServiceEntry ::=
        SEQUENCE {
            zxGponServiceName                         OCTET STRING,
            zxGponServiceType                         INTEGER,
            zxGponServiceIfId                         INTEGER,
            zxGponServiceGemPort                      INTEGER,
            zxGponServiceMapType                      INTEGER,
            zxGponServiceMapCos                       INTEGER,
            zxGponServiceMapVlan                      OCTET STRING,
            zxGponServiceMVlan                        INTEGER,
            zxGponServiceEntryStatus                  RowStatus
        }

    zxGponServiceName OBJECT-TYPE
        SYNTAX      OCTET STRING(SIZE(1..32))
        MAX-ACCESS  read-write
        STATUS      current
        DESCRIPTION
        ""
        REFERENCE   "G.984.4 & G.983.2"
        ::= { zxGponServiceEntry 1 }

    zxGponServiceType OBJECT-TYPE
        SYNTAX      INTEGER{
                    internet(1),
                    iptv(2),
                    voip(3),
                    internet-iptv(4),
                    hybrid(5)
                    }
        MAX-ACCESS  read-write
        STATUS      current
        DESCRIPTION
        ""
        REFERENCE   "G.984.4 & G.983.2"
        ::= { zxGponServiceEntry 2 }
        
    zxGponServiceIfId OBJECT-TYPE
        SYNTAX      INTEGER
        MAX-ACCESS  read-write
        STATUS      current
        DESCRIPTION
        "4bytes value contains:type(MSB 2bytes)/ifId(LSB 2bytes).
        type   means
        -------------
        0      bridge
        1      ethuni
        2      iphost"
        REFERENCE   "G.984.4 & G.983.2"
        ::= { zxGponServiceEntry 3 }
        
    zxGponServiceGemPort OBJECT-TYPE
        SYNTAX      INTEGER
        MAX-ACCESS  read-write
        STATUS      current
        DESCRIPTION
        ""
        REFERENCE   "G.984.4 & G.983.2"
        ::= { zxGponServiceEntry 4 }

    zxGponServiceMapType OBJECT-TYPE
        SYNTAX      INTEGER{
                    cos(1),
                    vlan(2),
                    cos-vlan(3)
                    }
        MAX-ACCESS  read-write
        STATUS      current
        DESCRIPTION
        ""
        REFERENCE   "G.984.4 & G.983.2"
        ::= { zxGponServiceEntry 5 }
        
    zxGponServiceMapCos OBJECT-TYPE
        SYNTAX      INTEGER
        MAX-ACCESS  read-write
        STATUS      current
        DESCRIPTION
        "1 byte value stands for the list of 802.1p priority.
        MSB stands for priority 7, LSB stands for priority 0.
        "
        REFERENCE   "G.984.4 & G.983.2"
        ::= { zxGponServiceEntry 6 }

    zxGponServiceMapVlan OBJECT-TYPE
        SYNTAX      OCTET STRING(SIZE(24))
        MAX-ACCESS  read-write
        STATUS      current
        DESCRIPTION
        "Each 2 bytes stand for the vlan id related with this service.
        The first N*2 bytes are valid, until vlan id=0."
        REFERENCE   "G.984.4 & G.983.2"
        ::= { zxGponServiceEntry 7 }

    zxGponServiceMVlan OBJECT-TYPE
        SYNTAX      INTEGER
        MAX-ACCESS  read-write
        STATUS      current
        DESCRIPTION
        ""
        REFERENCE   "G.984.4 & G.983.2"
        ::= { zxGponServiceEntry 8 }

    zxGponServiceEntryStatus OBJECT-TYPE
        SYNTAX      RowStatus
        MAX-ACCESS  read-write
        STATUS      current
        DESCRIPTION
        ""
        REFERENCE   "G.984.4 & G.983.2"
        ::= { zxGponServiceEntry 30 }

--OMCI Trap Info MIB

    zxGponOnuOMCITrapInfoTable    OBJECT-TYPE
        SYNTAX      SEQUENCE OF ZxGponOnuOMCITrapInfoEntry
        MAX-ACCESS  not-accessible
        STATUS      current
        DESCRIPTION
            ""
        REFERENCE   ""
        ::= { zxGponOmciTrapsInfo 1 }
        
    zxGponOnuOMCITrapInfoEntry OBJECT-TYPE
        SYNTAX      ZxGponOnuOMCITrapInfoEntry
        MAX-ACCESS  not-accessible
        STATUS      current
        DESCRIPTION
            ""
        INDEX   { ifIndex, zxGponOnuOMCITrapSubType, zxGponOnuOMCITrapPosition }
        ::= { zxGponOnuOMCITrapInfoTable 1 }

    ZxGponOnuOMCITrapInfoEntry ::=
        SEQUENCE {
            zxGponOnuOMCITrapSubType                       INTEGER,
            zxGponOnuOMCITrapPosition                      INTEGER,
            zxGponOnuOMCITrapStatus                        INTEGER
        }

    zxGponOnuOMCITrapSubType OBJECT-TYPE
        SYNTAX      INTEGER
        MAX-ACCESS  read-only
        STATUS      current
        DESCRIPTION
        "This attribute indicates the sub-type of an OMCI trap:
        1:      uni-LANLos,
        2:      ethUniPm-FCSErrs,
        3:      ethUniPm-ExecessCollisionCnt,
        4:      ethUniPm-LateCollisionCnt,
        5:      ethUniPm-FrameTooLongs,
        6:      ethUniPm-RxBufOverflows,
        7:      ethUniPm-TxBufOverflows,
        8:      ethUniPm-SingleCollisionCnt,
        9:      ethUniPm-MultiCollisionCnt,
        10:     ethUniPm-SQECnt,
        11:     ethUniPm-DeferredTxCnt,
        12:     ethUniPm-InternalMACTxErrCnt,
        13:     ethUniPm-CarrierSenseErrCnt,
        14:     ethUniPm-AlignErrCnt,
        15:     ethUniPm-InternalMACRxErrCnt,
        16:     galEthPm-DiscardedFrames,
        17:     gemPortPm-LostPkts,
        18:     gemPortPm-MisinsertedPkts,
        19:     gemPortPm-ImpairedBlocks
        "
        REFERENCE   ""
        ::= { zxGponOnuOMCITrapInfoEntry 1 }

    zxGponOnuOMCITrapPosition OBJECT-TYPE
        SYNTAX      INTEGER
        MAX-ACCESS  read-only
        STATUS      current
        DESCRIPTION
        "This attribute indicates the position of the OMCI trap.
        According to the sub-type, it may be the UNI index or the GEM port of the ONU."
        REFERENCE   ""
        ::= { zxGponOnuOMCITrapInfoEntry 2 }
        
    zxGponOnuOMCITrapStatus OBJECT-TYPE
        SYNTAX      INTEGER{
                    alarm(1),
                    restore(2)
                    }
        MAX-ACCESS  read-only
        STATUS      current
        DESCRIPTION
        "This attribute indicates the trap status."
        REFERENCE   ""
        ::= { zxGponOnuOMCITrapInfoEntry 3 }

--OMCI Trap MIB

    zxGponOnuOMCITrap        NOTIFICATION-TYPE
        OBJECTS {
                ifIndex,
                zxGponOnuOMCITrapSubType,
                zxGponOnuOMCITrapPosition,
                zxGponOnuOMCITrapStatus,
                zxGponOntDevMgmtName,
                zxGponOntDevMgmtTypeName,
                zxGponOntDevMgmtDescription
                }
        STATUS  current
        DESCRIPTION 
            ""
        ::={zxGponOmciTraps 1}   
        

--OMCI statistics
    zxGponOmciEthStatsTable    OBJECT-TYPE
        SYNTAX      SEQUENCE OF ZxGponOmciEthStatsEntry
        MAX-ACCESS  not-accessible
        STATUS      current
        DESCRIPTION
            ""
        REFERENCE   "G.984.4 Ethernet performance monitoring history data
                     Ethernet performance monitoring history data 2
                     Ethernet performance monitoring history data 3"
        ::= { zxGponOmciStatistics 1 }

    zxGponOmciEthStatsEntry OBJECT-TYPE
        SYNTAX      ZxGponOmciEthStatsEntry
        MAX-ACCESS  not-accessible
        STATUS      current
        DESCRIPTION
            "It is entry in the zxGponOmciEthStatsTable."
        INDEX   { zxGponOltIndex, zxGponONTIndex, zxGponUNIIndex }
        ::= { zxGponOmciEthStatsTable 1 }

    ZxGponOmciEthStatsEntry ::=
        SEQUENCE {
            zxGponOmciEthStatsIntervalEndTime              INTEGER,
            zxGponOmciEthStatsThresDataId                  INTEGER,
            zxGponOmciEthStatsFCSErrors                    Unsigned32,
            zxGponOmciEthStatsExcessiveCollisionCnt        Unsigned32,
            zxGponOmciEthStatsLateCollisionCnt             Unsigned32,
            zxGponOmciEthStatsFrameTooLongs                Unsigned32,
            zxGponOmciEthStatsRxBufOverflows               Unsigned32,
            zxGponOmciEthStatsTxBufOverflows               Unsigned32,
            zxGponOmciEthStatsSingleCollisionCnt           Unsigned32,
            zxGponOmciEthStatsMultipleCollisionCnt         Unsigned32,
            zxGponOmciEthStatsSQECnt                       Unsigned32,
            zxGponOmciEthStatsDeferredTxCnt                Unsigned32,
            zxGponOmciEthStatsInternalMACTxErrCnt          Unsigned32,
            zxGponOmciEthStatsCarrierSenseErrCnt           Unsigned32,
            zxGponOmciEthStatsAlignmentErrCnt              Unsigned32,
            zxGponOmciEthStatsInternalMACRxErrCnt          Unsigned32,
            zxGponOmciEthStatsEntryStatus                  RowStatus,
            zxGponOmciEthStatsPPPoEFilteredCnt             Unsigned32,
            zxGponOmciEthStatsDropEvents                   Unsigned32,
            zxGponOmciEthStatsRxOctets                     Unsigned32,
            zxGponOmciEthStatsRxPkts                       Unsigned32,
            zxGponOmciEthStatsRxBroadcastPkts              Unsigned32,
            zxGponOmciEthStatsRxMulticastPkts              Unsigned32,
            zxGponOmciEthStatsRxUndersizePkts              Unsigned32,
            zxGponOmciEthStatsRxFragments                  Unsigned32,
            zxGponOmciEthStatsRxJabbers                    Unsigned32,
            zxGponOmciEthStatsRx64OctetsPkts               Unsigned32,
            zxGponOmciEthStatsRx65To127OctetsPkts          Unsigned32,
            zxGponOmciEthStatsRx128To255OctetsPkts         Unsigned32,
            zxGponOmciEthStatsRx256To511OctetsPkts         Unsigned32,
            zxGponOmciEthStatsRx512To1023OctetsPkts        Unsigned32,
            zxGponOmciEthStatsRx1024To1518OctetsPkts       Unsigned32
        }

    zxGponOmciEthStatsIntervalEndTime OBJECT-TYPE
        SYNTAX      INTEGER
        MAX-ACCESS  read-only
        STATUS      current
        DESCRIPTION
        ""
        REFERENCE   "G.984.4"
        ::= { zxGponOmciEthStatsEntry 1 }

    zxGponOmciEthStatsThresDataId OBJECT-TYPE
        SYNTAX      INTEGER
        MAX-ACCESS  read-write
        STATUS      current
        DESCRIPTION
        ""
        REFERENCE   "G.984.4"
        ::= { zxGponOmciEthStatsEntry 2 }

    zxGponOmciEthStatsFCSErrors OBJECT-TYPE
        SYNTAX      Unsigned32
        MAX-ACCESS  read-only
        STATUS      current
        DESCRIPTION
        ""
        REFERENCE   "G.984.4 Ethernet performance monitoring history data"
        ::= { zxGponOmciEthStatsEntry 3 }

    zxGponOmciEthStatsExcessiveCollisionCnt OBJECT-TYPE
        SYNTAX      Unsigned32
        MAX-ACCESS  read-only
        STATUS      current
        DESCRIPTION
        ""
        REFERENCE   "G.984.4 Ethernet performance monitoring history data"
        ::= { zxGponOmciEthStatsEntry 4 }

    zxGponOmciEthStatsLateCollisionCnt OBJECT-TYPE
        SYNTAX      Unsigned32
        MAX-ACCESS  read-only
        STATUS      current
        DESCRIPTION
        ""
        REFERENCE   "G.984.4 Ethernet performance monitoring history data"
        ::= { zxGponOmciEthStatsEntry 5 }
        
    zxGponOmciEthStatsFrameTooLongs OBJECT-TYPE
        SYNTAX      Unsigned32
        MAX-ACCESS  read-only
        STATUS      current
        DESCRIPTION
        ""
        REFERENCE   "G.984.4 Ethernet performance monitoring history data"
        ::= { zxGponOmciEthStatsEntry 6 }
        
    zxGponOmciEthStatsRxBufOverflows OBJECT-TYPE
        SYNTAX      Unsigned32
        MAX-ACCESS  read-only
        STATUS      current
        DESCRIPTION
        ""
        REFERENCE   "G.984.4 Ethernet performance monitoring history data"
        ::= { zxGponOmciEthStatsEntry 7 }

    zxGponOmciEthStatsTxBufOverflows OBJECT-TYPE
        SYNTAX      Unsigned32
        MAX-ACCESS  read-only
        STATUS      current
        DESCRIPTION
        ""
        REFERENCE   "G.984.4 Ethernet performance monitoring history data"
        ::= { zxGponOmciEthStatsEntry 8 }
        
    zxGponOmciEthStatsSingleCollisionCnt OBJECT-TYPE
        SYNTAX      Unsigned32
        MAX-ACCESS  read-only
        STATUS      current
        DESCRIPTION
        ""
        REFERENCE   "G.984.4 Ethernet performance monitoring history data"
        ::= { zxGponOmciEthStatsEntry 9 }

    zxGponOmciEthStatsMultipleCollisionCnt OBJECT-TYPE
        SYNTAX      Unsigned32
        MAX-ACCESS  read-only
        STATUS      current
        DESCRIPTION
        ""
        REFERENCE   "G.984.4 Ethernet performance monitoring history data"
        ::= { zxGponOmciEthStatsEntry 10 }

    zxGponOmciEthStatsSQECnt OBJECT-TYPE
        SYNTAX      Unsigned32
        MAX-ACCESS  read-only
        STATUS      current
        DESCRIPTION
        ""
        REFERENCE   "G.984.4 Ethernet performance monitoring history data"
        ::= { zxGponOmciEthStatsEntry 11 }

    zxGponOmciEthStatsDeferredTxCnt OBJECT-TYPE
        SYNTAX      Unsigned32
        MAX-ACCESS  read-only
        STATUS      current
        DESCRIPTION
        ""
        REFERENCE   "G.984.4 Ethernet performance monitoring history data"
        ::= { zxGponOmciEthStatsEntry 12 }

    zxGponOmciEthStatsInternalMACTxErrCnt OBJECT-TYPE
        SYNTAX      Unsigned32
        MAX-ACCESS  read-only
        STATUS      current
        DESCRIPTION
        ""
        REFERENCE   "G.984.4 Ethernet performance monitoring history data"
        ::= { zxGponOmciEthStatsEntry 13 }

    zxGponOmciEthStatsCarrierSenseErrCnt OBJECT-TYPE
        SYNTAX      Unsigned32
        MAX-ACCESS  read-only
        STATUS      current
        DESCRIPTION
        ""
        REFERENCE   "G.984.4 Ethernet performance monitoring history data"
        ::= { zxGponOmciEthStatsEntry 14 }

    zxGponOmciEthStatsAlignmentErrCnt OBJECT-TYPE
        SYNTAX      Unsigned32
        MAX-ACCESS  read-only
        STATUS      current
        DESCRIPTION
        ""
        REFERENCE   "G.984.4 Ethernet performance monitoring history data"
        ::= { zxGponOmciEthStatsEntry 15 }

    zxGponOmciEthStatsInternalMACRxErrCnt OBJECT-TYPE
        SYNTAX      Unsigned32
        MAX-ACCESS  read-only
        STATUS      current
        DESCRIPTION
        ""
        REFERENCE   "G.984.4 Ethernet performance monitoring history data"
        ::= { zxGponOmciEthStatsEntry 16 }

    zxGponOmciEthStatsEntryStatus OBJECT-TYPE
        SYNTAX      RowStatus
        MAX-ACCESS  read-write
        STATUS      current
        DESCRIPTION
        "This attribute specifies the action of this entry."
        REFERENCE   "G.984.4"
        ::= { zxGponOmciEthStatsEntry 17 }

    zxGponOmciEthStatsPPPoEFilteredCnt OBJECT-TYPE
        SYNTAX      Unsigned32
        MAX-ACCESS  read-only
        STATUS      current
        DESCRIPTION
        ""
        REFERENCE   "G.984.4 Ethernet performance monitoring history data 2"
        ::= { zxGponOmciEthStatsEntry 18 }

    zxGponOmciEthStatsDropEvents OBJECT-TYPE
        SYNTAX      Unsigned32
        MAX-ACCESS  read-only
        STATUS      current
        DESCRIPTION
        ""
        REFERENCE   "G.984.4 Ethernet performance monitoring history data 3"
        ::= { zxGponOmciEthStatsEntry 19 }

    zxGponOmciEthStatsRxOctets OBJECT-TYPE
        SYNTAX      Unsigned32
        MAX-ACCESS  read-only
        STATUS      current
        DESCRIPTION
        ""
        REFERENCE   "G.984.4"
        ::= { zxGponOmciEthStatsEntry 20 }

    zxGponOmciEthStatsRxPkts OBJECT-TYPE
        SYNTAX      Unsigned32
        MAX-ACCESS  read-only
        STATUS      current
        DESCRIPTION
        ""
        REFERENCE   "G.984.4 Ethernet performance monitoring history data 3"
        ::= { zxGponOmciEthStatsEntry 21 }

    zxGponOmciEthStatsRxBroadcastPkts OBJECT-TYPE
        SYNTAX      Unsigned32
        MAX-ACCESS  read-only
        STATUS      current
        DESCRIPTION
        ""
        REFERENCE   "G.984.4 Ethernet performance monitoring history data 3"
        ::= { zxGponOmciEthStatsEntry 22 }

    zxGponOmciEthStatsRxMulticastPkts OBJECT-TYPE
        SYNTAX      Unsigned32
        MAX-ACCESS  read-only
        STATUS      current
        DESCRIPTION
        ""
        REFERENCE   "G.984.4 Ethernet performance monitoring history data 3"
        ::= { zxGponOmciEthStatsEntry 23 }

    zxGponOmciEthStatsRxUndersizePkts OBJECT-TYPE
        SYNTAX      Unsigned32
        MAX-ACCESS  read-only
        STATUS      current
        DESCRIPTION
        ""
        REFERENCE   "G.984.4 Ethernet performance monitoring history data 3"
        ::= { zxGponOmciEthStatsEntry 24 }

    zxGponOmciEthStatsRxFragments OBJECT-TYPE
        SYNTAX      Unsigned32
        MAX-ACCESS  read-only
        STATUS      current
        DESCRIPTION
        ""
        REFERENCE   "G.984.4 Ethernet performance monitoring history data 3"
        ::= { zxGponOmciEthStatsEntry 25 }

    zxGponOmciEthStatsRxJabbers OBJECT-TYPE
        SYNTAX      Unsigned32
        MAX-ACCESS  read-only
        STATUS      current
        DESCRIPTION
        ""
        REFERENCE   "G.984.4 Ethernet performance monitoring history data 3"
        ::= { zxGponOmciEthStatsEntry 26 }

    zxGponOmciEthStatsRx64OctetsPkts OBJECT-TYPE
        SYNTAX      Unsigned32
        MAX-ACCESS  read-only
        STATUS      current
        DESCRIPTION
        ""
        REFERENCE   "G.984.4 Ethernet performance monitoring history data 3"
        ::= { zxGponOmciEthStatsEntry 27 }

    zxGponOmciEthStatsRx65To127OctetsPkts OBJECT-TYPE
        SYNTAX      Unsigned32
        MAX-ACCESS  read-only
        STATUS      current
        DESCRIPTION
        ""
        REFERENCE   "G.984.4 Ethernet performance monitoring history data 3"
        ::= { zxGponOmciEthStatsEntry 28 }

    zxGponOmciEthStatsRx128To255OctetsPkts OBJECT-TYPE
        SYNTAX      Unsigned32
        MAX-ACCESS  read-only
        STATUS      current
        DESCRIPTION
        ""
        REFERENCE   "G.984.4 Ethernet performance monitoring history data 3"
        ::= { zxGponOmciEthStatsEntry 29 }

    zxGponOmciEthStatsRx256To511OctetsPkts OBJECT-TYPE
        SYNTAX      Unsigned32
        MAX-ACCESS  read-only
        STATUS      current
        DESCRIPTION
        ""
        REFERENCE   "G.984.4 Ethernet performance monitoring history data 3"
        ::= { zxGponOmciEthStatsEntry 30 }

    zxGponOmciEthStatsRx512To1023OctetsPkts OBJECT-TYPE
        SYNTAX      Unsigned32
        MAX-ACCESS  read-only
        STATUS      current
        DESCRIPTION
        ""
        REFERENCE   "G.984.4 Ethernet performance monitoring history data 3"
        ::= { zxGponOmciEthStatsEntry 31 }

    zxGponOmciEthStatsRx1024To1518OctetsPkts OBJECT-TYPE
        SYNTAX      Unsigned32
        MAX-ACCESS  read-only
        STATUS      current
        DESCRIPTION
        ""
        REFERENCE   "G.984.4 Ethernet performance monitoring history data 3"
        ::= { zxGponOmciEthStatsEntry 32 }


    zxGponOmciGEMStatsTable    OBJECT-TYPE
        SYNTAX      SEQUENCE OF ZxGponOmciGEMStatsEntry
        MAX-ACCESS  not-accessible
        STATUS      current
        DESCRIPTION
            ""
        REFERENCE   "G.984.4 & G.983.2"
        ::= { zxGponOmciStatistics 2 }

    zxGponOmciGEMStatsEntry OBJECT-TYPE
        SYNTAX      ZxGponOmciGEMStatsEntry
        MAX-ACCESS  not-accessible
        STATUS      current
        DESCRIPTION
            "It is entry in the zxGponOmciGEMStatsTable."
        INDEX   { zxGponOltIndex, zxGponONTIndex, zxGponGemPortIndex }
        ::= { zxGponOmciGEMStatsTable 1 }

    ZxGponOmciGEMStatsEntry ::=
        SEQUENCE {
            zxGponOmciGEMStatsIntervalEndTime               INTEGER,
            zxGponOmciGEMStatsThresDataId                   INTEGER,
            zxGponOmciGEMStatsLostPkts                      Unsigned32,
            zxGponOmciGEMStatsMisInsertedPkts               Unsigned32,
            zxGponOmciGEMStatsRxPkts                        Counter64,
            zxGponOmciGEMStatsRxBlocks                      Counter64,
            zxGponOmciGEMStatsTxBlocks                      Counter64,
            zxGponOmciGEMStatsImpairedBlocks                Unsigned32,
            zxGponOmciGEMStatsEntryStatus                   RowStatus
        }

    zxGponOmciGEMStatsIntervalEndTime OBJECT-TYPE
        SYNTAX      INTEGER
        MAX-ACCESS  read-only
        STATUS      current
        DESCRIPTION
        ""
        REFERENCE   "G.984.4 & G.983.2"
        ::= { zxGponOmciGEMStatsEntry 1 }

    zxGponOmciGEMStatsThresDataId OBJECT-TYPE
        SYNTAX      INTEGER
        MAX-ACCESS  read-write
        STATUS      current
        DESCRIPTION
        ""
        REFERENCE   "G.984.4 & G.983.2"
        ::= { zxGponOmciGEMStatsEntry 2 }

    zxGponOmciGEMStatsLostPkts OBJECT-TYPE
        SYNTAX      Unsigned32
        MAX-ACCESS  read-only
        STATUS      current
        DESCRIPTION
        ""
        REFERENCE   "G.984.4 & G.983.2"
        ::= { zxGponOmciGEMStatsEntry 3 }

    zxGponOmciGEMStatsMisInsertedPkts OBJECT-TYPE
        SYNTAX      Unsigned32
        MAX-ACCESS  read-only
        STATUS      current
        DESCRIPTION
        ""
        REFERENCE   "G.984.4 & G.983.2"
        ::= { zxGponOmciGEMStatsEntry 4 }

    zxGponOmciGEMStatsRxPkts OBJECT-TYPE
        SYNTAX      Counter64
        MAX-ACCESS  read-only
        STATUS      current
        DESCRIPTION
        ""
        REFERENCE   "G.984.4 & G.983.2"
        ::= { zxGponOmciGEMStatsEntry 6 }
        
    zxGponOmciGEMStatsRxBlocks OBJECT-TYPE
        SYNTAX      Counter64
        MAX-ACCESS  read-only
        STATUS      current
        DESCRIPTION
        ""
        REFERENCE   "G.984.4 & G.983.2"
        ::= { zxGponOmciGEMStatsEntry 7 }

    zxGponOmciGEMStatsTxBlocks OBJECT-TYPE
        SYNTAX      Counter64
        MAX-ACCESS  read-only
        STATUS      current
        DESCRIPTION
        ""
        REFERENCE   "G.984.4 & G.983.2"
        ::= { zxGponOmciGEMStatsEntry 8 }
        
    zxGponOmciGEMStatsImpairedBlocks OBJECT-TYPE
        SYNTAX      Unsigned32
        MAX-ACCESS  read-only
        STATUS      current
        DESCRIPTION
        ""
        REFERENCE   "G.984.4 & G.983.2"
        ::= { zxGponOmciGEMStatsEntry 9 }

    zxGponOmciGEMStatsEntryStatus OBJECT-TYPE
        SYNTAX      RowStatus
        MAX-ACCESS  read-write
        STATUS      current
        DESCRIPTION
        "This attribute specifies the action of this interworking."
        REFERENCE   "G.984.4 & G.983.2"
        ::= { zxGponOmciGEMStatsEntry 10 }
        
    zxGponOmciGALEthStatsTable    OBJECT-TYPE
        SYNTAX      SEQUENCE OF ZxGponOmciGALEthStatsEntry
        MAX-ACCESS  not-accessible
        STATUS      current
        DESCRIPTION
            ""
        REFERENCE   "G.984.4 & G.983.2"
        ::= { zxGponOmciStatistics 3 }

    zxGponOmciGALEthStatsEntry OBJECT-TYPE
        SYNTAX      ZxGponOmciGALEthStatsEntry
        MAX-ACCESS  not-accessible
        STATUS      current
        DESCRIPTION
            "It is entry in the zxGponOmciGALEthStatsTable."
        INDEX   { zxGponOltIndex, zxGponONTIndex, zxGponGemPortIndex }
        ::= { zxGponOmciGALEthStatsTable 1 }

    ZxGponOmciGALEthStatsEntry ::=
        SEQUENCE {
            zxGponOmciGALEthStatsIntervalEndTime               INTEGER,
            zxGponOmciGALEthStatsThresDataId                   INTEGER,
            zxGponOmciGALEthStatsDiscardedFrames               Unsigned32,
            zxGponOmciGALEthStatsEntryStatus                   RowStatus
        }

    zxGponOmciGALEthStatsIntervalEndTime OBJECT-TYPE
        SYNTAX      INTEGER
        MAX-ACCESS  read-only
        STATUS      current
        DESCRIPTION
        ""
        REFERENCE   "G.984.4 & G.983.2"
        ::= { zxGponOmciGALEthStatsEntry 1 }
        
    zxGponOmciGALEthStatsThresDataId OBJECT-TYPE
        SYNTAX      INTEGER
        MAX-ACCESS  read-write
        STATUS      current
        DESCRIPTION
        ""
        REFERENCE   "G.984.4 & G.983.2"
        ::= { zxGponOmciGALEthStatsEntry 2 }

    zxGponOmciGALEthStatsDiscardedFrames OBJECT-TYPE
        SYNTAX      Unsigned32
        MAX-ACCESS  read-only
        STATUS      current
        DESCRIPTION
        ""
        REFERENCE   "G.984.4 & G.983.2"
        ::= { zxGponOmciGALEthStatsEntry 3 }
    
    zxGponOmciGALEthStatsEntryStatus OBJECT-TYPE
        SYNTAX      RowStatus
        MAX-ACCESS  read-write
        STATUS      current
        DESCRIPTION
        ""
        REFERENCE   "G.984.4 & G.983.2"
        ::= { zxGponOmciGALEthStatsEntry 4 }

    zxGponOmciBridgeStatsTable    OBJECT-TYPE
        SYNTAX      SEQUENCE OF ZxGponOmciBridgeStatsEntry
        MAX-ACCESS  not-accessible
        STATUS      current
        DESCRIPTION
            ""
        REFERENCE   "G.984.4 & G.983.2"
        ::= { zxGponOmciStatistics 4 }

    zxGponOmciBridgeStatsEntry OBJECT-TYPE
        SYNTAX      ZxGponOmciBridgeStatsEntry
        MAX-ACCESS  not-accessible
        STATUS      current
        DESCRIPTION
            "It is entry in the zxGponOmciBridgeStatsTable."
        INDEX   { zxGponOltIndex, zxGponONTIndex, zxGponBridgeIndex }
        ::= { zxGponOmciBridgeStatsTable 1 }

    ZxGponOmciBridgeStatsEntry ::=
        SEQUENCE {
            zxGponOmciBridgeStatsIntervalEndTime               INTEGER,
            zxGponOmciBridgeStatsThresDataId                   INTEGER,
            zxGponOmciBridgeStatsLearnEntryDiscardFrames       Unsigned32,
            zxGponOmciBridgeStatsEntryStatus                   RowStatus
        }

    zxGponOmciBridgeStatsIntervalEndTime OBJECT-TYPE
        SYNTAX      INTEGER
        MAX-ACCESS  read-only
        STATUS      current
        DESCRIPTION
        ""
        REFERENCE   "G.984.4 & G.983.2"
        ::= { zxGponOmciBridgeStatsEntry 1 }
        
    zxGponOmciBridgeStatsThresDataId OBJECT-TYPE
        SYNTAX      INTEGER
        MAX-ACCESS  read-write
        STATUS      current
        DESCRIPTION
        ""
        REFERENCE   "G.984.4 & G.983.2"
        ::= { zxGponOmciBridgeStatsEntry 2 }

    zxGponOmciBridgeStatsLearnEntryDiscardFrames OBJECT-TYPE
        SYNTAX      Unsigned32
        MAX-ACCESS  read-only
        STATUS      current
        DESCRIPTION
        ""
        REFERENCE   "G.984.4 & G.983.2"
        ::= { zxGponOmciBridgeStatsEntry 3 }
    
    zxGponOmciBridgeStatsEntryStatus OBJECT-TYPE
        SYNTAX      RowStatus
        MAX-ACCESS  read-write
        STATUS      current
        DESCRIPTION
        ""
        REFERENCE   "G.984.4 & G.983.2"
        ::= { zxGponOmciBridgeStatsEntry 4 }


    zxGponOmciUNIBridgePortStatsTable    OBJECT-TYPE
        SYNTAX      SEQUENCE OF ZxGponOmciUNIBridgePortStatsEntry
        MAX-ACCESS  not-accessible
        STATUS      current
        DESCRIPTION
            ""
        REFERENCE   "G.984.4 & G.983.2"
        ::= { zxGponOmciStatistics 5 }

    zxGponOmciUNIBridgePortStatsEntry OBJECT-TYPE
        SYNTAX      ZxGponOmciUNIBridgePortStatsEntry
        MAX-ACCESS  not-accessible
        STATUS      current
        DESCRIPTION
            "It is entry in the zxGponOmciUNIBridgePortStatsTable."
        INDEX   { zxGponOltIndex, zxGponONTIndex, zxGponUNIIndex }
        ::= { zxGponOmciUNIBridgePortStatsTable 1 }

    ZxGponOmciUNIBridgePortStatsEntry ::=
        SEQUENCE {
            zxGponOmciUNIBridgePortStatsIntervalEndTime               INTEGER,
            zxGponOmciUNIBridgePortStatsThresDataId                   INTEGER,
            zxGponOmciUNIBridgePortStatsForwardFrameCnt               Unsigned32,
            zxGponOmciUNIBridgePortStatsDelayExceedDiscardCnt         Unsigned32,
            zxGponOmciUNIBridgePortStatsMTUExceedDiscardCnt           Unsigned32,
            zxGponOmciUNIBridgePortStatsRxFrameCnt                    Unsigned32,
            zxGponOmciUNIBridgePortStatsRxDiscardCnt                  Unsigned32,
            zxGponOmciUNIBridgePortStatsEntryStatus                   RowStatus
        }

    zxGponOmciUNIBridgePortStatsIntervalEndTime OBJECT-TYPE
        SYNTAX      INTEGER
        MAX-ACCESS  read-only
        STATUS      current
        DESCRIPTION
        ""
        REFERENCE   "G.984.4 & G.983.2"
        ::= { zxGponOmciUNIBridgePortStatsEntry 1 }
        
    zxGponOmciUNIBridgePortStatsThresDataId OBJECT-TYPE
        SYNTAX      INTEGER
        MAX-ACCESS  read-write
        STATUS      current
        DESCRIPTION
        ""
        REFERENCE   "G.984.4 & G.983.2"
        ::= { zxGponOmciUNIBridgePortStatsEntry 2 }

    zxGponOmciUNIBridgePortStatsForwardFrameCnt OBJECT-TYPE
        SYNTAX      Unsigned32
        MAX-ACCESS  read-only
        STATUS      current
        DESCRIPTION
        ""
        REFERENCE   "G.984.4 & G.983.2"
        ::= { zxGponOmciUNIBridgePortStatsEntry 3 }
        
    zxGponOmciUNIBridgePortStatsDelayExceedDiscardCnt OBJECT-TYPE
        SYNTAX      Unsigned32
        MAX-ACCESS  read-only
        STATUS      current
        DESCRIPTION
        ""
        REFERENCE   "G.984.4 & G.983.2"
        ::= { zxGponOmciUNIBridgePortStatsEntry 4 }
        
    zxGponOmciUNIBridgePortStatsMTUExceedDiscardCnt OBJECT-TYPE
        SYNTAX      Unsigned32
        MAX-ACCESS  read-only
        STATUS      current
        DESCRIPTION
        ""
        REFERENCE   "G.984.4 & G.983.2"
        ::= { zxGponOmciUNIBridgePortStatsEntry 5 }
        
    zxGponOmciUNIBridgePortStatsRxFrameCnt OBJECT-TYPE
        SYNTAX      Unsigned32
        MAX-ACCESS  read-only
        STATUS      current
        DESCRIPTION
        ""
        REFERENCE   "G.984.4 & G.983.2"
        ::= { zxGponOmciUNIBridgePortStatsEntry 6 }
        
    zxGponOmciUNIBridgePortStatsRxDiscardCnt OBJECT-TYPE
        SYNTAX      Unsigned32
        MAX-ACCESS  read-only
        STATUS      current
        DESCRIPTION
        ""
        REFERENCE   "G.984.4 & G.983.2"
        ::= { zxGponOmciUNIBridgePortStatsEntry 7 }
        
    zxGponOmciUNIBridgePortStatsEntryStatus OBJECT-TYPE
        SYNTAX      RowStatus
        MAX-ACCESS  read-write
        STATUS      current
        DESCRIPTION
        ""
        REFERENCE   "G.984.4 & G.983.2"
        ::= { zxGponOmciUNIBridgePortStatsEntry 8 }

    zxGponOmciUpLinkBridgePortStatsTable    OBJECT-TYPE
        SYNTAX      SEQUENCE OF ZxGponOmciUpLinkBridgePortStatsEntry
        MAX-ACCESS  not-accessible
        STATUS      current
        DESCRIPTION
            ""
        REFERENCE   "G.984.4 & G.983.2"
        ::= { zxGponOmciStatistics 6 }

    zxGponOmciUpLinkBridgePortStatsEntry OBJECT-TYPE
        SYNTAX      ZxGponOmciUpLinkBridgePortStatsEntry
        MAX-ACCESS  not-accessible
        STATUS      current
        DESCRIPTION
            "It is entry in the zxGponOmciUpLinkBridgePortStatsTable."
        INDEX   { zxGponOltIndex, zxGponONTIndex, zxGponUpLinkIndex }
        ::= { zxGponOmciUpLinkBridgePortStatsTable 1 }

    ZxGponOmciUpLinkBridgePortStatsEntry ::=
        SEQUENCE {
            zxGponOmciUpLinkBridgePortStatsIntervalEndTime               INTEGER,
            zxGponOmciUpLinkBridgePortStatsThresDataId                   INTEGER,
            zxGponOmciUpLinkBridgePortStatsForwardFrameCnt               Unsigned32,
            zxGponOmciUpLinkBridgePortStatsDelayExceedDiscardCnt         Unsigned32,
            zxGponOmciUpLinkBridgePortStatsMTUExceedDiscardCnt           Unsigned32,
            zxGponOmciUpLinkBridgePortStatsRxFrameCnt                    Unsigned32,
            zxGponOmciUpLinkBridgePortStatsRxDiscardCnt                  Unsigned32,
            zxGponOmciUpLinkBridgePortStatsEntryStatus                   RowStatus
        }

    zxGponOmciUpLinkBridgePortStatsIntervalEndTime OBJECT-TYPE
        SYNTAX      INTEGER
        MAX-ACCESS  read-only
        STATUS      current
        DESCRIPTION
        ""
        REFERENCE   "G.984.4 & G.983.2"
        ::= { zxGponOmciUpLinkBridgePortStatsEntry 1 }
        
    zxGponOmciUpLinkBridgePortStatsThresDataId OBJECT-TYPE
        SYNTAX      INTEGER
        MAX-ACCESS  read-write
        STATUS      current
        DESCRIPTION
        ""
        REFERENCE   "G.984.4 & G.983.2"
        ::= { zxGponOmciUpLinkBridgePortStatsEntry 2 }

    zxGponOmciUpLinkBridgePortStatsForwardFrameCnt OBJECT-TYPE
        SYNTAX      Unsigned32
        MAX-ACCESS  read-only
        STATUS      current
        DESCRIPTION
        ""
        REFERENCE   "G.984.4 & G.983.2"
        ::= { zxGponOmciUpLinkBridgePortStatsEntry 3 }
        
    zxGponOmciUpLinkBridgePortStatsDelayExceedDiscardCnt OBJECT-TYPE
        SYNTAX      Unsigned32
        MAX-ACCESS  read-only
        STATUS      current
        DESCRIPTION
        ""
        REFERENCE   "G.984.4 & G.983.2"
        ::= { zxGponOmciUpLinkBridgePortStatsEntry 4 }
        
    zxGponOmciUpLinkBridgePortStatsMTUExceedDiscardCnt OBJECT-TYPE
        SYNTAX      Unsigned32
        MAX-ACCESS  read-only
        STATUS      current
        DESCRIPTION
        ""
        REFERENCE   "G.984.4 & G.983.2"
        ::= { zxGponOmciUpLinkBridgePortStatsEntry 5 }
        
    zxGponOmciUpLinkBridgePortStatsRxFrameCnt OBJECT-TYPE
        SYNTAX      Unsigned32
        MAX-ACCESS  read-only
        STATUS      current
        DESCRIPTION
        ""
        REFERENCE   "G.984.4 & G.983.2"
        ::= { zxGponOmciUpLinkBridgePortStatsEntry 6 }
        
    zxGponOmciUpLinkBridgePortStatsRxDiscardCnt OBJECT-TYPE
        SYNTAX      Unsigned32
        MAX-ACCESS  read-only
        STATUS      current
        DESCRIPTION
        ""
        REFERENCE   "G.984.4 & G.983.2"
        ::= { zxGponOmciUpLinkBridgePortStatsEntry 7 }
        
    zxGponOmciUpLinkBridgePortStatsEntryStatus OBJECT-TYPE
        SYNTAX      RowStatus
        MAX-ACCESS  read-write
        STATUS      current
        DESCRIPTION
        ""
        REFERENCE   "G.984.4 & G.983.2"
        ::= { zxGponOmciUpLinkBridgePortStatsEntry 8 }

--IP Host Performance Monitoring History Data
    zxGponOmciIPHostStatsTable    OBJECT-TYPE
        SYNTAX      SEQUENCE OF ZxGponOmciIPHostStatsEntry
        MAX-ACCESS  not-accessible
        STATUS      current
        DESCRIPTION
            ""
        REFERENCE   "G.984.4 & G.983.2"
        ::= { zxGponOmciStatistics 7 }

    zxGponOmciIPHostStatsEntry OBJECT-TYPE
        SYNTAX      ZxGponOmciIPHostStatsEntry
        MAX-ACCESS  not-accessible
        STATUS      current
        DESCRIPTION
            "It is entry in the zxGponOmciIPHostStatsTable."
        INDEX   { zxGponOltIndex, zxGponONTIndex, zxGponIPHostConfigDataId }
        ::= { zxGponOmciIPHostStatsTable 1 }

    ZxGponOmciIPHostStatsEntry ::=
        SEQUENCE {
            zxGponOmciIPHostStatsIntervalEndTime              INTEGER,
            zxGponOmciIPHostStatsThresDataId                  INTEGER,
            zxGponOmciIPHostStatsICMPErrors                   Unsigned32,
            zxGponOmciIPHostStatsDNSErrors                    Unsigned32,
            zxGponOmciIPHostStatsEntryStatus                  RowStatus
        }

    zxGponOmciIPHostStatsIntervalEndTime OBJECT-TYPE
        SYNTAX      INTEGER
        MAX-ACCESS  read-only
        STATUS      current
        DESCRIPTION
        ""
        REFERENCE   "G.984.4 & G.983.2"
        ::= { zxGponOmciIPHostStatsEntry 1 }

    zxGponOmciIPHostStatsThresDataId OBJECT-TYPE
        SYNTAX      INTEGER
        MAX-ACCESS  read-write
        STATUS      current
        DESCRIPTION
        ""
        REFERENCE   "G.984.4 & G.983.2"
        ::= { zxGponOmciIPHostStatsEntry 2 }

    zxGponOmciIPHostStatsICMPErrors OBJECT-TYPE
        SYNTAX      Unsigned32
        MAX-ACCESS  read-only
        STATUS      current
        DESCRIPTION
        ""
        REFERENCE   "G.984.4 & G.983.2"
        ::= { zxGponOmciIPHostStatsEntry 3 }

    zxGponOmciIPHostStatsDNSErrors OBJECT-TYPE
        SYNTAX      Unsigned32
        MAX-ACCESS  read-only
        STATUS      current
        DESCRIPTION
        ""
        REFERENCE   "G.984.4 & G.983.2"
        ::= { zxGponOmciIPHostStatsEntry 4 }

    zxGponOmciIPHostStatsEntryStatus OBJECT-TYPE
        SYNTAX      RowStatus
        MAX-ACCESS  read-write
        STATUS      current
        DESCRIPTION
        "This attribute specifies the action of this entry."
        REFERENCE   "G.984.4 & G.983.2"
        ::= { zxGponOmciIPHostStatsEntry 5 }

--Call Control PM History Data
    zxGponOmciCallCtrlStatsTable    OBJECT-TYPE
        SYNTAX      SEQUENCE OF ZxGponOmciCallCtrlStatsEntry
        MAX-ACCESS  not-accessible
        STATUS      current
        DESCRIPTION
            ""
        REFERENCE   "G.984.4 & G.983.2"
        ::= { zxGponOmciStatistics 8 }

    zxGponOmciCallCtrlStatsEntry OBJECT-TYPE
        SYNTAX      ZxGponOmciCallCtrlStatsEntry
        MAX-ACCESS  not-accessible
        STATUS      current
        DESCRIPTION
            "It is entry in the zxGponOmciCallCtrlStatsTable."
        INDEX   { zxGponOltIndex, zxGponONTIndex, zxGponUNIIndex }
        ::= { zxGponOmciCallCtrlStatsTable 1 }

    ZxGponOmciCallCtrlStatsEntry ::=
        SEQUENCE {
            zxGponOmciCallCtrlStatsIntervalEndTime              INTEGER,
            zxGponOmciCallCtrlStatsThresDataId                  INTEGER,
            zxGponOmciCallCtrlStatsCallSetupFailures            Unsigned32,
            zxGponOmciCallCtrlStatsCallSetupTimer               Unsigned32,
            zxGponOmciCallCtrlStatsCallTerminateFailures        Unsigned32,
            zxGponOmciCallCtrlStatsAnalogPortReleases           Unsigned32,
            zxGponOmciCallCtrlStatsAnalogPortOffHookTimer       Unsigned32,
            zxGponOmciCallCtrlStatsEntryStatus                  RowStatus
        }

    zxGponOmciCallCtrlStatsIntervalEndTime OBJECT-TYPE
        SYNTAX      INTEGER
        MAX-ACCESS  read-only
        STATUS      current
        DESCRIPTION
        ""
        REFERENCE   "G.984.4 & G.983.2"
        ::= { zxGponOmciCallCtrlStatsEntry 1 }

    zxGponOmciCallCtrlStatsThresDataId OBJECT-TYPE
        SYNTAX      INTEGER
        MAX-ACCESS  read-write
        STATUS      current
        DESCRIPTION
        ""
        REFERENCE   "G.984.4 & G.983.2"
        ::= { zxGponOmciCallCtrlStatsEntry 2 }

    zxGponOmciCallCtrlStatsCallSetupFailures OBJECT-TYPE
        SYNTAX      Unsigned32
        MAX-ACCESS  read-only
        STATUS      current
        DESCRIPTION
        ""
        REFERENCE   "G.984.4 & G.983.2"
        ::= { zxGponOmciCallCtrlStatsEntry 3 }

    zxGponOmciCallCtrlStatsCallSetupTimer OBJECT-TYPE
        SYNTAX      Unsigned32
        MAX-ACCESS  read-only
        STATUS      current
        DESCRIPTION
        ""
        REFERENCE   "G.984.4 & G.983.2"
        ::= { zxGponOmciCallCtrlStatsEntry 4 }

    zxGponOmciCallCtrlStatsCallTerminateFailures OBJECT-TYPE
        SYNTAX      Unsigned32
        MAX-ACCESS  read-only
        STATUS      current
        DESCRIPTION
        ""
        REFERENCE   "G.984.4 & G.983.2"
        ::= { zxGponOmciCallCtrlStatsEntry 5 }

    zxGponOmciCallCtrlStatsAnalogPortReleases OBJECT-TYPE
        SYNTAX      Unsigned32
        MAX-ACCESS  read-only
        STATUS      current
        DESCRIPTION
        ""
        REFERENCE   "G.984.4 & G.983.2"
        ::= { zxGponOmciCallCtrlStatsEntry 6 }

    zxGponOmciCallCtrlStatsAnalogPortOffHookTimer OBJECT-TYPE
        SYNTAX      Unsigned32
        MAX-ACCESS  read-only
        STATUS      current
        DESCRIPTION
        ""
        REFERENCE   "G.984.4 & G.983.2"
        ::= { zxGponOmciCallCtrlStatsEntry 7 }

    zxGponOmciCallCtrlStatsEntryStatus OBJECT-TYPE
        SYNTAX      RowStatus
        MAX-ACCESS  read-write
        STATUS      current
        DESCRIPTION
        "This attribute specifies the action of this entry."
        REFERENCE   "G.984.4 & G.983.2"
        ::= { zxGponOmciCallCtrlStatsEntry 8 }

--RTP Monitoring Data
    zxGponOmciRTPStatsTable    OBJECT-TYPE
        SYNTAX      SEQUENCE OF ZxGponOmciRTPStatsEntry
        MAX-ACCESS  not-accessible
        STATUS      current
        DESCRIPTION
            ""
        REFERENCE   "G.984.4 & G.983.2"
        ::= { zxGponOmciStatistics 9 }

    zxGponOmciRTPStatsEntry OBJECT-TYPE
        SYNTAX      ZxGponOmciRTPStatsEntry
        MAX-ACCESS  not-accessible
        STATUS      current
        DESCRIPTION
            "It is entry in the zxGponOmciRTPStatsTable."
        INDEX   { zxGponOltIndex, zxGponONTIndex, zxGponUNIIndex }
        ::= { zxGponOmciRTPStatsTable 1 }

    ZxGponOmciRTPStatsEntry ::=
        SEQUENCE {
            zxGponOmciRTPStatsIntervalEndTime              INTEGER,
            zxGponOmciRTPStatsThresDataId                  INTEGER,
            zxGponOmciRTPStatsRTPErrors                    Unsigned32,
            zxGponOmciRTPStatsPktLoss                      Unsigned32,
            zxGponOmciRTPStatsMaxJitter                    Unsigned32,
            zxGponOmciRTPStatsMaxTimeBtwRTPPkts            Unsigned32,
            zxGponOmciRTPStatsBufUnderflows                Unsigned32,
            zxGponOmciRTPStatsBufOverflows                 Unsigned32,
            zxGponOmciRTPStatsEntryStatus                  RowStatus
        }

    zxGponOmciRTPStatsIntervalEndTime OBJECT-TYPE
        SYNTAX      INTEGER
        MAX-ACCESS  read-only
        STATUS      current
        DESCRIPTION
        ""
        REFERENCE   "G.984.4 & G.983.2"
        ::= { zxGponOmciRTPStatsEntry 1 }

    zxGponOmciRTPStatsThresDataId OBJECT-TYPE
        SYNTAX      INTEGER
        MAX-ACCESS  read-write
        STATUS      current
        DESCRIPTION
        ""
        REFERENCE   "G.984.4 & G.983.2"
        ::= { zxGponOmciRTPStatsEntry 2 }

    zxGponOmciRTPStatsRTPErrors OBJECT-TYPE
        SYNTAX      Unsigned32
        MAX-ACCESS  read-only
        STATUS      current
        DESCRIPTION
        ""
        REFERENCE   "G.984.4 & G.983.2"
        ::= { zxGponOmciRTPStatsEntry 3 }

    zxGponOmciRTPStatsPktLoss OBJECT-TYPE
        SYNTAX      Unsigned32
        MAX-ACCESS  read-only
        STATUS      current
        DESCRIPTION
        ""
        REFERENCE   "G.984.4 & G.983.2"
        ::= { zxGponOmciRTPStatsEntry 4 }

    zxGponOmciRTPStatsMaxJitter OBJECT-TYPE
        SYNTAX      Unsigned32
        MAX-ACCESS  read-only
        STATUS      current
        DESCRIPTION
        ""
        REFERENCE   "G.984.4 & G.983.2"
        ::= { zxGponOmciRTPStatsEntry 5 }

    zxGponOmciRTPStatsMaxTimeBtwRTPPkts OBJECT-TYPE
        SYNTAX      Unsigned32
        MAX-ACCESS  read-only
        STATUS      current
        DESCRIPTION
        ""
        REFERENCE   "G.984.4 & G.983.2"
        ::= { zxGponOmciRTPStatsEntry 6 }

    zxGponOmciRTPStatsBufUnderflows OBJECT-TYPE
        SYNTAX      Unsigned32
        MAX-ACCESS  read-only
        STATUS      current
        DESCRIPTION
        ""
        REFERENCE   "G.984.4 & G.983.2"
        ::= { zxGponOmciRTPStatsEntry 7 }

    zxGponOmciRTPStatsBufOverflows OBJECT-TYPE
        SYNTAX      Unsigned32
        MAX-ACCESS  read-only
        STATUS      current
        DESCRIPTION
        ""
        REFERENCE   "G.984.4 & G.983.2"
        ::= { zxGponOmciRTPStatsEntry 8 }

    zxGponOmciRTPStatsEntryStatus OBJECT-TYPE
        SYNTAX      RowStatus
        MAX-ACCESS  read-write
        STATUS      current
        DESCRIPTION
        "This attribute specifies the action of this entry."
        REFERENCE   "G.984.4 & G.983.2"
        ::= { zxGponOmciRTPStatsEntry 9 }

--SIP Call Initiation Performance Monitoring History Data
    zxGponOmciSIPCallInitStatsTable    OBJECT-TYPE
        SYNTAX      SEQUENCE OF ZxGponOmciSIPCallInitStatsEntry
        MAX-ACCESS  not-accessible
        STATUS      current
        DESCRIPTION
            ""
        REFERENCE   "G.984.4 & G.983.2"
        ::= { zxGponOmciStatistics 10 }

    zxGponOmciSIPCallInitStatsEntry OBJECT-TYPE
        SYNTAX      ZxGponOmciSIPCallInitStatsEntry
        MAX-ACCESS  not-accessible
        STATUS      current
        DESCRIPTION
            "It is entry in the zxGponOmciSIPCallInitStatsTable."
        INDEX   { zxGponOltIndex, zxGponONTIndex, zxGponSIPAgentConfigDataId }
        ::= { zxGponOmciSIPCallInitStatsTable 1 }

    ZxGponOmciSIPCallInitStatsEntry ::=
        SEQUENCE {
            zxGponOmciSIPCallInitStatsIntervalEndTime              INTEGER,
            zxGponOmciSIPCallInitStatsThresDataId                  INTEGER,
            zxGponOmciSIPCallInitStatsConnectFailures              Unsigned32,
            zxGponOmciSIPCallInitStatsValidateFailures             Unsigned32,
            zxGponOmciSIPCallInitStatsTimeoutCounter               Unsigned32,
            zxGponOmciSIPCallInitStatsRxFailures                   Unsigned32,
            zxGponOmciSIPCallInitStatsAuthFailures                 Unsigned32,
            zxGponOmciSIPCallInitStatsEntryStatus                  RowStatus
        }

    zxGponOmciSIPCallInitStatsIntervalEndTime OBJECT-TYPE
        SYNTAX      INTEGER
        MAX-ACCESS  read-only
        STATUS      current
        DESCRIPTION
        ""
        REFERENCE   "G.984.4 & G.983.2"
        ::= { zxGponOmciSIPCallInitStatsEntry 1 }

    zxGponOmciSIPCallInitStatsThresDataId OBJECT-TYPE
        SYNTAX      INTEGER
        MAX-ACCESS  read-write
        STATUS      current
        DESCRIPTION
        ""
        REFERENCE   "G.984.4 & G.983.2"
        ::= { zxGponOmciSIPCallInitStatsEntry 2 }

    zxGponOmciSIPCallInitStatsConnectFailures OBJECT-TYPE
        SYNTAX      Unsigned32
        MAX-ACCESS  read-only
        STATUS      current
        DESCRIPTION
        ""
        REFERENCE   "G.984.4 & G.983.2"
        ::= { zxGponOmciSIPCallInitStatsEntry 3 }

    zxGponOmciSIPCallInitStatsValidateFailures OBJECT-TYPE
        SYNTAX      Unsigned32
        MAX-ACCESS  read-only
        STATUS      current
        DESCRIPTION
        ""
        REFERENCE   "G.984.4 & G.983.2"
        ::= { zxGponOmciSIPCallInitStatsEntry 4 }

    zxGponOmciSIPCallInitStatsTimeoutCounter OBJECT-TYPE
        SYNTAX      Unsigned32
        MAX-ACCESS  read-only
        STATUS      current
        DESCRIPTION
        ""
        REFERENCE   "G.984.4 & G.983.2"
        ::= { zxGponOmciSIPCallInitStatsEntry 5 }

    zxGponOmciSIPCallInitStatsRxFailures OBJECT-TYPE
        SYNTAX      Unsigned32
        MAX-ACCESS  read-only
        STATUS      current
        DESCRIPTION
        ""
        REFERENCE   "G.984.4 & G.983.2"
        ::= { zxGponOmciSIPCallInitStatsEntry 6 }

    zxGponOmciSIPCallInitStatsAuthFailures OBJECT-TYPE
        SYNTAX      Unsigned32
        MAX-ACCESS  read-only
        STATUS      current
        DESCRIPTION
        ""
        REFERENCE   "G.984.4 & G.983.2"
        ::= { zxGponOmciSIPCallInitStatsEntry 7 }

    zxGponOmciSIPCallInitStatsEntryStatus OBJECT-TYPE
        SYNTAX      RowStatus
        MAX-ACCESS  read-write
        STATUS      current
        DESCRIPTION
        "This attribute specifies the action of this entry."
        REFERENCE   "G.984.4 & G.983.2"
        ::= { zxGponOmciSIPCallInitStatsEntry 8 }

--SIP Agent Monitoring History Data
    zxGponOmciSIPAgentStatsTable    OBJECT-TYPE
        SYNTAX      SEQUENCE OF ZxGponOmciSIPAgentStatsEntry
        MAX-ACCESS  not-accessible
        STATUS      current
        DESCRIPTION
            ""
        REFERENCE   "G.984.4 & G.983.2"
        ::= { zxGponOmciStatistics 11 }

    zxGponOmciSIPAgentStatsEntry OBJECT-TYPE
        SYNTAX      ZxGponOmciSIPAgentStatsEntry
        MAX-ACCESS  not-accessible
        STATUS      current
        DESCRIPTION
            "It is entry in the zxGponOmciSIPAgentStatsTable."
        INDEX   { zxGponOltIndex, zxGponONTIndex, zxGponSIPAgentConfigDataId }
        ::= { zxGponOmciSIPAgentStatsTable 1 }

    ZxGponOmciSIPAgentStatsEntry ::=
        SEQUENCE {
            zxGponOmciSIPAgentStatsIntervalEndTime              INTEGER,
            zxGponOmciSIPAgentStatsThresDataId                  INTEGER,
            zxGponOmciSIPAgentStatsTransactions                 Unsigned32,
            zxGponOmciSIPAgentStatsRxInviteReqs                 Unsigned32,
            zxGponOmciSIPAgentStatsRxInviteRetrans              Unsigned32,
            zxGponOmciSIPAgentStatsRxNonInviteReqs              Unsigned32,
            zxGponOmciSIPAgentStatsRxNonInviteRetrans           Unsigned32,
            zxGponOmciSIPAgentStatsRxResponses                  Unsigned32,
            zxGponOmciSIPAgentStatsRxResponseRetrans            Unsigned32,
            zxGponOmciSIPAgentStatsTxInviteReqs                 Unsigned32,
            zxGponOmciSIPAgentStatsTxInviteRetrans              Unsigned32,
            zxGponOmciSIPAgentStatsTxNonInviteReqs              Unsigned32,
            zxGponOmciSIPAgentStatsTxNonInviteRetrans           Unsigned32,
            zxGponOmciSIPAgentStatsTxResponses                  Unsigned32,
            zxGponOmciSIPAgentStatsTxResponseRetrans            Unsigned32,
            zxGponOmciSIPAgentStatsEntryStatus                  RowStatus
        }

    zxGponOmciSIPAgentStatsIntervalEndTime OBJECT-TYPE
        SYNTAX      INTEGER
        MAX-ACCESS  read-only
        STATUS      current
        DESCRIPTION
        ""
        REFERENCE   "G.984.4 & G.983.2"
        ::= { zxGponOmciSIPAgentStatsEntry 1 }

    zxGponOmciSIPAgentStatsThresDataId OBJECT-TYPE
        SYNTAX      INTEGER
        MAX-ACCESS  read-write
        STATUS      current
        DESCRIPTION
        ""
        REFERENCE   "G.984.4 & G.983.2"
        ::= { zxGponOmciSIPAgentStatsEntry 2 }

    zxGponOmciSIPAgentStatsTransactions OBJECT-TYPE
        SYNTAX      Unsigned32
        MAX-ACCESS  read-only
        STATUS      current
        DESCRIPTION
        ""
        REFERENCE   "G.984.4 & G.983.2"
        ::= { zxGponOmciSIPAgentStatsEntry 3 }

    zxGponOmciSIPAgentStatsRxInviteReqs OBJECT-TYPE
        SYNTAX      Unsigned32
        MAX-ACCESS  read-only
        STATUS      current
        DESCRIPTION
        ""
        REFERENCE   "G.984.4 & G.983.2"
        ::= { zxGponOmciSIPAgentStatsEntry 4 }

    zxGponOmciSIPAgentStatsRxInviteRetrans OBJECT-TYPE
        SYNTAX      Unsigned32
        MAX-ACCESS  read-only
        STATUS      current
        DESCRIPTION
        ""
        REFERENCE   "G.984.4 & G.983.2"
        ::= { zxGponOmciSIPAgentStatsEntry 5 }

    zxGponOmciSIPAgentStatsRxNonInviteReqs OBJECT-TYPE
        SYNTAX      Unsigned32
        MAX-ACCESS  read-only
        STATUS      current
        DESCRIPTION
        ""
        REFERENCE   "G.984.4 & G.983.2"
        ::= { zxGponOmciSIPAgentStatsEntry 6 }

    zxGponOmciSIPAgentStatsRxNonInviteRetrans OBJECT-TYPE
        SYNTAX      Unsigned32
        MAX-ACCESS  read-only
        STATUS      current
        DESCRIPTION
        ""
        REFERENCE   "G.984.4 & G.983.2"
        ::= { zxGponOmciSIPAgentStatsEntry 7 }

    zxGponOmciSIPAgentStatsRxResponses OBJECT-TYPE
        SYNTAX      Unsigned32
        MAX-ACCESS  read-only
        STATUS      current
        DESCRIPTION
        ""
        REFERENCE   "G.984.4 & G.983.2"
        ::= { zxGponOmciSIPAgentStatsEntry 8 }

    zxGponOmciSIPAgentStatsRxResponseRetrans OBJECT-TYPE
        SYNTAX      Unsigned32
        MAX-ACCESS  read-only
        STATUS      current
        DESCRIPTION
        ""
        REFERENCE   "G.984.4 & G.983.2"
        ::= { zxGponOmciSIPAgentStatsEntry 9 }

    zxGponOmciSIPAgentStatsTxInviteReqs OBJECT-TYPE
        SYNTAX      Unsigned32
        MAX-ACCESS  read-only
        STATUS      current
        DESCRIPTION
        ""
        REFERENCE   "G.984.4 & G.983.2"
        ::= { zxGponOmciSIPAgentStatsEntry 10 }

    zxGponOmciSIPAgentStatsTxInviteRetrans OBJECT-TYPE
        SYNTAX      Unsigned32
        MAX-ACCESS  read-only
        STATUS      current
        DESCRIPTION
        ""
        REFERENCE   "G.984.4 & G.983.2"
        ::= { zxGponOmciSIPAgentStatsEntry 11 }

    zxGponOmciSIPAgentStatsTxNonInviteReqs OBJECT-TYPE
        SYNTAX      Unsigned32
        MAX-ACCESS  read-only
        STATUS      current
        DESCRIPTION
        ""
        REFERENCE   "G.984.4 & G.983.2"
        ::= { zxGponOmciSIPAgentStatsEntry 12 }

    zxGponOmciSIPAgentStatsTxNonInviteRetrans OBJECT-TYPE
        SYNTAX      Unsigned32
        MAX-ACCESS  read-only
        STATUS      current
        DESCRIPTION
        ""
        REFERENCE   "G.984.4 & G.983.2"
        ::= { zxGponOmciSIPAgentStatsEntry 13 }

    zxGponOmciSIPAgentStatsTxResponses OBJECT-TYPE
        SYNTAX      Unsigned32
        MAX-ACCESS  read-only
        STATUS      current
        DESCRIPTION
        ""
        REFERENCE   "G.984.4 & G.983.2"
        ::= { zxGponOmciSIPAgentStatsEntry 14 }

    zxGponOmciSIPAgentStatsTxResponseRetrans OBJECT-TYPE
        SYNTAX      Unsigned32
        MAX-ACCESS  read-only
        STATUS      current
        DESCRIPTION
        ""
        REFERENCE   "G.984.4 & G.983.2"
        ::= { zxGponOmciSIPAgentStatsEntry 15 }

    zxGponOmciSIPAgentStatsEntryStatus OBJECT-TYPE
        SYNTAX      RowStatus
        MAX-ACCESS  read-write
        STATUS      current
        DESCRIPTION
        "This attribute specifies the action of this entry."
        REFERENCE   "G.984.4 & G.983.2"
        ::= { zxGponOmciSIPAgentStatsEntry 16 }

--MGC Config Data
    zxGponMGCConfigDataTable    OBJECT-TYPE
        SYNTAX      SEQUENCE OF ZxGponMGCConfigDataEntry
        MAX-ACCESS  not-accessible
        STATUS      current
        DESCRIPTION
            "An instance of this managed entity may be associated with one or 
             more VoIP voice CTP managed entities."
        REFERENCE   "G.984.4"
        ::= { zxGponL2Mgmt 65 }
        
    zxGponMGCConfigDataEntry    OBJECT-TYPE
        SYNTAX      ZxGponMGCConfigDataEntry
        MAX-ACCESS  not-accessible
        STATUS      current
        DESCRIPTION
            "It is entry in the zxGponMGCConfigDataTable."
        INDEX   { zxGponOltIndex, zxGponONTIndex, zxGponMGCConfigDataId }
        ::= { zxGponMGCConfigDataTable 1 }

    ZxGponMGCConfigDataEntry ::=
        SEQUENCE {
            zxGponMGCConfigDataId                       INTEGER,
            zxGponMGCConfigDataPrimaryMGC               OCTET STRING,
            zxGponMGCConfigDataPrimaryValidateScheme    INTEGER,
            zxGponMGCConfigDataPrimaryUsername          OCTET STRING,
            zxGponMGCConfigDataPrimaryPassword          OCTET STRING,
            zxGponMGCConfigDataPrimaryRealm             OCTET STRING,
            zxGponMGCConfigDataSecondaryMGC             OCTET STRING,
            zxGponMGCConfigDataSecondaryValidateScheme  INTEGER,
            zxGponMGCConfigDataSecondaryUsername        OCTET STRING,
            zxGponMGCConfigDataSecondaryPassword        OCTET STRING,
            zxGponMGCConfigDataSecondaryRealm           OCTET STRING,
            zxGponMGCConfigDataTCPUDPPort               INTEGER,
            zxGponMGCConfigDataHostId                   INTEGER,
            zxGponMGCConfigDataVersion                  INTEGER,
            zxGponMGCConfigDataMessageFormat            INTEGER,
            zxGponMGCConfigDataMaxRetryTime             INTEGER,
            zxGponMGCConfigDataMaxRetryAttempts         INTEGER,
            zxGponMGCConfigDataServiceChangeDelay       INTEGER,
            zxGponMGCConfigDataTerminationIDbase        OCTET STRING,
            zxGponMGCConfigDataSSVendor                 OCTET STRING,
            zxGponMGCConfigDataEntryStatus              RowStatus
        }

    zxGponMGCConfigDataId   OBJECT-TYPE
        SYNTAX      INTEGER
        MAX-ACCESS  not-accessible
        STATUS      current
        DESCRIPTION
        "This attribute provides a unique number for each instance of this managed entity.
        (1~n)(R, Set-by-create) (mandatory) (2 bytes)"
        REFERENCE   "G.984.4 section 9.9.16    MGC config data"
        ::= { zxGponMGCConfigDataEntry 1 }
        
    zxGponMGCConfigDataPrimaryMGC    OBJECT-TYPE
        SYNTAX      OCTET STRING(SIZE(0..128))
        MAX-ACCESS  read-write
        STATUS      current
        DESCRIPTION
        "This attribute points to a network address ME that contains the name (IP address 
        or resolved name) of the primary MGC that controls the signalling  messages. The 
        port is optional and defaults to 2944 for text message formats and 2955 for binary
        message formats. (R, W, Set-by-create) (mandatory) (2 bytes)"
        REFERENCE   "G.984.4 section 9.9.16    MGC config data"
        ::= { zxGponMGCConfigDataEntry 2 }
        
    zxGponMGCConfigDataPrimaryValidateScheme OBJECT-TYPE
        SYNTAX      INTEGER{
                    disable(1),
                    md5(2),
                    basic(3)
                    }
        MAX-ACCESS  read-write
        STATUS      current
        DESCRIPTION
        ""
        REFERENCE   ""
        ::= { zxGponMGCConfigDataEntry 3 }

    zxGponMGCConfigDataPrimaryUsername    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 4 }

    zxGponMGCConfigDataPrimaryPassword    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 5 }

    zxGponMGCConfigDataPrimaryRealm    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 6 }

    zxGponMGCConfigDataSecondaryMGC    OBJECT-TYPE
        SYNTAX      OCTET STRING(SIZE(0..128))
        MAX-ACCESS  read-write
        STATUS      current
        DESCRIPTION
        "This attribute points to a network address ME that contains the name (IP address 
        or resolved name) of the secondary or backup MGC that controls the signalling 
        messages. The port is optional and defaults to 2944 for text message formats and 
        2955 for binary message formats. (R, W, Set-by-create) (mandatory) (2 bytes)"
        REFERENCE   "G.984.4 section 9.9.16    MGC config data"
        ::= { zxGponMGCConfigDataEntry 7 }
           
    zxGponMGCConfigDataSecondaryValidateScheme OBJECT-TYPE
        SYNTAX      INTEGER{
                    disable(1),
                    md5(2),
                    basic(3)
                    }
        MAX-ACCESS  read-write
        STATUS      current
        DESCRIPTION
        ""
        REFERENCE   ""
        ::= { zxGponMGCConfigDataEntry 8 }

    zxGponMGCConfigDataSecondaryUsername    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 9 }
      
    zxGponMGCConfigDataSecondaryPassword    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 10 }

    zxGponMGCConfigDataSecondaryRealm    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 11 }

    zxGponMGCConfigDataTCPUDPPort    OBJECT-TYPE
        SYNTAX      INTEGER
        MAX-ACCESS  read-write
        STATUS      current
        DESCRIPTION
        "This attribute specifies the port(1~65535) of TCP/UDP used for communication
        with the MGC. (R, W, Set-by-create) (mandatory) (2 bytes)"
        REFERENCE   "G.984.4 section 9.9.16    MGC config data"
        ::={ zxGponMGCConfigDataEntry 12 }
  
      zxGponMGCConfigDataHostId OBJECT-TYPE
        SYNTAX      INTEGER
        MAX-ACCESS  read-write
        STATUS      current
        DESCRIPTION
        ""
        REFERENCE   ""
        ::= { zxGponMGCConfigDataEntry 13 }
    
    zxGponMGCConfigDataVersion    OBJECT-TYPE
        SYNTAX      INTEGER
        MAX-ACCESS  read-write    
        STATUS      current
        DESCRIPTION
        "This integer attribute reports the version(1~255) of the Megaco protocol in use. 
        (R, W, Set-by-create) (mandatory) (1 byte)"
        REFERENCE   "G.984.4 section 9.9.16    MGC config data"
        ::={ zxGponMGCConfigDataEntry 14 }
        
    zxGponMGCConfigDataMessageFormat    OBJECT-TYPE
        SYNTAX      INTEGER{
                    text-long(1),
                    text-short(2),
                    binary(3)
                    }
        MAX-ACCESS  read-write
        STATUS      current
        DESCRIPTION
        "This attribute defines the message format. Valid values are:
        0    Text long
        1    Text short
        2    Binary
        The default value is 0. (R, W, Set-by-create) (mandatory) (1 byte)"
        REFERENCE   "G.984.4 section 9.9.16    MGC config data"
        ::={ zxGponMGCConfigDataEntry 15 }
        
    zxGponMGCConfigDataMaxRetryTime    OBJECT-TYPE
        SYNTAX      INTEGER   
        MAX-ACCESS  read-write
        STATUS      current
        DESCRIPTION
        "This attribute specifies the maximum retry time for MGC transactions, in seconds.
        The default value 0 specifies vendor-specific implementation (R, W) (optional) (2 bytes)"
        REFERENCE   "G.984.4 section 9.9.16    MGC config data"
        ::={ zxGponMGCConfigDataEntry 16 }
        
    zxGponMGCConfigDataMaxRetryAttempts    OBJECT-TYPE
        SYNTAX      INTEGER   
        MAX-ACCESS  read-write
        STATUS      current
        DESCRIPTION
        "This attribute specifies the maximum number of times a message is retransmitted
        to the MGC. The default value 0 specifies vendor-specific implementation 
        (R, W, Set-by-create) (optional) (2 bytes)"   
        REFERENCE   "G.984.4 section 9.9.16    MGC config data"
        ::={ zxGponMGCConfigDataEntry 17 }
        
    zxGponMGCConfigDataServiceChangeDelay    OBJECT-TYPE
        SYNTAX      INTEGER   
        MAX-ACCESS  read-write
        STATUS      current 
        DESCRIPTION
        "The attribute specifies the service status delay time for changes in line service
        status. This attribute is specified in seconds. The default value 0 specifies no 
        delay. (R, W) (optional) (2 bytes)"   
        REFERENCE   "G.984.4 section 9.9.16    MGC config data"
        ::={ zxGponMGCConfigDataEntry 18 }       
        
    zxGponMGCConfigDataTerminationIDbase   OBJECT-TYPE
        SYNTAX      OCTET STRING (SIZE(0..25))
        MAX-ACCESS  read-write
        STATUS      current 
        DESCRIPTION
        "The attribute specifies the base string for the H.248 physical termination id(s)
        for this ONT. This string is intended to uniquely identify an ONT. Vendor specific
        termination identifiers (i.e. port ids) are optionally added to this string to
        uniquely identify a termination on a specific ONT. (R, W) (optional) (25 bytes)"
        REFERENCE   "G.984.4 section 9.9.16    MGC config data"
        ::={ zxGponMGCConfigDataEntry 19 }    

    zxGponMGCConfigDataSSVendor   OBJECT-TYPE
        SYNTAX      OCTET STRING (SIZE(0..4))
        MAX-ACCESS  read-write
        STATUS      current 
        DESCRIPTION
        "This attribute identifies the gateway softswitch vendor. 
         The format is four ASCII coded alphabetic characters [A..Z] as defined in ANSI T1.220. 
         A value of four null characters indicates no particular vendor. (R, W, Set-by-create) (mandatory) (4 bytes)"
        REFERENCE   "G.984.4 section 9.9.16    MGC config data"
        ::={ zxGponMGCConfigDataEntry 20 }    
        
    zxGponMGCConfigDataEntryStatus OBJECT-TYPE
        SYNTAX      RowStatus
        MAX-ACCESS  read-write
        STATUS      current
        DESCRIPTION
        "This attribute specifies the action of this entry."
        REFERENCE   "G.984.4 section 9.9.16    MGC config data"
        ::= { zxGponMGCConfigDataEntry 21 }
        
--MGC performance monitoring history data
    zxGponOmciMGCStatsTable    OBJECT-TYPE
        SYNTAX      SEQUENCE OF ZxGponOmciMGCStatsEntry
        MAX-ACCESS  not-accessible
        STATUS      current
        DESCRIPTION
            "An instance of this managed entity is associated with an instance of the
            MGC config data or MGC config portal ME."
        REFERENCE   "G.984.4"
        ::= { zxGponOmciStatistics 12 }
        
    zxGponOmciMGCStatsEntry    OBJECT-TYPE
        SYNTAX      ZxGponOmciMGCStatsEntry
        MAX-ACCESS  not-accessible
        STATUS      current
        DESCRIPTION
            "It is entry in the zxGponOmciMGCStatsTable."
        INDEX   { zxGponOltIndex, zxGponONTIndex, zxGponMGCConfigDataId }
        ::= { zxGponOmciMGCStatsTable 1 }
    
    ZxGponOmciMGCStatsEntry ::=
        SEQUENCE {
            zxGponOmciMGCStatsIntervalEndTime         INTEGER,
            zxGponOmciMGCStatsThresholdDataId         INTEGER,
            zxGponOmciMGCStatsRecvMsg                 INTEGER,
            zxGponOmciMGCStatsRecvOctets              INTEGER,
            zxGponOmciMGCStatsSendMsg                 INTEGER,
            zxGponOmciMGCStatsSendOctets              INTEGER,
            zxGponOmciMGCStatsProtocolErrors          INTEGER,
            zxGponOmciMGCStatsTransLosses             INTEGER,
            zxGponOmciMGCStatsLastEvent               INTEGER,
            zxGponOmciMGCStatsLastEventTime           INTEGER,
            zxGponOmciMGCStatsLastResetTime           INTEGER,
            zxGponOmciMGCStatsEntryStatus             RowStatus
        }
        
    zxGponOmciMGCStatsIntervalEndTime   OBJECT-TYPE
        SYNTAX      INTEGER
        MAX-ACCESS  read-only
        STATUS      current
        DESCRIPTION
        "This attribute identifies the most recently finished 15-minute interval. (R) (mandatory) (1 byte)"
        REFERENCE   "G.984.4 section    9.9.17    MGC performance monitoring history data"
        ::= { zxGponOmciMGCStatsEntry 1 }

    zxGponOmciMGCStatsThresholdDataId   OBJECT-TYPE
        SYNTAX      INTEGER
        MAX-ACCESS  read-write
        STATUS      current
        DESCRIPTION
        "This attribute points to an instance of the threshold data  managed entity 
        that contains PM threshold values."
        REFERENCE   "G.984.4 section    9.9.17    MGC performance monitoring history data"
        ::= { zxGponOmciMGCStatsEntry 2 }
   
    zxGponOmciMGCStatsRecvMsg   OBJECT-TYPE
        SYNTAX      INTEGER
        MAX-ACCESS  read-only
        STATUS      current
        DESCRIPTION
        "This attribute counts the number of received Megaco messages on this association,
        as defined by H.341. (R) (mandatory) (4 bytes)"
        REFERENCE   "G.984.4 section    9.9.17    MGC performance monitoring history data"
        ::= { zxGponOmciMGCStatsEntry 3 }

    zxGponOmciMGCStatsRecvOctets   OBJECT-TYPE
        SYNTAX      INTEGER
        MAX-ACCESS  read-only
        STATUS      current
        DESCRIPTION
        "This attribute counts the total number of octets received on this association, 
        as defined by H.341. (R) (mandatory) (4 bytes)"
        REFERENCE   "G.984.4 section    9.9.17    MGC performance monitoring history data"
        ::= { zxGponOmciMGCStatsEntry 4 }
        
    zxGponOmciMGCStatsSendMsg   OBJECT-TYPE
        SYNTAX      INTEGER
        MAX-ACCESS  read-only
        STATUS      current
        DESCRIPTION
        "This attribute counts the total number of Megaco messages sent over this association,
        as defined by H.341. (R) (mandatory) (4 bytes)"
        REFERENCE   "G.984.4 section    9.9.17    MGC performance monitoring history data"
        ::= { zxGponOmciMGCStatsEntry 5 }

    zxGponOmciMGCStatsSendOctets   OBJECT-TYPE
        SYNTAX      INTEGER
        MAX-ACCESS  read-only
        STATUS      current
        DESCRIPTION
        "This attribute counts the total number of octets sent over this association, 
        as defined by H.341. (R) (mandatory) (4 bytes)"
        REFERENCE   "G.984.4 section    9.9.17    MGC performance monitoring history data"
        ::= { zxGponOmciMGCStatsEntry 6 }

    zxGponOmciMGCStatsProtocolErrors   OBJECT-TYPE
        SYNTAX      INTEGER
        MAX-ACCESS  read-only
        STATUS      current
        DESCRIPTION
        "This attribute counts the total number of errors detected on this association, 
        as defined by H.341. This includes:syntax errors detected in a given received message,
          outgoing transactions that failed for protocol reasons.(R) (mandatory) (4 bytes)"
        REFERENCE   "G.984.4 section    9.9.17    MGC performance monitoring history data"
        ::= { zxGponOmciMGCStatsEntry 7 }

    zxGponOmciMGCStatsTransLosses   OBJECT-TYPE
        SYNTAX      INTEGER
        MAX-ACCESS  read-only
        STATUS      current
        DESCRIPTION
        "This attribute counts the total number of transport losses (for example, socket problems)
        detected on this association. A link loss is defined as loss of communication with the 
        remote entity due to hardware/transient problems, or problems in related software.
        (R) (mandatory) (4 bytes)"
        REFERENCE   "G.984.4 section    9.9.17    MGC performance monitoring history data"
        ::= { zxGponOmciMGCStatsEntry 8 }
        
    zxGponOmciMGCStatsLastEvent   OBJECT-TYPE
        SYNTAX      INTEGER{
                    no-event(1),
                    link-up(2),
                    link-down(3),
                    persistent-error(4),
                    local-shutdown(5),
                    failover-down(6)
                    } 
        MAX-ACCESS  read-only
        STATUS      current
        DESCRIPTION
        "This attribute reports the last event detected on this association. 
        This includes events such as the link failing or being set up."
        REFERENCE   "G.984.4 section    9.9.17    MGC performance monitoring history data"
        ::= { zxGponOmciMGCStatsEntry 9 }
        
    zxGponOmciMGCStatsLastEventTime   OBJECT-TYPE
        SYNTAX      INTEGER
        MAX-ACCESS  read-only
        STATUS      current
        DESCRIPTION
        "This attribute reports the time in seconds since the last event on
        this association was detected, as defined by H.341. (R) (mandatory) (4 bytes)"
        REFERENCE   "G.984.4 section    9.9.17    MGC performance monitoring history data"
        ::= { zxGponOmciMGCStatsEntry 10 }

    zxGponOmciMGCStatsLastResetTime   OBJECT-TYPE
        SYNTAX      INTEGER
        MAX-ACCESS  read-only
        STATUS      current
        DESCRIPTION
        "This attribute reports the time in seconds since these statistics were last reset, 
        as defined by H.341. Under normal circumstances, a get action on this attribute would 
        return 900 seconds to indicate a completed 15-minute interval. (R) (mandatory) (4 bytes)"
        REFERENCE   "G.984.4 section    9.9.17    MGC performance monitoring history data"
        ::= { zxGponOmciMGCStatsEntry 11 }
        
    zxGponOmciMGCStatsEntryStatus OBJECT-TYPE
        SYNTAX      RowStatus
        MAX-ACCESS  read-write
        STATUS      current
        DESCRIPTION
        "This attribute specifies the action of this entry."
        REFERENCE   "G.984.4 section    9.9.17    MGC performance monitoring history data"
        ::= { zxGponOmciMGCStatsEntry 12 }


--CES performance monitoring history data
    zxGponOmciCESStatsTable    OBJECT-TYPE
        SYNTAX      SEQUENCE OF ZxGponOmciCESStatsEntry
        MAX-ACCESS  not-accessible
        STATUS      current
        DESCRIPTION
            "Performance monitoring history data of Physical path termination point CES UNI."
        REFERENCE
           "G.984.4, CES physical interface performance monitoring history data,
        Pseudowire performance monitoring history data"
        ::= { zxGponOmciStatistics 13 }
        
    zxGponOmciCESStatsEntry    OBJECT-TYPE
        SYNTAX      ZxGponOmciCESStatsEntry
        MAX-ACCESS  not-accessible
        STATUS      current
        DESCRIPTION
            "It is entry in the zxGponOmciCESStatsTable."
        INDEX   { zxGponOltIndex, zxGponONTIndex, zxGponUNIIndex }
        ::= { zxGponOmciCESStatsTable 1 }
    
    ZxGponOmciCESStatsEntry ::=
        SEQUENCE {
            zxGponOmciCESStatsIntervalEndTime               INTEGER,
            zxGponOmciCESStatsThresholdDataId               INTEGER,
            zxGponOmciCESStatsDownPkts                      Unsigned32,
            zxGponOmciCESStatsUpPkts                        Unsigned32,
            zxGponOmciCESStatsDownMissingPkts               Unsigned32,
            zxGponOmciCESStatsDownReorderedPkts             Unsigned32,
            zxGponOmciCESStatsDownMisorderedPkts            Unsigned32,
            zxGponOmciCESStatsDownBufUnderrunOrOverrunPkts  Unsigned32,
            zxGponOmciCESStatsDownMalformedPkts             Unsigned32,
            zxGponOmciCESStatsDownStrayPkts                 Unsigned32,
            zxGponOmciCESStatsDownRemotePktLoss             Unsigned32,
            zxGponOmciCESStatsUpTDMLbitPkts                 Unsigned32,
            zxGponOmciCESStatsDownErrSeconds                Unsigned32,
            zxGponOmciCESStatsDownSeverelyErrSeconds        Unsigned32,
            zxGponOmciCESStatsDownUnavailableSeconds        Unsigned32,
--            zxGponOmciCESStatsUpErrSeconds                  Unsigned32,
--            zxGponOmciCESStatsUpSeverelyErrSeconds          Unsigned32,
--            zxGponOmciCESStatsUpBurstErrSeconds             Unsigned32,
--            zxGponOmciCESStatsUpUnavailableSeconds          Unsigned32,
--            zxGponOmciCESStatsUpControlledSlipSeconds       Unsigned32,
            zxGponOmciCESStatsEntryStatus                   RowStatus
        }

    zxGponOmciCESStatsIntervalEndTime   OBJECT-TYPE
        SYNTAX      INTEGER
        MAX-ACCESS  read-only
        STATUS      current
        DESCRIPTION
        ""
        REFERENCE   "G.984.4, Pseudowire performance monitoring history data"
        ::= { zxGponOmciCESStatsEntry 1 }

    zxGponOmciCESStatsThresholdDataId   OBJECT-TYPE
        SYNTAX      INTEGER
        MAX-ACCESS  read-write
        STATUS      current
        DESCRIPTION
        ""
        REFERENCE   "G.984.4, Pseudowire performance monitoring history data"
        ::= { zxGponOmciCESStatsEntry 2 }

    zxGponOmciCESStatsDownPkts   OBJECT-TYPE
        SYNTAX      Unsigned32
        MAX-ACCESS  read-only
        STATUS      current
        DESCRIPTION
        ""
        REFERENCE   "G.984.4, Pseudowire performance monitoring history data"
        ::= { zxGponOmciCESStatsEntry 3 }

    zxGponOmciCESStatsUpPkts   OBJECT-TYPE
        SYNTAX      Unsigned32
        MAX-ACCESS  read-only
        STATUS      current
        DESCRIPTION
        ""
        REFERENCE   "G.984.4, Pseudowire performance monitoring history data"
        ::= { zxGponOmciCESStatsEntry 4 }

    zxGponOmciCESStatsDownMissingPkts   OBJECT-TYPE
        SYNTAX      Unsigned32
        MAX-ACCESS  read-only
        STATUS      current
        DESCRIPTION
        ""
        REFERENCE   "G.984.4, Pseudowire performance monitoring history data"
        ::= { zxGponOmciCESStatsEntry 5 }

    zxGponOmciCESStatsDownReorderedPkts   OBJECT-TYPE
        SYNTAX      Unsigned32
        MAX-ACCESS  read-only
        STATUS      current
        DESCRIPTION
        ""
        REFERENCE   "G.984.4, Pseudowire performance monitoring history data"
        ::= { zxGponOmciCESStatsEntry 6 }

    zxGponOmciCESStatsDownMisorderedPkts   OBJECT-TYPE
        SYNTAX      Unsigned32
        MAX-ACCESS  read-only
        STATUS      current
        DESCRIPTION
        ""
        REFERENCE   "G.984.4, Pseudowire performance monitoring history data"
        ::= { zxGponOmciCESStatsEntry 7 }

    zxGponOmciCESStatsDownBufUnderrunOrOverrunPkts   OBJECT-TYPE
        SYNTAX      Unsigned32
        MAX-ACCESS  read-only
        STATUS      current
        DESCRIPTION
        ""
        REFERENCE   "G.984.4, Pseudowire performance monitoring history data"
        ::= { zxGponOmciCESStatsEntry 8 }

    zxGponOmciCESStatsDownMalformedPkts   OBJECT-TYPE
        SYNTAX      Unsigned32
        MAX-ACCESS  read-only
        STATUS      current
        DESCRIPTION
        ""
        REFERENCE   "G.984.4, Pseudowire performance monitoring history data"
        ::= { zxGponOmciCESStatsEntry 9 }

    zxGponOmciCESStatsDownStrayPkts   OBJECT-TYPE
        SYNTAX      Unsigned32
        MAX-ACCESS  read-only
        STATUS      current
        DESCRIPTION
        ""
        REFERENCE   "G.984.4, Pseudowire performance monitoring history data"
        ::= { zxGponOmciCESStatsEntry 10 }

    zxGponOmciCESStatsDownRemotePktLoss   OBJECT-TYPE
        SYNTAX      Unsigned32
        MAX-ACCESS  read-only
        STATUS      current
        DESCRIPTION
        ""
        REFERENCE   "G.984.4, Pseudowire performance monitoring history data"
        ::= { zxGponOmciCESStatsEntry 11 }

    zxGponOmciCESStatsUpTDMLbitPkts   OBJECT-TYPE
        SYNTAX      Unsigned32
        MAX-ACCESS  read-only
        STATUS      current
        DESCRIPTION
        ""
        REFERENCE   "G.984.4, Pseudowire performance monitoring history data"
        ::= { zxGponOmciCESStatsEntry 12 }

    zxGponOmciCESStatsDownErrSeconds   OBJECT-TYPE
        SYNTAX      Unsigned32
        MAX-ACCESS  read-only
        STATUS      current
        DESCRIPTION
        ""
        REFERENCE   "G.984.4, Pseudowire performance monitoring history data"
        ::= { zxGponOmciCESStatsEntry 13 }

    zxGponOmciCESStatsDownSeverelyErrSeconds   OBJECT-TYPE
        SYNTAX      Unsigned32
        MAX-ACCESS  read-only
        STATUS      current
        DESCRIPTION
        ""
        REFERENCE   "G.984.4, Pseudowire performance monitoring history data"
        ::= { zxGponOmciCESStatsEntry 14 }

    zxGponOmciCESStatsDownUnavailableSeconds   OBJECT-TYPE
        SYNTAX      Unsigned32
        MAX-ACCESS  read-only
        STATUS      current
        DESCRIPTION
        ""
        REFERENCE   "G.984.4, Pseudowire performance monitoring history data"
        ::= { zxGponOmciCESStatsEntry 15 }

--    zxGponOmciCESStatsUpErrSeconds   OBJECT-TYPE
--        SYNTAX      Unsigned32
--        MAX-ACCESS  read-only
--        STATUS      current
--        DESCRIPTION
--        ""
--        REFERENCE   "G.984.4, CES physical interface performance monitoring history data"
--        ::= { zxGponOmciCESStatsEntry 16 }
--
--    zxGponOmciCESStatsUpSeverelyErrSeconds   OBJECT-TYPE
--        SYNTAX      Unsigned32
--        MAX-ACCESS  read-only
--        STATUS      current
--        DESCRIPTION
--        ""
--        REFERENCE   "G.984.4, CES physical interface performance monitoring history data"
--        ::= { zxGponOmciCESStatsEntry 17 }
--
--    zxGponOmciCESStatsUpBurstErrSeconds   OBJECT-TYPE
--        SYNTAX      Unsigned32
--        MAX-ACCESS  read-only
--        STATUS      current
--        DESCRIPTION
--        ""
--        REFERENCE   "G.984.4, CES physical interface performance monitoring history data"
--        ::= { zxGponOmciCESStatsEntry 18 }
--
--    zxGponOmciCESStatsUpUnavailableSeconds   OBJECT-TYPE
--        SYNTAX      Unsigned32
--        MAX-ACCESS  read-only
--        STATUS      current
--        DESCRIPTION
--        ""
--        REFERENCE   "G.984.4, CES physical interface performance monitoring history data"
--        ::= { zxGponOmciCESStatsEntry 19 }
--
--    zxGponOmciCESStatsUpControlledSlipSeconds   OBJECT-TYPE
--        SYNTAX      Unsigned32
--        MAX-ACCESS  read-only
--        STATUS      current
--        DESCRIPTION
--        ""
--        REFERENCE   "G.984.4, CES physical interface performance monitoring history data"
--        ::= { zxGponOmciCESStatsEntry 20 }
        
    zxGponOmciCESStatsEntryStatus OBJECT-TYPE
        SYNTAX      RowStatus
        MAX-ACCESS  read-write
        STATUS      current
        DESCRIPTION
        ""
        REFERENCE   "G.984.4"
        ::= { zxGponOmciCESStatsEntry 25 }

--Private Eth Statistics
    zxGponOmciPrivateEthStatsTable    OBJECT-TYPE
        SYNTAX      SEQUENCE OF ZxGponOmciPrivateEthStatsEntry
        MAX-ACCESS  not-accessible
        STATUS      current
        DESCRIPTION
            ""
        REFERENCE   "Vender specific Ethernet performance
                     Ethernet performance monitoring history data 4"
        ::= { zxGponOmciStatistics 14 }

    zxGponOmciPrivateEthStatsEntry OBJECT-TYPE
        SYNTAX      ZxGponOmciPrivateEthStatsEntry
        MAX-ACCESS  not-accessible
        STATUS      current
        DESCRIPTION
            "It is entry in the zxGponOmciPrivateEthStatsTable."
        INDEX   { zxGponOltIndex, zxGponONTIndex, zxGponUNIIndex }
        ::= { zxGponOmciPrivateEthStatsTable 1 }

    ZxGponOmciPrivateEthStatsEntry ::=
        SEQUENCE {
            zxGponOmciPrivateEthStatsIntervalEndTime  INTEGER,
            zxGponOmciPrivateEthStatsThresDataId      INTEGER,
            zxGponOmciPrivateEthStatsRxBroadcast      Unsigned32,
            zxGponOmciPrivateEthStatsRxUnicast        Unsigned32,
            zxGponOmciPrivateEthStatsRxMulticast      Unsigned32,
            zxGponOmciPrivateEthStatsRxDiscarded      Unsigned32,
            zxGponOmciPrivateEthStatsTxBroadcast      Unsigned32,
            zxGponOmciPrivateEthStatsTxUnicast        Unsigned32,
            zxGponOmciPrivateEthStatsTxMulticast      Unsigned32,
            zxGponOmciPrivateEthStatsTxDiscarded      Unsigned32,
            zxGponOmciPrivateEthStatsTxPauseFrames    Unsigned32,
            zxGponOmciPrivateEthStatsRxPauseFrames    Unsigned32,
            zxGponOmciPrivateEthStatsTxErroredOctets  Unsigned32,
            zxGponOmciPrivateEthStatsRxErroredOctets  Unsigned32,
            zxGponOmciPrivateEthStatsEntryStatus      RowStatus
        }

    zxGponOmciPrivateEthStatsIntervalEndTime OBJECT-TYPE
        SYNTAX      INTEGER
        MAX-ACCESS  read-only
        STATUS      current
        DESCRIPTION
        ""
        REFERENCE   "G.984.4"
        ::= { zxGponOmciPrivateEthStatsEntry 1 }

    zxGponOmciPrivateEthStatsThresDataId OBJECT-TYPE
        SYNTAX      INTEGER
        MAX-ACCESS  read-write
        STATUS      current
        DESCRIPTION
        ""
        REFERENCE   "G.984.4"
        ::= { zxGponOmciPrivateEthStatsEntry 2 }

    zxGponOmciPrivateEthStatsRxBroadcast OBJECT-TYPE
        SYNTAX      Unsigned32
        MAX-ACCESS  read-only
        STATUS      current
        DESCRIPTION
        ""
        REFERENCE   "G.984.4 Ethernet performance monitoring history data"
        ::= { zxGponOmciPrivateEthStatsEntry 3 }

    zxGponOmciPrivateEthStatsRxUnicast OBJECT-TYPE
        SYNTAX      Unsigned32
        MAX-ACCESS  read-only
        STATUS      current
        DESCRIPTION
        ""
        REFERENCE   "G.984.4 Ethernet performance monitoring history data"
        ::= { zxGponOmciPrivateEthStatsEntry 4 }

    zxGponOmciPrivateEthStatsRxMulticast OBJECT-TYPE
        SYNTAX      Unsigned32
        MAX-ACCESS  read-only
        STATUS      current
        DESCRIPTION
        ""
        REFERENCE   "G.984.4 Ethernet performance monitoring history data"
        ::= { zxGponOmciPrivateEthStatsEntry 5 }
        
    zxGponOmciPrivateEthStatsRxDiscarded OBJECT-TYPE
        SYNTAX      Unsigned32
        MAX-ACCESS  read-only
        STATUS      current
        DESCRIPTION
        ""
        REFERENCE   "G.984.4 Ethernet performance monitoring history data"
        ::= { zxGponOmciPrivateEthStatsEntry 6 }
        
    zxGponOmciPrivateEthStatsTxBroadcast OBJECT-TYPE
        SYNTAX      Unsigned32
        MAX-ACCESS  read-only
        STATUS      current
        DESCRIPTION
        ""
        REFERENCE   "G.984.4 Ethernet performance monitoring history data"
        ::= { zxGponOmciPrivateEthStatsEntry 7 }

    zxGponOmciPrivateEthStatsTxUnicast OBJECT-TYPE
        SYNTAX      Unsigned32
        MAX-ACCESS  read-only
        STATUS      current
        DESCRIPTION
        ""
        REFERENCE   "G.984.4 Ethernet performance monitoring history data"
        ::= { zxGponOmciPrivateEthStatsEntry 8 }
        
    zxGponOmciPrivateEthStatsTxMulticast OBJECT-TYPE
        SYNTAX      Unsigned32
        MAX-ACCESS  read-only
        STATUS      current
        DESCRIPTION
        ""
        REFERENCE   "G.984.4 Ethernet performance monitoring history data"
        ::= { zxGponOmciPrivateEthStatsEntry 9 }

    zxGponOmciPrivateEthStatsTxDiscarded OBJECT-TYPE
        SYNTAX      Unsigned32
        MAX-ACCESS  read-only
        STATUS      current
        DESCRIPTION
        ""
        REFERENCE   "G.984.4 Ethernet performance monitoring history data"
        ::= { zxGponOmciPrivateEthStatsEntry 10 }

    zxGponOmciPrivateEthStatsTxPauseFrames OBJECT-TYPE
        SYNTAX      Unsigned32
        MAX-ACCESS  read-only
        STATUS      current
        DESCRIPTION
        ""
        REFERENCE   "G.984.4 Ethernet performance monitoring history data"
        ::= { zxGponOmciPrivateEthStatsEntry 11 }
    
    zxGponOmciPrivateEthStatsRxPauseFrames OBJECT-TYPE
        SYNTAX      Unsigned32
        MAX-ACCESS  read-only
        STATUS      current
        DESCRIPTION
        ""
        REFERENCE   "G.984.4 Ethernet performance monitoring history data"
        ::= { zxGponOmciPrivateEthStatsEntry 12 }
        
    zxGponOmciPrivateEthStatsTxErroredOctets OBJECT-TYPE
        SYNTAX      Unsigned32
        MAX-ACCESS  read-only
        STATUS      current
        DESCRIPTION
        ""
        REFERENCE   "G.984.4 Ethernet performance monitoring history data"
        ::= { zxGponOmciPrivateEthStatsEntry 13 }
        
    zxGponOmciPrivateEthStatsRxErroredOctets OBJECT-TYPE
        SYNTAX      Unsigned32
        MAX-ACCESS  read-only
        STATUS      current
        DESCRIPTION
        ""
        REFERENCE   "G.984.4 Ethernet performance monitoring history data"
        ::= { zxGponOmciPrivateEthStatsEntry 14 }

    zxGponOmciPrivateEthStatsEntryStatus OBJECT-TYPE
        SYNTAX      RowStatus
        MAX-ACCESS  read-write
        STATUS      current
        DESCRIPTION
        "This attribute specifies the action of this entry."
        REFERENCE   "G.984.4"
        ::= { zxGponOmciPrivateEthStatsEntry 20 }


--G.984.4 9.3.13 Extended VLAN tagging operation configuration data
    zxGponExVLANTagConfigTable     OBJECT-TYPE
        SYNTAX      SEQUENCE OF ZxGponExVLANTagConfigEntry
        MAX-ACCESS  not-accessible
        STATUS      current
        DESCRIPTION
            "This managed entity organizes data associated with VLAN tagging. 
            Regardless of its point of attachment, the specified tagging operations 
            refer to the upstream direction. Instances of this managed entity are 
            created and deleted by the OLT."
        REFERENCE   "G.984.4 9.3.13 Extended VLAN tagging operation configuration data"
        ::= { zxGponL2Mgmt 66 }
        
    zxGponExVLANTagConfigEntry OBJECT-TYPE
        SYNTAX      ZxGponExVLANTagConfigEntry
        MAX-ACCESS  not-accessible
        STATUS      current
        DESCRIPTION
            "It is entry in the zxGponExVLANTagConfigTable."
        INDEX   { zxGponOltIndex, zxGponONTIndex, zxGponExVlanIfType, zxGponExVlanIndex }
        ::= { zxGponExVLANTagConfigTable 1 }
        
    ZxGponExVLANTagConfigEntry ::=
        SEQUENCE {
            zxGponExVlanIfType                   INTEGER,
            zxGponExVlanIndex                    INTEGER,
            zxGponExVLANTagConfigInputTPID       INTEGER,
            zxGponExVLANTagConfigOutputTPID      INTEGER,
            zxGponExVLANTagConfigDownStreamMode  INTEGER,
            zxGponExVLANTagConfigEntryStatus     RowStatus,
            zxGponDscp2CosProfileIndex            INTEGER
        }

     zxGponExVlanIfType OBJECT-TYPE
        SYNTAX      INTEGER
        MAX-ACCESS  not-accessible
        STATUS      current
        DESCRIPTION
            "This attribute indicates the type of interface.
            1 eth uni
            2 uplink
            3 IP host"
        ::= { zxGponExVLANTagConfigEntry 1}

     zxGponExVlanIndex OBJECT-TYPE
        SYNTAX      INTEGER
        MAX-ACCESS  not-accessible
        STATUS      current
        DESCRIPTION
            "This attribute indicates the type of interface.
            For eth UNI:
            The third byte specifies the slot Id associated with this UNI;the forth byte 
            specifies the port Id associated with this UNI.
            For UpLink:
            The first 2 bytes specifies the slot Id and bridge group Id associated with the bridge;
            the second 2 bytes specifies the bridge port associated with this uplink.(4 bytes)
            For IPHostConfigDataId:
            The third and forth bytes provides a unique number for each instance of this managed entity.(4 bytes)"
        ::= { zxGponExVLANTagConfigEntry 2}

    zxGponExVLANTagConfigInputTPID     OBJECT-TYPE
        SYNTAX      INTEGER
        MAX-ACCESS  read-write
        STATUS      current
        DESCRIPTION
        "This attribute gives the special TPID value for operations 
        on the input (filtering) side of the table. Typical values 
        include 0x8a88 and 0x9100. (R, W) (mandatory) (2 bytes)."
        ::= { zxGponExVLANTagConfigEntry 3 }    
   
    zxGponExVLANTagConfigOutputTPID     OBJECT-TYPE
        SYNTAX      INTEGER
        MAX-ACCESS  read-write
        STATUS      current
        DESCRIPTION
        "This attribute gives the special TPID value for operations
         on the output (tagging) side of the table. Typical values 
         include 0x8a88 and 0x9100. (R, W) (mandatory) (2 bytes)."
        ::= { zxGponExVLANTagConfigEntry 4 }    
        
    zxGponExVLANTagConfigDownStreamMode   OBJECT-TYPE
        SYNTAX      INTEGER{
                    inverseUpstream(1),
                    noOperation(2)
                    }
        MAX-ACCESS  read-write
        STATUS      current
        DESCRIPTION
        "Regardless of its association, the extended VLAN tagging
         operation configuration data ME pertains to upstream traffic.
         This attribute specifies the mode for downstream mapping. (R, W) (mandatory) (1 byte)"
        ::= { zxGponExVLANTagConfigEntry 5 }  
        
    zxGponExVLANTagConfigEntryStatus OBJECT-TYPE
        SYNTAX      RowStatus
        MAX-ACCESS  read-write
        STATUS      current
        DESCRIPTION
        "This attribute specifies the action of this entry."
        REFERENCE   "G.984.4 9.3.13 Extended VLAN tagging operation configuration data"
        ::= { zxGponExVLANTagConfigEntry 6 }
        
    zxGponDscp2CosProfileIndex OBJECT-TYPE 
        SYNTAX      INTEGER
        MAX-ACCESS  read-write
        STATUS      current
        DESCRIPTION
        "This attribute specifies mapping from DSCP to P-bits. 
        The attribute can be considered a bit string sequence of 64 3-bit groups. 
        The 64 sequence entries represent the possible values of the 6-bit DSCP field. 
        Each 3-bit group specifies the P-bit value to which the associated DSCP value should be mapped."
        REFERENCE   "G.984.4 9.3.13 Extended VLAN tagging operation configuration data"
        ::= { zxGponExVLANTagConfigEntry 7 }        
        
    zxGponFilterRuleTable    OBJECT-TYPE
        SYNTAX      SEQUENCE OF ZxGponFilterRuleEntry
        MAX-ACCESS  not-accessible
        STATUS      current
        DESCRIPTION
            "This managed entity organizes data associated with VLAN tagging. 
            Regardless of its point of attachment, the specified tagging operations 
            refer to the upstream direction. Instances of this managed entity are 
            created and deleted by the OLT."
        REFERENCE   "G.984.4 9.3.13 Extended VLAN tagging operation configuration data"
        ::= { zxGponL2Mgmt 67 }
        
    zxGponFilterRuleEntry OBJECT-TYPE
        SYNTAX      ZxGponFilterRuleEntry
        MAX-ACCESS  not-accessible
        STATUS      current
        DESCRIPTION
            "It is entry in the zxGponFilterRuleEntry."
        INDEX   {zxGponFilterRuleId}
        ::= { zxGponFilterRuleTable 1 } 
        
    ZxGponFilterRuleEntry ::=
        SEQUENCE {
            zxGponFilterRuleId              INTEGER,
            zxGponFilterRuleName            OCTET STRING,
            zxGponFilterRuleTagNum          INTEGER,
            zxGponFilterRuleEthType         INTEGER,
            zxGponFilterRuleInnerPrio       INTEGER,
            zxGponFilterRuleInnerVID        INTEGER,
            zxGponFilterRuleInnerTPID       INTEGER,
            zxGponFilterRuleOuterPrio       INTEGER,
            zxGponFilterRuleOuterVID        INTEGER,
            zxGponFilterRuleOuterTPID       INTEGER,
            zxGponFilterRuleRefCnt          INTEGER,
            zxGponFilterRuleEntryStatus     RowStatus
        }
        
    zxGponFilterRuleId OBJECT-TYPE
        SYNTAX      INTEGER
        MAX-ACCESS  not-accessible
        STATUS      current
        DESCRIPTION
        "This attribute provides a unique number for each instance of this managed entity.  
        (R, Set-by-create) (mandatory) (4 bytes)"
        ::= { zxGponFilterRuleEntry 1 }
        
    zxGponFilterRuleName OBJECT-TYPE
        SYNTAX      OCTET STRING(SIZE(1..63))
        MAX-ACCESS  read-write
        STATUS      current
        DESCRIPTION
        "This attribute provides a unique name for each instance of this managed entity.  
        (R, Set-by-create) (mandatory) (2 bytes)"
        ::= { zxGponFilterRuleEntry 2 }
        
    zxGponFilterRuleTagNum  OBJECT-TYPE
        SYNTAX      INTEGER
        MAX-ACCESS  read-write
        STATUS      current
        DESCRIPTION
        "This attribute provides the number of tag.
        (R, Set-by-create) (mandatory) (2 bytes)"
        ::= { zxGponFilterRuleEntry 3 }

    zxGponFilterRuleEthType     OBJECT-TYPE
        SYNTAX      INTEGER{
                    notFilter(1),
                    ipoe(2),
                    pppoe(3),
                    arp(4)
                    }
        MAX-ACCESS  read-write
        STATUS      current
        DESCRIPTION
        "The Ethertype value on which to filter received frames, 
         as listed below. Note: This filter is recommended for 
         use on untagged frames or frames with only priority.(4 bits)" 
        ::= { zxGponFilterRuleEntry 4 }  
        
    zxGponFilterRuleInnerPrio     OBJECT-TYPE
        SYNTAX      INTEGER
        MAX-ACCESS  read-write
        STATUS      current
        DESCRIPTION
        "Filter received frames on this priority value(0-7).Do not filter on inner priority(8).
        This is the default filter when no other one-tag rule applies(14).This entry is a no-tag
        rule; ignore all other filter fields(15).(4 bits)" 
        ::= { zxGponFilterRuleEntry 5 }  
        
    zxGponFilterRuleInnerVID     OBJECT-TYPE
        SYNTAX      INTEGER
        MAX-ACCESS  read-write
        STATUS      current
        DESCRIPTION
        "Filter received frames on this VID value(0-4094).Do not filter on the inner VID(4096).(13 bits)" 
        ::= { zxGponFilterRuleEntry 6 }  

    zxGponFilterRuleInnerTPID   OBJECT-TYPE
        SYNTAX      INTEGER{
                    notFilter(1),
                    defaultTPID(5),
                    ignoreDE(6),
                    zeroDE(7),
                    oneDE(8)                
                    }
        MAX-ACCESS  read-write
        STATUS      current
        DESCRIPTION
        "Filter Inner TPID/DE: (3 bits)" 
        ::= { zxGponFilterRuleEntry 7 }
        
    zxGponFilterRuleOuterPrio     OBJECT-TYPE
        SYNTAX      INTEGER
        MAX-ACCESS  read-write
        STATUS      current
        DESCRIPTION
        "Filter received frames on this priority value(0-7).Do not filter on outer priority.(8).
        This is the default filter when no other two-tag rule applies(14).This entry is not a
        double-tag rule; ignore all other outer tag filter fields(15).(4 bits)" 
        ::= { zxGponFilterRuleEntry 8 }  
        
    zxGponFilterRuleOuterVID     OBJECT-TYPE
        SYNTAX      INTEGER
        MAX-ACCESS  read-write
        STATUS      current
        DESCRIPTION
        "Filter received frames on this VID value(0-4094).Do not filter on the outer VID(4096).(13 bits)" 
        ::= { zxGponFilterRuleEntry 9 }  

    zxGponFilterRuleOuterTPID   OBJECT-TYPE
        SYNTAX      INTEGER{
                    notFilter(1),
                    defaultTPID(5),
                    ignoreDE(6),
                    zeroDE(7),
                    oneDE(8)                
                    }
        MAX-ACCESS  read-write
        STATUS      current
        DESCRIPTION
        "Filter outer TPID/DE: (3 bits)" 
        ::= { zxGponFilterRuleEntry 10 }
        
    zxGponFilterRuleRefCnt OBJECT-TYPE
        SYNTAX      INTEGER
        MAX-ACCESS  read-only
        STATUS      current
        DESCRIPTION
        "Forbidden to delete table entry if not equal zero."
        ::= { zxGponFilterRuleEntry 11 }
             
    zxGponFilterRuleEntryStatus OBJECT-TYPE
        SYNTAX      RowStatus
        MAX-ACCESS  read-write
        STATUS      current
        DESCRIPTION
        "This attribute specifies the action of this entry."
        REFERENCE   "G.984.4 9.3.13 Extended VLAN tagging operation configuration data"
        ::= { zxGponFilterRuleEntry 12 }
    zxGponTreatmentRuleTable    OBJECT-TYPE
        SYNTAX      SEQUENCE OF ZxGponTreatmentRuleEntry
        MAX-ACCESS  not-accessible
        STATUS      current
        DESCRIPTION
            "This managed entity organizes data associated with VLAN tagging. 
            Regardless of its point of attachment, the specified tagging operations 
            refer to the upstream direction. Instances of this managed entity are 
            created and deleted by the OLT."
        REFERENCE   "G.984.4 9.3.13 Extended VLAN tagging operation configuration data"
        ::= { zxGponL2Mgmt 68 }
        
    zxGponTreatmentRuleEntry OBJECT-TYPE
        SYNTAX      ZxGponTreatmentRuleEntry
        MAX-ACCESS  not-accessible
        STATUS      current
        DESCRIPTION
            "It is entry in the zxGponTreatmentRuleEntry."
        INDEX   {zxGponTreatmentRuleId }
        ::= { zxGponTreatmentRuleTable 1 }
    
    ZxGponTreatmentRuleEntry ::=
        SEQUENCE {
            zxGponTreatmentRuleId              INTEGER,
            zxGponTreatmentRuleName            OCTET STRING,
            zxGponTreatmentRuleTagsRemove      INTEGER,
            zxGponTreatmentRuleAddInnerTag     TruthValue,
            zxGponTreatmentRuleAddOuterTag     TruthValue,
            zxGponTreatmentRuleInnerPrio       INTEGER,
            zxGponTreatmentRuleInnerPrioInsert INTEGER,
            zxGponTreatmentRuleInnerVID        INTEGER,
            zxGponTreatmentRuleInnerVIDInsert  INTEGER,
            zxGponTreatmentRuleInnerTPID       INTEGER,
            zxGponTreatmentRuleOuterPrio       INTEGER,
            zxGponTreatmentRuleOuterPrioInsert INTEGER,
            zxGponTreatmentRuleOuterVID        INTEGER,
            zxGponTreatmentRuleOuterVIDInsert  INTEGER,
            zxGponTreatmentRuleOuterTPID       INTEGER,
            zxGponTreatmentRuleRefCnt          INTEGER,
            zxGponTreatmentRuleEntryStatus     RowStatus
        }
        
    zxGponTreatmentRuleId OBJECT-TYPE
        SYNTAX      INTEGER
        MAX-ACCESS  not-accessible
        STATUS      current
        DESCRIPTION
        "This attribute provides a unique number for each instance of this managed entity.  
        (R, Set-by-create) (mandatory) (4 bytes)"
        ::= { zxGponTreatmentRuleEntry 1 }
        
    zxGponTreatmentRuleName OBJECT-TYPE
        SYNTAX      OCTET STRING(SIZE(1..63))
        MAX-ACCESS  read-write
        STATUS      current
        DESCRIPTION
        "This attribute provides a unique name for each instance of this managed entity.  
        (R, Set-by-create) (mandatory) (2 bytes)"
        ::= { zxGponTreatmentRuleEntry 2 }
        
    zxGponTreatmentRuleTagsRemove OBJECT-TYPE
        SYNTAX      INTEGER
        MAX-ACCESS  read-write
        STATUS      current
        DESCRIPTION
        "This attribute provides the number of tags to remove(0~3).(R, Set-by-create) (mandatory) (2 bytes)
        0..2    Remove 0, 1 or 2 tags, respectively. 
        If one tag is specified, then the outer tag is stripped from double-tagged frames.
        3    Discard the frame. 
        No symmetric downstream operation exists; 
        ie this rule is ignored in the downstream direction."
        ::= { zxGponTreatmentRuleEntry 3 }
        
    zxGponTreatmentRuleAddInnerTag OBJECT-TYPE
        SYNTAX      TruthValue
        MAX-ACCESS  read-write
        STATUS      current
        DESCRIPTION
        "This Boolean attribute indicates whether or not a add inner tag is 
        enabled. The value TRUE means enabled.(1 byte)"
        ::= { zxGponTreatmentRuleEntry 4 }
        
    zxGponTreatmentRuleAddOuterTag OBJECT-TYPE
        SYNTAX      TruthValue
        MAX-ACCESS  read-write
        STATUS      current
        DESCRIPTION
        "This Boolean attribute indicates whether or not a add outer tag is 
        enabled. The value TRUE means enabled.(1 byte)"
        ::= { zxGponTreatmentRuleEntry 5 }

    zxGponTreatmentRuleInnerPrio  OBJECT-TYPE
        SYNTAX      INTEGER{
                    insert(1),
                    copyInner(2),
                    copyOuter(3),
                    dscp(4)
                    }
        MAX-ACCESS  read-write
        STATUS      current
        DESCRIPTION
        "Treatment priority: (4 bits)" 
        ::= { zxGponTreatmentRuleEntry 6 }  
        
    zxGponTreatmentRuleInnerPrioInsert  OBJECT-TYPE
        SYNTAX      INTEGER
        MAX-ACCESS  read-write
        STATUS      current
        DESCRIPTION
        "Use this value as the priority to insert in the inner VLAN tag. (0-7)(4 bits)" 
        ::= { zxGponTreatmentRuleEntry 7 }  

    zxGponTreatmentRuleInnerVID     OBJECT-TYPE
        SYNTAX      INTEGER{
                    insert(1),
                    copyInner(2),
                    copyOuter(3)
                    }
        MAX-ACCESS  read-write
        STATUS      current
        DESCRIPTION
        "Treatment VID: (13 bits)" 
        ::= { zxGponTreatmentRuleEntry 8 }  
    
    zxGponTreatmentRuleInnerVIDInsert     OBJECT-TYPE
        SYNTAX      INTEGER
        MAX-ACCESS  read-write
        STATUS      current
        DESCRIPTION
        "Use this value as the VID in the inner VLAN tag. (0-4094)(13 bits)" 
        ::= { zxGponTreatmentRuleEntry 9 }  

    zxGponTreatmentRuleInnerTPID     OBJECT-TYPE
        SYNTAX      INTEGER{
                    mode0(1),
                    mode1(2),
                    mode2(3),
                    mode3(4),
                    mode4(5),
                    mode5(6),
                    mode6(7),
                    mode7(8)
                    }
        MAX-ACCESS  read-write
        STATUS      current
        DESCRIPTION
        "Treatment inner TPID/DE: (3 bits)
         000    Copy TPID (and DE, if present) from inner tag of received frame
         001    Copy TPID (and DE, if present) from outer tag of received frame
         010    Set TPID = output TPID attribute value, copy DE bit from inner tag of received frame
         011    Set TPID = output TPID, copy DE from outer tag of received frame
         100    Set TPID = 0x8100
         101    Reserved
         110    Set TPID = output TPID, DE=0
         111    Set TPID = output TPID, DE=1" 
        ::= { zxGponTreatmentRuleEntry 10 }

    zxGponTreatmentRuleOuterPrio     OBJECT-TYPE
        SYNTAX      INTEGER{
                    insert(1),
                    copyInner(2),
                    copyOuter(3),
                    dscp(4)
                    }
        MAX-ACCESS  read-write
        STATUS      current
        DESCRIPTION
        "Treatment priority: (4 bits)" 
        ::= { zxGponTreatmentRuleEntry 11 }  
        
    zxGponTreatmentRuleOuterPrioInsert     OBJECT-TYPE
        SYNTAX      INTEGER
        MAX-ACCESS  read-write
        STATUS      current
        DESCRIPTION
        "Use this value as the priority to insert in the outer VLAN tag. (0-7)(4 bits)" 
        ::= { zxGponTreatmentRuleEntry 12 }  

    zxGponTreatmentRuleOuterVID     OBJECT-TYPE
        SYNTAX      INTEGER{
                    insert(1),
                    copyInner(2),
                    copyOuter(3)
                    }
        MAX-ACCESS  read-write
        STATUS      current
        DESCRIPTION
        "Treatment VID: (13 bits)"  
        ::= { zxGponTreatmentRuleEntry 13 }  
        
    zxGponTreatmentRuleOuterVIDInsert     OBJECT-TYPE
        SYNTAX      INTEGER
        MAX-ACCESS  read-write
        STATUS      current
        DESCRIPTION
        "Use this value as the VID in the outer VLAN tag. (0-4094)(13 bits)" 
        ::= { zxGponTreatmentRuleEntry 14 }  

    zxGponTreatmentRuleOuterTPID     OBJECT-TYPE
        SYNTAX      INTEGER{
                    mode0(1),
                    mode1(2),
                    mode2(3),
                    mode3(4),
                    mode4(5),
                    mode5(6),
                    mode6(7),
                    mode7(8)
                    }
        MAX-ACCESS  read-write
        STATUS      current
        DESCRIPTION
        "Treatment outer TPID/DE: (3 bits)
         000    Copy TPID (and DE, if present) from inner tag of received frame
         001    Copy TPID (and DE, if present) from outer tag of received frame
         010    Set TPID = output TPID attribute value, copy DE bit from inner tag of received frame
         011    Set TPID = output TPID, copy DE from outer tag of received frame
         100    Set TPID = 0x8100
         101    Reserved
         110    Set TPID = output TPID, DE=0
         111    Set TPID = output TPID, DE=1" 
        ::= { zxGponTreatmentRuleEntry 15}   
        
    zxGponTreatmentRuleRefCnt OBJECT-TYPE
        SYNTAX      INTEGER
        MAX-ACCESS  read-only
        STATUS      current
        DESCRIPTION
        "Forbidden to delete table entry if not equal zero."
        ::= { zxGponTreatmentRuleEntry 16 }
             
    zxGponTreatmentRuleEntryStatus OBJECT-TYPE
        SYNTAX      RowStatus
        MAX-ACCESS  read-write
        STATUS      current
        DESCRIPTION
        "This attribute specifies the action of this entry."
        REFERENCE   "G.984.4 9.3.13 Extended VLAN tagging operation configuration data"
        ::= { zxGponTreatmentRuleEntry 17 }
        
   zxGponExVLANTableConfigTable     OBJECT-TYPE
        SYNTAX      SEQUENCE OF ZxGponExVLANTableConfigEntry
        MAX-ACCESS  not-accessible
        STATUS      current
        DESCRIPTION
            "This managed entity organizes data associated with VLAN tagging. 
            Regardless of its point of attachment, the specified tagging operations 
            refer to the upstream direction. Instances of this managed entity are 
            created and deleted by the OLT."
        REFERENCE   "G.984.4 9.3.13 Extended VLAN tagging operation configuration data"
        ::= { zxGponL2Mgmt 69 }
        
   zxGponExVLANTableConfigEntry OBJECT-TYPE
        SYNTAX      ZxGponExVLANTableConfigEntry
        MAX-ACCESS  not-accessible
        STATUS      current
        DESCRIPTION
            "It is entry in the zxGponUniExVLANTableConfigTable."
        INDEX   { zxGponOltIndex, zxGponONTIndex, zxGponExVlanIfType, zxGponExVlanIndex, zxGponExVlANTableConfigFilterId }
        ::= { zxGponExVLANTableConfigTable 1 } 
     
   ZxGponExVLANTableConfigEntry ::=
        SEQUENCE {
            zxGponExVlANTableConfigFilterId        INTEGER,
            zxGponExVlANTableConfigTreatId         INTEGER,
            zxGponExVLANTableConfigEntryStatus     RowStatus
        }
        
    zxGponExVlANTableConfigFilterId OBJECT-TYPE
        SYNTAX      INTEGER
        MAX-ACCESS  read-write
        STATUS      current
        DESCRIPTION
        "This attribute provides a unique index of filter for this ExVLAN table.  
        (R, Set-by-create) (mandatory) (2 bytes)"
        ::= { zxGponExVLANTableConfigEntry 1 }
 
    zxGponExVlANTableConfigTreatId OBJECT-TYPE
        SYNTAX      INTEGER
        MAX-ACCESS  read-write
        STATUS      current
        DESCRIPTION
        "This attribute provides a unique index of treatment for this ExVLAN table.  
        (R, Set-by-create) (mandatory) (2 bytes)"
        ::= { zxGponExVLANTableConfigEntry 2 }

    zxGponExVLANTableConfigEntryStatus OBJECT-TYPE
        SYNTAX      RowStatus
        MAX-ACCESS  read-write
        STATUS      current
        DESCRIPTION
        "This attribute specifies the action of this entry."
        REFERENCE   "G.984.4 9.3.13 Extended VLAN tagging operation configuration data"
        ::= { zxGponExVLANTableConfigEntry 3 }

--G.984.4 9.8.7    Pseudowire maintenance profile
    zxGponPwProfileTable    OBJECT-TYPE
        SYNTAX      SEQUENCE OF ZxGponPwProfileEntry
        MAX-ACCESS  not-accessible
        STATUS      current
        DESCRIPTION
            "The pseudowire maintenance profile permits the configuration of pseudowire 
            service exception handling. It is created and deleted by the OLT."
        REFERENCE   "G.984.4 9.8.7    Pseudowire maintenance profile"
        ::= { zxGponTDMMgmt 2 }
        
    zxGponPwProfileEntry OBJECT-TYPE
        SYNTAX      ZxGponPwProfileEntry
        MAX-ACCESS  not-accessible
        STATUS      current
        DESCRIPTION
            "It is entry in the zxGponPwProfileTable."
        INDEX   {zxGponPwProfileId }
        ::= { zxGponPwProfileTable 1 }
    
    ZxGponPwProfileEntry ::=
        SEQUENCE {
            zxGponPwProfileId                     INTEGER,
            zxGponPwProfileName                   OCTET STRING,
            zxGponPwProfileJtrBfrMaxDepth         INTEGER,
            zxGponPwProfileJtrBfrDesireDepth      INTEGER,
            zxGponPwProfileFillPolicy             INTEGER,
            zxGponPwProfileMisconnectPacketDeclr  INTEGER,
            zxGponPwProfileMisconnectPacketClr    INTEGER,
            zxGponPwProfileLossPacketDeclr        INTEGER,
            zxGponPwProfileLossPacketClr          INTEGER,
            zxGponPwProfileBfrDeclr               INTEGER,
            zxGponPwProfileBfrClr                 INTEGER,
            zxGponPwProfileMalformedPacketDeclr   INTEGER,
            zxGponPwProfileMalformedPacketClr     INTEGER,
            zxGponPwProfileRbitTxset              INTEGER,
            zxGponPwProfileRbitTxClr              INTEGER,
            zxGponPwProfileRbitRecieve            INTEGER,            
            zxGponPwProfileLbitRecieve            INTEGER,
            zxGponPwProfileSesThreshold           INTEGER,
            zxGponPwProfileRefCnt                 INTEGER,
            zxGponPwProfileEntryStatus            RowStatus
        }
        
    zxGponPwProfileId OBJECT-TYPE
        SYNTAX      INTEGER
        MAX-ACCESS  not-accessible
        STATUS      current
        DESCRIPTION
        "This attribute provides a unique number for each instance of this managed entity.  
        (R, Set-by-create) (mandatory) (2 bytes)"
        ::= { zxGponPwProfileEntry 1 }
        
    zxGponPwProfileName OBJECT-TYPE
        SYNTAX      OCTET STRING(SIZE(1..63))
        MAX-ACCESS  read-write
        STATUS      current
        DESCRIPTION
        "This attribute provides a unique name for each instance of this managed entity.  
        (R, Set-by-create) (mandatory) (2 bytes)"
        ::= { zxGponPwProfileEntry 2 }
        
    zxGponPwProfileJtrBfrMaxDepth OBJECT-TYPE
        SYNTAX      INTEGER
        MAX-ACCESS  read-write
        STATUS      current
        DESCRIPTION
        "This attribute specifies the desired maximum depth of the playout buffer in the 
        PSN to TDM direction. The value is expressed as a multiple of the 125 us frame rate. 
        The default value 0 selects the ONT's internal policy. (R, W, Set-by-create) (optional) (2 bytes)"
        ::= { zxGponPwProfileEntry 3 }
        
    zxGponPwProfileJtrBfrDesireDepth OBJECT-TYPE
        SYNTAX      INTEGER
        MAX-ACCESS  read-write
        STATUS      current
        DESCRIPTION
        "This attribute specifies the desired nominal fill depth of the playout buffer in the PSN to TDM 
        direction. The value is expressed as a multiple of the 125 us frame rate. The default value 0 selects 
        the ONT's internal policy. (R, W, Set-by-create) (optional) (2 bytes)"
        ::= { zxGponPwProfileEntry 4 }
        
    zxGponPwProfileFillPolicy OBJECT-TYPE
        SYNTAX      INTEGER
        MAX-ACCESS  read-write
        STATUS      current
        DESCRIPTION
        "TThis attribute defines the payload bit pattern to be applied toward the TDM service if no payload 
        packet is available to play out. The default value 0 specifies that the ONT apply its internal policy.
        0    ONT default, vendor-specific (recommended: AIS for unstructured service, all 1s for structured service)
        1    Play out AIS according to the service definition (for example, DS3 AIS)
        2    Play out all 1s
        3    Play out all 0s
        4    Repeat the previous data
        5    Play out DS1 idle (ANSI T1.403-1999 appendix C)
        6..15    Reserved for future standardization
        16..255    Vendor-specific, not to be standardized.(R, W, Set-by-create) (optional) (1 byte)"
        ::= { zxGponPwProfileEntry 5 }

    zxGponPwProfileMisconnectPacketDeclr  OBJECT-TYPE
        SYNTAX      INTEGER
        MAX-ACCESS  read-write
        STATUS      current
        DESCRIPTION
        "The alarm declaration policy attribute defines the anomaly rate that causes the corresponding alarm 
        to be declared. It is an integer percentage between 1..100. If this density of anomalies occurs during 
        the alarm onset soak interval, the alarm is declared. The default value 0 selects the ONT's internal policy.
        (R, W, Set-by-create) (optional) (1 byte)" 
        ::= { zxGponPwProfileEntry 6 }  
        
    zxGponPwProfileMisconnectPacketClr  OBJECT-TYPE
        SYNTAX      INTEGER
        MAX-ACCESS  read-write
        STATUS      current
        DESCRIPTION
        "The alarm clear policy attribute defines the anomaly rate that causes the corresponding alarm to be 
        cleared. It is an integer percentage between 0..99. If no more than this density of anomalies occurs 
        during the alarm clear soak interval, the alarm is cleared. The default value 255 selects the ONT's 
        internal policy. (R, W, Set-by-create) (optional) (1 byte)" 
        ::= { zxGponPwProfileEntry 7 }  
            
    zxGponPwProfileLossPacketDeclr     OBJECT-TYPE
        SYNTAX      INTEGER
        MAX-ACCESS  read-write
        STATUS      current
        DESCRIPTION
        "(R, W, Set-by-create) (optional) (1 byte)" 
        ::= { zxGponPwProfileEntry 8 }  
    
    zxGponPwProfileLossPacketClr     OBJECT-TYPE
        SYNTAX      INTEGER
        MAX-ACCESS  read-write
        STATUS      current
        DESCRIPTION
        "(R, W, Set-by-create) (optional) (1 byte)" 
        ::= { zxGponPwProfileEntry 9 }  

    zxGponPwProfileBfrDeclr     OBJECT-TYPE
        SYNTAX      INTEGER
        MAX-ACCESS  read-write
        STATUS      current
        DESCRIPTION
        "(R, W, Set-by-create) (optional) (1 byte)" 
        ::= { zxGponPwProfileEntry 10 }

    zxGponPwProfileBfrClr     OBJECT-TYPE
        SYNTAX      INTEGER
        MAX-ACCESS  read-write
        STATUS      current
        DESCRIPTION
        "(R, W, Set-by-create) (optional) (1 byte)" 
        ::= { zxGponPwProfileEntry 11 }  
                
    zxGponPwProfileMalformedPacketDeclr     OBJECT-TYPE
        SYNTAX      INTEGER
        MAX-ACCESS  read-write
        STATUS      current
        DESCRIPTION
        "(R, W, Set-by-create) (optional) (1 byte)" 
        ::= { zxGponPwProfileEntry 12 }  

    zxGponPwProfileMalformedPacketClr     OBJECT-TYPE
        SYNTAX      INTEGER
        MAX-ACCESS  read-write
        STATUS      current
        DESCRIPTION
        "(R, W, Set-by-create) (optional) (1 byte)" 
        ::= { zxGponPwProfileEntry 13}   
        
    zxGponPwProfileRbitTxset OBJECT-TYPE
        SYNTAX      INTEGER
        MAX-ACCESS  read-write
        STATUS      current
        DESCRIPTION
        "This attribute defines the number of consecutive lost packets that causes 
        the transmitted R bit to be set in the TDM to PSN direction, indicating lost
        packets to the far end. The default value 0 selects the ONT's internal policy. 
        (R, W, Set-by-create) (optional) (1 byte)"
        ::= { zxGponPwProfileEntry 14 }

    zxGponPwProfileRbitTxClr OBJECT-TYPE
        SYNTAX      INTEGER
        MAX-ACCESS  read-write
        STATUS      current
        DESCRIPTION
        "This attribute defines the number of consecutive valid packets that causes the 
        transmitted R bit to be cleared in the TDM to PSN direction, removing the remote 
        failure indication to the far end. The default value 0 selects the ONT's internal 
        policy. (R, W, Set-by-create) (optional) (1 byte)"
        ::= { zxGponPwProfileEntry 15 }   
         
    zxGponPwProfileRbitRecieve OBJECT-TYPE
        SYNTAX      INTEGER{
                    doNothing(1),
                    playOutSrvSpecialCode(2),
                    sendChannelIdle(3)
                    }
        MAX-ACCESS  read-write
        STATUS      current
        DESCRIPTION
        "This attribute defines the action toward the Nx64 TDM interface when remote 
        failure is indicated on packets received from the PSN (either R bit set or M = 0b10 
        while the L bit is cleared).
        0    Do nothing (default)
        1    Play out service-specific RAI/REI/RDI code
        2    Send channel idle signalling and idle channel payload to all DS0s comprising the service
        (R, W, Set-by-create) (optional) (1 byte)"
        ::= { zxGponPwProfileEntry 16 } 
         
    zxGponPwProfileLbitRecieve OBJECT-TYPE
        SYNTAX      INTEGER{
                    playOutAIS(1),
                    repeatLast(2),
                    sendChannelIdle(3)
                    }
        MAX-ACCESS  read-write
        STATUS      current
        DESCRIPTION
        "This attribute defines the action toward the TDM interface when far end TDM failure 
        is indicated on packets received from the PSN (L bit set).
        0    Play out service-specific AIS (default)
        1    Repeat last received packet
        2    Send channel idle signalling and idle channel payload to all DS0s comprising the service
        (R, W, Set-by-create) (optional) (1 byte)"
        ::= { zxGponPwProfileEntry 17 } 
        
    zxGponPwProfileSesThreshold OBJECT-TYPE
        SYNTAX      INTEGER
        MAX-ACCESS  read-write
        STATUS      current
        DESCRIPTION
        "Number of lost, malformed or otherwise unusable packets expected in the PSN to TDM 
        direction within a one-second interval that causes a severely errored second to be counted. 
        Stray packets do not count toward a severely errored second, nor do packets whose L bit is 
        set at the far end. The default value is 3. (R, W, Set-by-create) (optional) (2 bytes)"
        ::= { zxGponPwProfileEntry 18 } 
         
    zxGponPwProfileRefCnt OBJECT-TYPE
        SYNTAX      INTEGER
        MAX-ACCESS  read-only
        STATUS      current
        DESCRIPTION
        "Forbidden to delete table entry if not equal zero."
        ::= { zxGponPwProfileEntry 19 }
             
    zxGponPwProfileEntryStatus OBJECT-TYPE
        SYNTAX      RowStatus
        MAX-ACCESS  read-write
        STATUS      current
        DESCRIPTION
        "This attribute specifies the action of this entry."
        ::= { zxGponPwProfileEntry 30 }
        
--G.984.4 9.8.5    Pseudowire termination point      
--G.984.4 9.8.9    Ethernet flow termination point
    zxGponCESoETHConfigTable     OBJECT-TYPE
        SYNTAX      SEQUENCE OF ZxGponCESoETHConfigEntry
        MAX-ACCESS  not-accessible
        STATUS      current
        DESCRIPTION
            "The Ethernet flow termination point contains the attributes necessary 
            to originate and terminate Ethernet frames in the ONT. It is appropriate 
            when transporting pseudowire services via layer 2. Instances of this managed 
            entity are created and deleted by the OLT."
        REFERENCE   "G.984.4 9.8.9    Ethernet flow termination point,9.8.5    Pseudowire termination point"
        ::= { zxGponTDMMgmt 3 }
        
    zxGponCESoETHConfigEntry OBJECT-TYPE
        SYNTAX      ZxGponCESoETHConfigEntry
        MAX-ACCESS  not-accessible
        STATUS      current
        DESCRIPTION
            "It is entry in the zxGponCESoETHConfigTable."
        INDEX   { zxGponOltIndex, zxGponONTIndex, zxGponUNIIndex }
        ::= { zxGponCESoETHConfigTable 1 }
       
    ZxGponCESoETHConfigEntry ::=
        SEQUENCE {
            zxGponCESoETHBridgeIndex             INTEGER,
            zxGponCESoETHTxPayloadECID           INTEGER,
            zxGponCESoETHTxSignallingECID        INTEGER,
            zxGponCESoETHExpPayloadECID          INTEGER,
            zxGponCESoETHExpSignallingECID       INTEGER,  
            zxGponCESoETHRecvPayloadECID         INTEGER,
            zxGponCESoETHRecvSignallingECID      INTEGER,
            zxGponCESoETHTagPolicy               INTEGER,    
            zxGponCESoETHVlanTagVal              INTEGER,    
            zxGponCESoETHSrcMac                  MacAddress,    
            zxGponCESoETHDstMac                  MacAddress,    
            zxGponCESoETHLoopback                INTEGER,   
            zxGponCESoETHEntryStatus             RowStatus
        }
        
     zxGponCESoETHBridgeIndex OBJECT-TYPE
        SYNTAX      INTEGER
        MAX-ACCESS  read-write
        STATUS      current
        DESCRIPTION
            "This attribute indicates the index of MAC bridge in ONT, from 1 to M.
            The first byte specifies the slot Id associated with this MAC bridge;
            the second byte specifies the bridge group Id associated with this MAC bridge.(2 bytes)"
        ::= { zxGponCESoETHConfigEntry 1} 
              
     zxGponCESoETHTxPayloadECID OBJECT-TYPE
        SYNTAX      INTEGER
        MAX-ACCESS  read-write
        STATUS      current
        DESCRIPTION
            "reference to Transmit circuit ID in G.984.4 9.8.5    Pseudowire termination point,
            This attribute is a pair of ECID (Ethernet circuit ID)values that the ONT transmits 
            in the direction from the TDM termination toward the packet-switched network.
            This is the first value which is used for the payload ECID.(4 bytes)."
        ::= { zxGponCESoETHConfigEntry 2}

    zxGponCESoETHTxSignallingECID     OBJECT-TYPE
        SYNTAX      INTEGER
        MAX-ACCESS  read-write
        STATUS      current
        DESCRIPTION
        "reference to Transmit circuit ID in G.984.4 9.8.5    Pseudowire termination point,
        this is the second which is required only if signalling is to be carried in a distinct channel. 
        If signalling is not present, or is carried in the same channel as the payload, 
        the second ECID should be set to 0.(4 bytes)."
        ::= { zxGponCESoETHConfigEntry 3}    
   
    zxGponCESoETHExpPayloadECID     OBJECT-TYPE
        SYNTAX      INTEGER
        MAX-ACCESS  read-write
        STATUS      current
        DESCRIPTION
            "reference to Expected circuit ID in G.984.4 9.8.5    Pseudowire termination point,
            This attribute is a pair of ECID (Ethernet circuit ID) values that the ONT can 
            expect in the direction from the packet-switched network toward the TDM termination.
            This is the first value which is used for the payload ECID.(4 bytes)."
        ::= { zxGponCESoETHConfigEntry 4}
        
    zxGponCESoETHExpSignallingECID     OBJECT-TYPE
        SYNTAX      INTEGER
        MAX-ACCESS  read-write
        STATUS      current
        DESCRIPTION
            "reference to Expected circuit ID in G.984.4 9.8.5    Pseudowire termination point,
            This attribute is a pair of ECID (Ethernet circuit ID) values that the ONT can 
            expect in the direction from the packet-switched network toward the TDM termination.
            This is the second which is used for the optional separate signalling ECID. In both cases,
            default value 0 indicates that no ECID checking is expected..(4 bytes)."
        ::= { zxGponCESoETHConfigEntry 5}
        
    zxGponCESoETHRecvPayloadECID     OBJECT-TYPE
        SYNTAX      INTEGER
        MAX-ACCESS  read-only
        STATUS      current
        DESCRIPTION
            "reference to Received circuit ID in G.984.4 9.8.5    Pseudowire termination point,
            This attribute is a pair of ECID (Ethernet circuit ID) values that the ONT can 
            expect in the direction from the packet-switched network toward the TDM termination.
            This is the first value which is used for the payload ECID.(4 bytes)."
        ::= { zxGponCESoETHConfigEntry 6}
        
    zxGponCESoETHRecvSignallingECID     OBJECT-TYPE
        SYNTAX      INTEGER
        MAX-ACCESS  read-only
        STATUS      current
        DESCRIPTION
            "reference to Received circuit ID in G.984.4 9.8.5    Pseudowire termination point,
            This attribute is a pair of ECID (Ethernet circuit ID) values that the ONT can 
            expect in the direction from the packet-switched network toward the TDM termination.
            This is the second which is used for the optional separate signalling ECID. In both cases,
            the default value 0 indicates that no ECID checking is expected.(4 bytes)."
        ::= { zxGponCESoETHConfigEntry 7}
        
    zxGponCESoETHTagPolicy     OBJECT-TYPE
        SYNTAX      INTEGER{
                    untag(1),
                    tag(2)
                    }
        MAX-ACCESS  read-write
        STATUS      current
        DESCRIPTION
        "This attribute specifies the tagging policy to be applied to upstream Ethernet frames.(1 byte)"
        ::= { zxGponCESoETHConfigEntry 8 } 
           
    zxGponCESoETHVlanTagVal     OBJECT-TYPE
        SYNTAX      INTEGER
        MAX-ACCESS  read-write
        STATUS      current
        DESCRIPTION
        "If the tag policy calls for tagging of upstream Ethernet frames, this attribute specifies the tag 
        control information, which includes the VLAN tag, P bits and CFI bit. (R, W) (optional) (2 bytes)"
        ::= { zxGponCESoETHConfigEntry 9 } 
        
    zxGponCESoETHSrcMac     OBJECT-TYPE
        SYNTAX      MacAddress
        MAX-ACCESS  read-only
        STATUS      current
        DESCRIPTION
        "This attribute specifies the near-end MAC address. It is established by non-OMCI means (eg factory 
        programmed into ONT flash memory) and included here for information only.(R)(mandatory) (6 bytes)"
        ::= { zxGponCESoETHConfigEntry 10 }
            
    zxGponCESoETHDstMac     OBJECT-TYPE
        SYNTAX      MacAddress
        MAX-ACCESS  read-write
        STATUS      current
        DESCRIPTION
        "This attribute specifies the MAC address of the destination Ethernet frames. 
        (R, W, Set-by-create) (mandatory) (6 bytes)"
        ::= { zxGponCESoETHConfigEntry 11 }    

    zxGponCESoETHLoopback     OBJECT-TYPE
        SYNTAX      INTEGER{
                    noloopback(1),
                    loopback(2)
                    }
        MAX-ACCESS  read-write
        STATUS      current
        DESCRIPTION
        "This attribute sets the loopback configuration:
        0    No loopback
        1    Loopback of downstream traffic at MAC client(R, W) (mandatory) (1 byte)"
        ::= { zxGponCESoETHConfigEntry 12 }    

        
    zxGponCESoETHEntryStatus OBJECT-TYPE
        SYNTAX      RowStatus
        MAX-ACCESS  read-write
        STATUS      current
        DESCRIPTION
        "This attribute specifies the action of this entry."
        REFERENCE   "G.984.4 9.8.9    Ethernet flow termination point"
        ::= { zxGponCESoETHConfigEntry 20 }
        
    zxGponCESoIPConfigTable     OBJECT-TYPE
        SYNTAX      SEQUENCE OF ZxGponCESoIPConfigEntry
        MAX-ACCESS  not-accessible
        STATUS      current
        DESCRIPTION
            "The pseudowire termination point supports packetized (rather than TDM) G-PON
             transport of TDM services, transported either directly over Ethernet or over UDP/IP. 
             Instances of this managed entity are created and deleted by the OLT.This table is 
             the config of transported over UDP/IP"
        REFERENCE   "G.984.4 9.8.5    Pseudowire termination point"
        ::= { zxGponTDMMgmt 4 }
        
    zxGponCESoIPConfigEntry OBJECT-TYPE
        SYNTAX      ZxGponCESoIPConfigEntry
        MAX-ACCESS  not-accessible
        STATUS      current
        DESCRIPTION
            "It is entry in the zxGponCESoIPConfigTable."
        INDEX   { zxGponOltIndex, zxGponONTIndex, zxGponUNIIndex }
        ::= { zxGponCESoIPConfigTable 1 }
       
    ZxGponCESoIPConfigEntry ::=
        SEQUENCE {
            zxGponCESoIPNearEndIp            INTEGER,
            zxGponCESoIPHostId               INTEGER,
            zxGponCESoIPFarEndIp             OCTET STRING,
            zxGponCESoIPEntryStatus          RowStatus
        }

    zxGponCESoIPNearEndIp     OBJECT-TYPE
        SYNTAX      INTEGER
        MAX-ACCESS  read-write
        STATUS      current
        DESCRIPTION
        "When the pseudowire service is transported via IP, this attribute points to 
        an instance of the TCP/UDP config data managed entity. The default value 0 is 
        applicable if the pseudowire is not transported via IP. (R, W, Set-by-create) 
        (mandatory for IP transport) (2 bytes)"
        ::= { zxGponCESoIPConfigEntry 1 }         
        
    zxGponCESoIPHostId     OBJECT-TYPE
        SYNTAX      INTEGER
        MAX-ACCESS  read-write
        STATUS      current
        DESCRIPTION
        "(2 bytes)"
        ::= { zxGponCESoIPConfigEntry 2 }     
        
     zxGponCESoIPFarEndIp     OBJECT-TYPE
        SYNTAX      OCTET STRING
        MAX-ACCESS  read-write
        STATUS      current
        DESCRIPTION
        "When the pseudowire service is transported via IP, this attribute points to a large
         string managed entity that contains the URI of the far-end termination point(2 bytes)"
        ::= { zxGponCESoIPConfigEntry 3 }   
       
    zxGponCESoIPEntryStatus OBJECT-TYPE
        SYNTAX      RowStatus
        MAX-ACCESS  read-write
        STATUS      current
        DESCRIPTION
        "This attribute specifies the action of this entry."
        REFERENCE   ""
        ::= { zxGponCESoIPConfigEntry 10 }
                
    zxGponPwTDMConfigTable     OBJECT-TYPE
        SYNTAX      SEQUENCE OF ZxGponPwTDMConfigEntry
        MAX-ACCESS  not-accessible
        STATUS      current
        DESCRIPTION
            ""
        REFERENCE   "G.984.4 9.8.5    Pseudowire termination point"
        ::= { zxGponTDMMgmt 5 }
        
    zxGponPwTDMConfigEntry OBJECT-TYPE
        SYNTAX      ZxGponPwTDMConfigEntry
        MAX-ACCESS  not-accessible
        STATUS      current
        DESCRIPTION
            "It is entry in the zxGponPwTDMConfigTable."
        INDEX   { zxGponOltIndex, zxGponONTIndex, zxGponUNIIndex }
        ::= { zxGponPwTDMConfigTable 1 }
       
    ZxGponPwTDMConfigEntry ::=
        SEQUENCE {
            zxGponPwTDMPayloadSize          INTEGER,
            zxGponPwTDMPayloadDelay         INTEGER,
            zxGponPwTDMTimingMode           INTEGER,
            zxGponPwTDMProfile              INTEGER,
            zxGponPwTDMTransport            INTEGER
        }

    zxGponPwTDMPayloadSize     OBJECT-TYPE
        SYNTAX      INTEGER
        MAX-ACCESS  read-write
        STATUS      current
        DESCRIPTION
        "Number of payload bytes per packet. Valid only if service type = 
        unstructured or unstructured octet-aligned. Valid choices depend on the TDM
        service, but must include the following. Other choices are at the vendor's discretion.
                DS1    192
                DS1    200, required only if unstructured octet aligned service is supported
              E1    256
        DS3    1024
        E3    1024   (R, W, Set-by-create) (mandatory for unstructured service) (2 bytes)"
        ::= { zxGponPwTDMConfigEntry 1 }         
        
    zxGponPwTDMPayloadDelay     OBJECT-TYPE
        SYNTAX      INTEGER
        MAX-ACCESS  read-write
        STATUS      current
        DESCRIPTION
        "Number of 125 microsecond frames to be encapsulated in each pseudowire packet.
        Valid only if service type = structured. The minimum set of choices for various 
        TDM services is listed below, and is affected by the possible presence of in-band 
        signalling. Other choices are at the vendor's discretion.
                NxDS0, no signalling, N = 1    64 (8 ms) required, 
        40 (5 ms) desired
        NxDS0, no signalling, N = 2..4    32 (4 ms)
        NxDS0, no signalling, N > 4    8 (1 ms)
        NxDS0 with DS1 CAS    24 (3 ms)
        NxDS0 with E1 CAS    16 (2 ms)  (R, W, Set-by-create) (mandatory for structured service) (1 byte)"
        ::= { zxGponPwTDMConfigEntry 2 }     
        
     zxGponPwTDMTimingMode     OBJECT-TYPE
        SYNTAX      INTEGER{
                    network(1),
                    differential(2),
                    adaptive(3),
                    loop(4)
                    }
        MAX-ACCESS  read-write
        STATUS      current
        DESCRIPTION
        "This attribute selects the timing mode of the TDM service. If RTP is used, this attribute must 
        be set to be consistent with the value of the RTP time stamp mode attribute in the RTP parameters
        managed entity at the far end.
        0    Network timing (default)
                1    Differential timing
                2    Adaptive timing
                3    Loop timing: local TDM transmit clock derived from local TDM receive stream(R, W) (mandatory) (1 byte)"
        ::= { zxGponPwTDMConfigEntry 3 }             
        
     zxGponPwTDMProfile     OBJECT-TYPE
        SYNTAX      INTEGER
        MAX-ACCESS  read-write
        STATUS      current
        DESCRIPTION
        "This attribute points to an instance of the pseudowire maintenance profile managed entity. If the 
        pointer has its default value 0, the ONT's internal defaults apply. (R, W) (optional) (2 bytes)"
        ::= { zxGponPwTDMConfigEntry 4 }    
        
     zxGponPwTDMTransport     OBJECT-TYPE
        SYNTAX      INTEGER{
                    ethernet(1),
                    ip(2)
                    }
        MAX-ACCESS  read-write
        STATUS      current
        DESCRIPTION
        "Underlying transport:
           0    Ethernet, MEF8
           1    UDP/IP
        (R, W, Set-by-create) (mandatory) (1 byte)"
        ::= { zxGponPwTDMConfigEntry 5 }  

    zxGponPwOptionalConfigTable     OBJECT-TYPE
        SYNTAX      SEQUENCE OF ZxGponPwOptionalConfigEntry
        MAX-ACCESS  not-accessible
        STATUS      current
        DESCRIPTION
            ""
        REFERENCE   "G.984.4 9.8.5    Pseudowire termination point"
        ::= { zxGponTDMMgmt 6 }
        
    zxGponPwOptionalConfigEntry OBJECT-TYPE
        SYNTAX      ZxGponPwOptionalConfigEntry
        MAX-ACCESS  not-accessible
        STATUS      current
        DESCRIPTION
            "It is entry in the zxGponPwTDMConfigTable."
        INDEX   { zxGponOltIndex, zxGponONTIndex, zxGponUNIIndex }
        ::= { zxGponPwOptionalConfigTable 1 }
       
    ZxGponPwOptionalConfigEntry ::=
        SEQUENCE {
            zxGponPwOptionalServiceType          INTEGER,
            zxGponPwOptionalSignalling           INTEGER,
            zxGponPwOptionalARC                  INTEGER,
            zxGponPwOptionalARCInterval          INTEGER 
        }

    zxGponPwOptionalServiceType     OBJECT-TYPE
        SYNTAX      INTEGER{
                    basicUnstructured(1),
                    octetAlignedUnstructured(2),
                    structured(3)
                    }
        MAX-ACCESS  read-write
        STATUS      current
        DESCRIPTION
        "This attribute specifies the basic service type, either a transparent bit
         pipe or an encapsulation that recognizes the underlying structure of the payload.
         0    Basic unstructured (also known as structure agnostic)
         1    Octet aligned unstructured, structure agnostic. Applicable only to DS1, a mode
            in which each frame of 193 bits is encapsulated in 25 bytes with 7 padding bits.
         2    Structured (structure-locked)(R, W, Set-by-create) (mandatory) (1 byte)"
        ::= { zxGponPwOptionalConfigEntry 1 }         
        
    zxGponPwOptionalSignalling     OBJECT-TYPE
        SYNTAX      INTEGER{
                    noSignalling(1),
                    casSame(2),
                    casSeparate(3)
                    }
        MAX-ACCESS  read-write
        STATUS      current
        DESCRIPTION
        "0    No signalling visible at this layer
         1    CAS, to be carried in the same packet stream as the payload
         2    CAS, to be carried in a separate signalling channel
         (R, W, Set-by-create) (mandatory for structured service type) (1 byte)"
        ::= { zxGponPwOptionalConfigEntry 2 }     
        
     zxGponPwOptionalARC     OBJECT-TYPE
        SYNTAX      INTEGER
        MAX-ACCESS  read-write
        STATUS      current
        DESCRIPTION
        "See clause I.1.8/G.984.4. (R, W) (optional) (1 byte)"
        ::= { zxGponPwOptionalConfigEntry 3 }             
        
     zxGponPwOptionalARCInterval     OBJECT-TYPE
        SYNTAX      INTEGER
        MAX-ACCESS  read-write
        STATUS      current
        DESCRIPTION
        "See clause I.1.8/G.984.4. (R, W) (optional) (1 byte)"
        ::= { zxGponPwOptionalConfigEntry 4 }   
                              
--G.984.4 9.8.6    RTP pseudowire parameters
      zxGponPwRTPConfigTable     OBJECT-TYPE
        SYNTAX      SEQUENCE OF ZxGponPwRTPConfigEntry
        MAX-ACCESS  not-accessible
        STATUS      current
        DESCRIPTION
            "The pseudowire termination point supports packetized (rather than TDM) G-PON
             transport of TDM services, transported either directly over Ethernet or over UDP/IP. 
             Instances of this managed entity are created and deleted by the OLT.This table is 
             the config of transported over UDP/IP"
        REFERENCE   "G.984.4 9.8.6    RTP pseudowire parameters"
        ::= { zxGponTDMMgmt 7 }
        
    zxGponPwRTPConfigEntry OBJECT-TYPE
        SYNTAX      ZxGponPwRTPConfigEntry
        MAX-ACCESS  not-accessible
        STATUS      current
        DESCRIPTION
            "It is entry in the zxGponPwRTPConfigTable."
        INDEX   { zxGponOltIndex, zxGponONTIndex, zxGponUNIIndex }
        ::= { zxGponPwRTPConfigTable 1 }
        
    ZxGponPwRTPConfigEntry ::=
        SEQUENCE {
            zxGponPwRTPTsMode                       INTEGER,
            zxGponPwRTPPayloadPTYPE                 INTEGER,
            zxGponPwRTPSignallingPTYPE              INTEGER,
            zxGponPwRTPExpPayloadPTYPE              INTEGER,    
            zxGponPwRTPExpSignallingPTYPE           INTEGER,    
            zxGponPwRTPPayloadSSRC                  INTEGER,    
            zxGponPwRTPSignallingSSRC               INTEGER,    
            zxGponPwRTPExpPayloadSSRC               INTEGER,    
            zxGponPwRTPExpSignallingSSRC            INTEGER,   
            zxGponPwRTPClockReference               INTEGER,
            zxGponPwRTPEntryStatus                  RowStatus 
        }
      
    zxGponPwRTPTsMode     OBJECT-TYPE
        SYNTAX      INTEGER{
                    unknown(1),
                    absolute(2),
                    differential(3)
                    }
        MAX-ACCESS  read-write
        STATUS      current
        DESCRIPTION
            "This attribute determines the mode in which RTP timestamps are generated in the TDM to PSN direction.
            0    Unknown or not applicable (default)
            1    Absolute. Timestamps are based on the timing of the incoming TDM signal.
            2    Differential. Timestamps are based on the ONT's reference clock, which is understood to be 
                             stratum-traceable along with the reference clock at the far end.
            (R, W, Set-by-create) (mandatory) (1 byte)"
        ::= { zxGponPwRTPConfigEntry 1}
        
    zxGponPwRTPPayloadPTYPE     OBJECT-TYPE
        SYNTAX      INTEGER
        MAX-ACCESS  read-write
        STATUS      current
        DESCRIPTION
            "PTYPE specifies the RTP payload type in the TDM to PSN direction. It comprises two values. 
            The first is for the payload channel, the second, for the optional separate signalling channel. 
            Assignable PTYPEs lie in the dynamic range 96..127. If signalling is not transported in its own channel, 
            the second value should be set to 0. (R, W, Set-by-create) (mandatory) (1 bytes)"
        ::= { zxGponPwRTPConfigEntry 2}

    zxGponPwRTPSignallingPTYPE     OBJECT-TYPE
        SYNTAX      INTEGER
        MAX-ACCESS  read-write
        STATUS      current
        DESCRIPTION
            "PTYPE specifies the RTP payload type in the TDM to PSN direction. It comprises two values. 
            The first is for the payload channel, the second, for the optional separate signalling channel. 
            Assignable PTYPEs lie in the dynamic range 96..127. If signalling is not transported in its own channel, 
            the second value should be set to 0. (R, W, Set-by-create) (mandatory) (1 bytes)"
        ::= { zxGponPwRTPConfigEntry 3}

    zxGponPwRTPExpPayloadPTYPE     OBJECT-TYPE
        SYNTAX      INTEGER
        MAX-ACCESS  read-write
        STATUS      current
        DESCRIPTION
            "Expected PTYPE specifies the RTP payload type in the PSN to TDM direction. The received payload type 
            may be used to detect malformed packets. It comprises two values. The first is for the payload channel, 
            the second, for the optional separate signalling channel. To disable either or both of the check functions,
            set the corresponding value to its default value 0. (R, W, Set-by-create) (optional) (1 bytes)"
        ::= { zxGponPwRTPConfigEntry 4}
        
    zxGponPwRTPExpSignallingPTYPE     OBJECT-TYPE
        SYNTAX      INTEGER
        MAX-ACCESS  read-write
        STATUS      current
        DESCRIPTION
            "Expected PTYPE specifies the RTP payload type in the PSN to TDM direction. The received payload type 
            may be used to detect malformed packets. It comprises two values. The first is for the payload channel, 
            the second, for the optional separate signalling channel. To disable either or both of the check functions,
            set the corresponding value to its default value 0. (R, W, Set-by-create) (optional) (1 bytes)"
        ::= { zxGponPwRTPConfigEntry 5}
        
    zxGponPwRTPPayloadSSRC     OBJECT-TYPE
        SYNTAX      INTEGER
        MAX-ACCESS  read-write
        STATUS      current
        DESCRIPTION
            "SSRC specifies the RTP synchronization source in the TDM to PSN direction. It comprises two values. The first
            is for the payload channel, the second, for the optional separate signalling channel. If signalling is not 
            transported in its own channel, the second value should be set to 0. (R, W, Set-by-create) (mandatory) (4 bytes)"
        ::= { zxGponPwRTPConfigEntry 6}
        
    zxGponPwRTPSignallingSSRC     OBJECT-TYPE
        SYNTAX      INTEGER
        MAX-ACCESS  read-write
        STATUS      current
        DESCRIPTION
            "SSRC specifies the RTP synchronization source in the TDM to PSN direction. It comprises two values. The first
            is for the payload channel, the second, for the optional separate signalling channel. If signalling is not 
            transported in its own channel, the second value should be set to 0. (R, W, Set-by-create) (mandatory) (4 bytes)"
        ::= { zxGponPwRTPConfigEntry 7}

    zxGponPwRTPExpPayloadSSRC     OBJECT-TYPE
        SYNTAX      INTEGER
        MAX-ACCESS  read-write
        STATUS      current
        DESCRIPTION
            "Expected SSRC specifies the RTP synchronization source in the PSN to TDM direction. The received SSRC may be used 
            to detect misconnection (stray packets). It comprises two values. The first is for the payload channel, the second, 
            for the optional separate signalling channel. To disable either or both of the check functions, set the corresponding 
            value to its default value 0. (R, W, Set-by-create) (optional) (8 bytes)"
        ::= { zxGponPwRTPConfigEntry 8}
        
    zxGponPwRTPExpSignallingSSRC     OBJECT-TYPE
        SYNTAX      INTEGER
        MAX-ACCESS  read-write
        STATUS      current
        DESCRIPTION
            "Expected SSRC specifies the RTP synchronization source in the PSN to TDM direction. The received SSRC may be used 
            to detect misconnection (stray packets). It comprises two values. The first is for the payload channel, the second, 
            for the optional separate signalling channel. To disable either or both of the check functions, set the corresponding 
            value to its default value 0. (R, W, Set-by-create) (optional) (8 bytes)"
        ::= { zxGponPwRTPConfigEntry 9}
        
    zxGponPwRTPClockReference     OBJECT-TYPE
        SYNTAX      INTEGER
        MAX-ACCESS  read-write
        STATUS      current
        DESCRIPTION
            "This attribute specifies the frequency of the common timing reference, in multiples of 8 kHz.
             The default value is 1 (8 kHz). (R, W, Set-by-create) (mandatory) (2 bytes)"
        ::= { zxGponPwRTPConfigEntry 10}
        
    zxGponPwRTPEntryStatus OBJECT-TYPE
        SYNTAX      RowStatus
        MAX-ACCESS  read-write
        STATUS      current
        DESCRIPTION
        "This attribute specifies the action of this entry."
        REFERENCE   ""
        ::= { zxGponPwRTPConfigEntry 20 }        

--OMCI history statistics
    zxGponOmciEthHisStatsTable    OBJECT-TYPE
        SYNTAX      SEQUENCE OF ZxGponOmciEthHisStatsEntry
        MAX-ACCESS  not-accessible
        STATUS      current
        DESCRIPTION
            ""
        REFERENCE   "G.984.4 Ethernet performance monitoring history data
                     Ethernet performance monitoring history data 2
                     Ethernet performance monitoring history data 3"
        ::= { zxGponOmciStatistics 21 }

    zxGponOmciEthHisStatsEntry OBJECT-TYPE
        SYNTAX      ZxGponOmciEthHisStatsEntry
        MAX-ACCESS  not-accessible
        STATUS      current
        DESCRIPTION
            "It is entry in the zxGponOmciEthHisStatsTable."
        INDEX   { zxGponOltIndex, zxGponONTIndex, zxGponUNIIndex }
        ::= { zxGponOmciEthHisStatsTable 1 }

    ZxGponOmciEthHisStatsEntry ::=
        SEQUENCE {
            zxGponOmciEthHisStatsIntervalEndTime              INTEGER,
            zxGponOmciEthHisStatsThresDataId                  INTEGER,
            zxGponOmciEthHisStatsFCSErrors                    Unsigned32,
            zxGponOmciEthHisStatsExcessiveCollisionCnt        Unsigned32,
            zxGponOmciEthHisStatsLateCollisionCnt             Unsigned32,
            zxGponOmciEthHisStatsFrameTooLongs                Unsigned32,
            zxGponOmciEthHisStatsRxBufOverflows               Unsigned32,
            zxGponOmciEthHisStatsTxBufOverflows               Unsigned32,
            zxGponOmciEthHisStatsSingleCollisionCnt           Unsigned32,
            zxGponOmciEthHisStatsMultipleCollisionCnt         Unsigned32,
            zxGponOmciEthHisStatsSQECnt                       Unsigned32,
            zxGponOmciEthHisStatsDeferredTxCnt                Unsigned32,
            zxGponOmciEthHisStatsInternalMACTxErrCnt          Unsigned32,
            zxGponOmciEthHisStatsCarrierSenseErrCnt           Unsigned32,
            zxGponOmciEthHisStatsAlignmentErrCnt              Unsigned32,
            zxGponOmciEthHisStatsInternalMACRxErrCnt          Unsigned32,
            zxGponOmciEthHisStatsEntryStatus                  RowStatus,
            zxGponOmciEthHisStatsPPPoEFilteredCnt             Unsigned32,
            zxGponOmciEthHisStatsDropEvents                   Unsigned32,
            zxGponOmciEthHisStatsRxOctets                     Unsigned32,
            zxGponOmciEthHisStatsRxPkts                       Unsigned32,
            zxGponOmciEthHisStatsRxBroadcastPkts              Unsigned32,
            zxGponOmciEthHisStatsRxMulticastPkts              Unsigned32,
            zxGponOmciEthHisStatsRxUndersizePkts              Unsigned32,
            zxGponOmciEthHisStatsRxFragments                  Unsigned32,
            zxGponOmciEthHisStatsRxJabbers                    Unsigned32,
            zxGponOmciEthHisStatsRx64OctetsPkts               Unsigned32,
            zxGponOmciEthHisStatsRx65To127OctetsPkts          Unsigned32,
            zxGponOmciEthHisStatsRx128To255OctetsPkts         Unsigned32,
            zxGponOmciEthHisStatsRx256To511OctetsPkts         Unsigned32,
            zxGponOmciEthHisStatsRx512To1023OctetsPkts        Unsigned32,
            zxGponOmciEthHisStatsRx1024To1518OctetsPkts       Unsigned32
        }

    zxGponOmciEthHisStatsIntervalEndTime OBJECT-TYPE
        SYNTAX      INTEGER
        MAX-ACCESS  read-only
        STATUS      current
        DESCRIPTION
        ""
        REFERENCE   "G.984.4"
        ::= { zxGponOmciEthHisStatsEntry 1 }

    zxGponOmciEthHisStatsThresDataId OBJECT-TYPE
        SYNTAX      INTEGER
        MAX-ACCESS  read-only
        STATUS      current
        DESCRIPTION
        ""
        REFERENCE   "G.984.4"
        ::= { zxGponOmciEthHisStatsEntry 2 }

    zxGponOmciEthHisStatsFCSErrors OBJECT-TYPE
        SYNTAX      Unsigned32
        MAX-ACCESS  read-only
        STATUS      current
        DESCRIPTION
        ""
        REFERENCE   "G.984.4 Ethernet performance monitoring history data"
        ::= { zxGponOmciEthHisStatsEntry 3 }

    zxGponOmciEthHisStatsExcessiveCollisionCnt OBJECT-TYPE
        SYNTAX      Unsigned32
        MAX-ACCESS  read-only
        STATUS      current
        DESCRIPTION
        ""
        REFERENCE   "G.984.4 Ethernet performance monitoring history data"
        ::= { zxGponOmciEthHisStatsEntry 4 }

    zxGponOmciEthHisStatsLateCollisionCnt OBJECT-TYPE
        SYNTAX      Unsigned32
        MAX-ACCESS  read-only
        STATUS      current
        DESCRIPTION
        ""
        REFERENCE   "G.984.4 Ethernet performance monitoring history data"
        ::= { zxGponOmciEthHisStatsEntry 5 }
        
    zxGponOmciEthHisStatsFrameTooLongs OBJECT-TYPE
        SYNTAX      Unsigned32
        MAX-ACCESS  read-only
        STATUS      current
        DESCRIPTION
        ""
        REFERENCE   "G.984.4 Ethernet performance monitoring history data"
        ::= { zxGponOmciEthHisStatsEntry 6 }
        
    zxGponOmciEthHisStatsRxBufOverflows OBJECT-TYPE
        SYNTAX      Unsigned32
        MAX-ACCESS  read-only
        STATUS      current
        DESCRIPTION
        ""
        REFERENCE   "G.984.4 Ethernet performance monitoring history data"
        ::= { zxGponOmciEthHisStatsEntry 7 }

    zxGponOmciEthHisStatsTxBufOverflows OBJECT-TYPE
        SYNTAX      Unsigned32
        MAX-ACCESS  read-only
        STATUS      current
        DESCRIPTION
        ""
        REFERENCE   "G.984.4 Ethernet performance monitoring history data"
        ::= { zxGponOmciEthHisStatsEntry 8 }
        
    zxGponOmciEthHisStatsSingleCollisionCnt OBJECT-TYPE
        SYNTAX      Unsigned32
        MAX-ACCESS  read-only
        STATUS      current
        DESCRIPTION
        ""
        REFERENCE   "G.984.4 Ethernet performance monitoring history data"
        ::= { zxGponOmciEthHisStatsEntry 9 }

    zxGponOmciEthHisStatsMultipleCollisionCnt OBJECT-TYPE
        SYNTAX      Unsigned32
        MAX-ACCESS  read-only
        STATUS      current
        DESCRIPTION
        ""
        REFERENCE   "G.984.4 Ethernet performance monitoring history data"
        ::= { zxGponOmciEthHisStatsEntry 10 }

    zxGponOmciEthHisStatsSQECnt OBJECT-TYPE
        SYNTAX      Unsigned32
        MAX-ACCESS  read-only
        STATUS      current
        DESCRIPTION
        ""
        REFERENCE   "G.984.4 Ethernet performance monitoring history data"
        ::= { zxGponOmciEthHisStatsEntry 11 }

    zxGponOmciEthHisStatsDeferredTxCnt OBJECT-TYPE
        SYNTAX      Unsigned32
        MAX-ACCESS  read-only
        STATUS      current
        DESCRIPTION
        ""
        REFERENCE   "G.984.4 Ethernet performance monitoring history data"
        ::= { zxGponOmciEthHisStatsEntry 12 }

    zxGponOmciEthHisStatsInternalMACTxErrCnt OBJECT-TYPE
        SYNTAX      Unsigned32
        MAX-ACCESS  read-only
        STATUS      current
        DESCRIPTION
        ""
        REFERENCE   "G.984.4 Ethernet performance monitoring history data"
        ::= { zxGponOmciEthHisStatsEntry 13 }

    zxGponOmciEthHisStatsCarrierSenseErrCnt OBJECT-TYPE
        SYNTAX      Unsigned32
        MAX-ACCESS  read-only
        STATUS      current
        DESCRIPTION
        ""
        REFERENCE   "G.984.4 Ethernet performance monitoring history data"
        ::= { zxGponOmciEthHisStatsEntry 14 }

    zxGponOmciEthHisStatsAlignmentErrCnt OBJECT-TYPE
        SYNTAX      Unsigned32
        MAX-ACCESS  read-only
        STATUS      current
        DESCRIPTION
        ""
        REFERENCE   "G.984.4 Ethernet performance monitoring history data"
        ::= { zxGponOmciEthHisStatsEntry 15 }

    zxGponOmciEthHisStatsInternalMACRxErrCnt OBJECT-TYPE
        SYNTAX      Unsigned32
        MAX-ACCESS  read-only
        STATUS      current
        DESCRIPTION
        ""
        REFERENCE   "G.984.4 Ethernet performance monitoring history data"
        ::= { zxGponOmciEthHisStatsEntry 16 }

    zxGponOmciEthHisStatsEntryStatus OBJECT-TYPE
        SYNTAX      RowStatus
        MAX-ACCESS  read-only
        STATUS      current
        DESCRIPTION
        "This attribute specifies the action of this entry."
        REFERENCE   "G.984.4"
        ::= { zxGponOmciEthHisStatsEntry 17 }

    zxGponOmciEthHisStatsPPPoEFilteredCnt OBJECT-TYPE
        SYNTAX      Unsigned32
        MAX-ACCESS  read-only
        STATUS      current
        DESCRIPTION
        ""
        REFERENCE   "G.984.4 Ethernet performance monitoring history data 2"
        ::= { zxGponOmciEthHisStatsEntry 18 }

    zxGponOmciEthHisStatsDropEvents OBJECT-TYPE
        SYNTAX      Unsigned32
        MAX-ACCESS  read-only
        STATUS      current
        DESCRIPTION
        ""
        REFERENCE   "G.984.4 Ethernet performance monitoring history data 3"
        ::= { zxGponOmciEthHisStatsEntry 19 }

    zxGponOmciEthHisStatsRxOctets OBJECT-TYPE
        SYNTAX      Unsigned32
        MAX-ACCESS  read-only
        STATUS      current
        DESCRIPTION
        ""
        REFERENCE   "G.984.4"
        ::= { zxGponOmciEthHisStatsEntry 20 }

    zxGponOmciEthHisStatsRxPkts OBJECT-TYPE
        SYNTAX      Unsigned32
        MAX-ACCESS  read-only
        STATUS      current
        DESCRIPTION
        ""
        REFERENCE   "G.984.4 Ethernet performance monitoring history data 3"
        ::= { zxGponOmciEthHisStatsEntry 21 }

    zxGponOmciEthHisStatsRxBroadcastPkts OBJECT-TYPE
        SYNTAX      Unsigned32
        MAX-ACCESS  read-only
        STATUS      current
        DESCRIPTION
        ""
        REFERENCE   "G.984.4 Ethernet performance monitoring history data 3"
        ::= { zxGponOmciEthHisStatsEntry 22 }

    zxGponOmciEthHisStatsRxMulticastPkts OBJECT-TYPE
        SYNTAX      Unsigned32
        MAX-ACCESS  read-only
        STATUS      current
        DESCRIPTION
        ""
        REFERENCE   "G.984.4 Ethernet performance monitoring history data 3"
        ::= { zxGponOmciEthHisStatsEntry 23 }

    zxGponOmciEthHisStatsRxUndersizePkts OBJECT-TYPE
        SYNTAX      Unsigned32
        MAX-ACCESS  read-only
        STATUS      current
        DESCRIPTION
        ""
        REFERENCE   "G.984.4 Ethernet performance monitoring history data 3"
        ::= { zxGponOmciEthHisStatsEntry 24 }

    zxGponOmciEthHisStatsRxFragments OBJECT-TYPE
        SYNTAX      Unsigned32
        MAX-ACCESS  read-only
        STATUS      current
        DESCRIPTION
        ""
        REFERENCE   "G.984.4 Ethernet performance monitoring history data 3"
        ::= { zxGponOmciEthHisStatsEntry 25 }

    zxGponOmciEthHisStatsRxJabbers OBJECT-TYPE
        SYNTAX      Unsigned32
        MAX-ACCESS  read-only
        STATUS      current
        DESCRIPTION
        ""
        REFERENCE   "G.984.4 Ethernet performance monitoring history data 3"
        ::= { zxGponOmciEthHisStatsEntry 26 }

    zxGponOmciEthHisStatsRx64OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 27 }

    zxGponOmciEthHisStatsRx65To127OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 28 }

    zxGponOmciEthHisStatsRx128To255OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 29 }

    zxGponOmciEthHisStatsRx256To511OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 30 }

    zxGponOmciEthHisStatsRx512To1023OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 31 }

    zxGponOmciEthHisStatsRx1024To1518OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 32 }

--GEM history data
    zxGponOmciGEMHisStatsTable    OBJECT-TYPE
        SYNTAX      SEQUENCE OF ZxGponOmciGEMHisStatsEntry
        MAX-ACCESS  not-accessible
        STATUS      current
        DESCRIPTION
            ""
        REFERENCE   "G.984.4 & G.983.2"
        ::= { zxGponOmciStatistics 22 }

    zxGponOmciGEMHisStatsEntry OBJECT-TYPE
        SYNTAX      ZxGponOmciGEMHisStatsEntry
        MAX-ACCESS  not-accessible
        STATUS      current
        DESCRIPTION
            "It is entry in the zxGponOmciGEMHisStatsTable."
        INDEX   { zxGponOltIndex, zxGponONTIndex, zxGponGemPortIndex }
        ::= { zxGponOmciGEMHisStatsTable 1 }

    ZxGponOmciGEMHisStatsEntry ::=
        SEQUENCE {
            zxGponOmciGEMHisStatsIntervalEndTime               INTEGER,
            zxGponOmciGEMHisStatsThresDataId                   INTEGER,
            zxGponOmciGEMHisStatsLostPkts                      Unsigned32,
            zxGponOmciGEMHisStatsMisInsertedPkts               Unsigned32,
            zxGponOmciGEMHisStatsRxPkts                        Counter64,
            zxGponOmciGEMHisStatsRxBlocks                      Counter64,
            zxGponOmciGEMHisStatsTxBlocks                      Counter64,
            zxGponOmciGEMHisStatsImpairedBlocks                Unsigned32,
            zxGponOmciGEMHisStatsEntryStatus                   RowStatus
        }

    zxGponOmciGEMHisStatsIntervalEndTime OBJECT-TYPE
        SYNTAX      INTEGER
        MAX-ACCESS  read-only
        STATUS      current
        DESCRIPTION
        ""
        REFERENCE   "G.984.4 & G.983.2"
        ::= { zxGponOmciGEMHisStatsEntry 1 }

    zxGponOmciGEMHisStatsThresDataId OBJECT-TYPE
        SYNTAX      INTEGER
        MAX-ACCESS  read-only
        STATUS      current
        DESCRIPTION
        ""
        REFERENCE   "G.984.4 & G.983.2"
        ::= { zxGponOmciGEMHisStatsEntry 2 }

    zxGponOmciGEMHisStatsLostPkts OBJECT-TYPE
        SYNTAX      Unsigned32
        MAX-ACCESS  read-only
        STATUS      current
        DESCRIPTION
        ""
        REFERENCE   "G.984.4 & G.983.2"
        ::= { zxGponOmciGEMHisStatsEntry 3 }

    zxGponOmciGEMHisStatsMisInsertedPkts OBJECT-TYPE
        SYNTAX      Unsigned32
        MAX-ACCESS  read-only
        STATUS      current
        DESCRIPTION
        ""
        REFERENCE   "G.984.4 & G.983.2"
        ::= { zxGponOmciGEMHisStatsEntry 4 }

    zxGponOmciGEMHisStatsRxPkts OBJECT-TYPE
        SYNTAX      Counter64
        MAX-ACCESS  read-only
        STATUS      current
        DESCRIPTION
        ""
        REFERENCE   "G.984.4 & G.983.2"
        ::= { zxGponOmciGEMHisStatsEntry 6 }
        
    zxGponOmciGEMHisStatsRxBlocks OBJECT-TYPE
        SYNTAX      Counter64
        MAX-ACCESS  read-only
        STATUS      current
        DESCRIPTION
        ""
        REFERENCE   "G.984.4 & G.983.2"
        ::= { zxGponOmciGEMHisStatsEntry 7 }

    zxGponOmciGEMHisStatsTxBlocks OBJECT-TYPE
        SYNTAX      Counter64
        MAX-ACCESS  read-only
        STATUS      current
        DESCRIPTION
        ""
        REFERENCE   "G.984.4 & G.983.2"
        ::= { zxGponOmciGEMHisStatsEntry 8 }
        
    zxGponOmciGEMHisStatsImpairedBlocks OBJECT-TYPE
        SYNTAX      Unsigned32
        MAX-ACCESS  read-only
        STATUS      current
        DESCRIPTION
        ""
        REFERENCE   "G.984.4 & G.983.2"
        ::= { zxGponOmciGEMHisStatsEntry 9 }

    zxGponOmciGEMHisStatsEntryStatus OBJECT-TYPE
        SYNTAX      RowStatus
        MAX-ACCESS  read-only
        STATUS      current
        DESCRIPTION
        "This attribute specifies the action of this interworking."
        REFERENCE   "G.984.4 & G.983.2"
        ::= { zxGponOmciGEMHisStatsEntry 10 }

--UNI bridge port history statistics
    zxGponOmciUNIBridgePortHisStatsTable    OBJECT-TYPE
        SYNTAX      SEQUENCE OF ZxGponOmciUNIBridgePortHisStatsEntry
        MAX-ACCESS  not-accessible
        STATUS      current
        DESCRIPTION
            ""
        REFERENCE   "G.984.4 & G.983.2"
        ::= { zxGponOmciStatistics 25 }

    zxGponOmciUNIBridgePortHisStatsEntry OBJECT-TYPE
        SYNTAX      ZxGponOmciUNIBridgePortHisStatsEntry
        MAX-ACCESS  not-accessible
        STATUS      current
        DESCRIPTION
            "It is entry in the zxGponOmciUNIBridgePortHisStatsTable."
        INDEX   { zxGponOltIndex, zxGponONTIndex, zxGponUNIIndex }
        ::= { zxGponOmciUNIBridgePortHisStatsTable 1 }

    ZxGponOmciUNIBridgePortHisStatsEntry ::=
        SEQUENCE {
            zxGponOmciUNIBridgePortHisStatsIntervalEndTime               INTEGER,
            zxGponOmciUNIBridgePortHisStatsThresDataId                   INTEGER,
            zxGponOmciUNIBridgePortHisStatsForwardFrameCnt               Unsigned32,
            zxGponOmciUNIBridgePortHisStatsDelayExceedDiscardCnt         Unsigned32,
            zxGponOmciUNIBridgePortHisStatsMTUExceedDiscardCnt           Unsigned32,
            zxGponOmciUNIBridgePortHisStatsRxFrameCnt                    Unsigned32,
            zxGponOmciUNIBridgePortHisStatsRxDiscardCnt                  Unsigned32,
            zxGponOmciUNIBridgePortHisStatsEntryStatus                   RowStatus
        }

    zxGponOmciUNIBridgePortHisStatsIntervalEndTime OBJECT-TYPE
        SYNTAX      INTEGER
        MAX-ACCESS  read-only
        STATUS      current
        DESCRIPTION
        ""
        REFERENCE   "G.984.4 & G.983.2"
        ::= { zxGponOmciUNIBridgePortHisStatsEntry 1 }
        
    zxGponOmciUNIBridgePortHisStatsThresDataId OBJECT-TYPE
        SYNTAX      INTEGER
        MAX-ACCESS  read-only
        STATUS      current
        DESCRIPTION
        ""
        REFERENCE   "G.984.4 & G.983.2"
        ::= { zxGponOmciUNIBridgePortHisStatsEntry 2 }

    zxGponOmciUNIBridgePortHisStatsForwardFrameCnt OBJECT-TYPE
        SYNTAX      Unsigned32
        MAX-ACCESS  read-only
        STATUS      current
        DESCRIPTION
        ""
        REFERENCE   "G.984.4 & G.983.2"
        ::= { zxGponOmciUNIBridgePortHisStatsEntry 3 }
        
    zxGponOmciUNIBridgePortHisStatsDelayExceedDiscardCnt OBJECT-TYPE
        SYNTAX      Unsigned32
        MAX-ACCESS  read-only
        STATUS      current
        DESCRIPTION
        ""
        REFERENCE   "G.984.4 & G.983.2"
        ::= { zxGponOmciUNIBridgePortHisStatsEntry 4 }
        
    zxGponOmciUNIBridgePortHisStatsMTUExceedDiscardCnt OBJECT-TYPE
        SYNTAX      Unsigned32
        MAX-ACCESS  read-only
        STATUS      current
        DESCRIPTION
        ""
        REFERENCE   "G.984.4 & G.983.2"
        ::= { zxGponOmciUNIBridgePortHisStatsEntry 5 }
        
    zxGponOmciUNIBridgePortHisStatsRxFrameCnt OBJECT-TYPE
        SYNTAX      Unsigned32
        MAX-ACCESS  read-only
        STATUS      current
        DESCRIPTION
        ""
        REFERENCE   "G.984.4 & G.983.2"
        ::= { zxGponOmciUNIBridgePortHisStatsEntry 6 }
        
    zxGponOmciUNIBridgePortHisStatsRxDiscardCnt OBJECT-TYPE
        SYNTAX      Unsigned32
        MAX-ACCESS  read-only
        STATUS      current
        DESCRIPTION
        ""
        REFERENCE   "G.984.4 & G.983.2"
        ::= { zxGponOmciUNIBridgePortHisStatsEntry 7 }
        
    zxGponOmciUNIBridgePortHisStatsEntryStatus OBJECT-TYPE
        SYNTAX      RowStatus
        MAX-ACCESS  read-only
        STATUS      current
        DESCRIPTION
        ""
        REFERENCE   "G.984.4 & G.983.2"
        ::= { zxGponOmciUNIBridgePortHisStatsEntry 8 }

--Uplink bridge port history statistics
    zxGponOmciUpLinkBridgePortHisStatsTable    OBJECT-TYPE
        SYNTAX      SEQUENCE OF ZxGponOmciUpLinkBridgePortHisStatsEntry
        MAX-ACCESS  not-accessible
        STATUS      current
        DESCRIPTION
            ""
        REFERENCE   "G.984.4 & G.983.2"
        ::= { zxGponOmciStatistics 26 }

    zxGponOmciUpLinkBridgePortHisStatsEntry OBJECT-TYPE
        SYNTAX      ZxGponOmciUpLinkBridgePortHisStatsEntry
        MAX-ACCESS  not-accessible
        STATUS      current
        DESCRIPTION
            "It is entry in the zxGponOmciUpLinkBridgePortHisStatsTable."
        INDEX   { zxGponOltIndex, zxGponONTIndex, zxGponUpLinkIndex }
        ::= { zxGponOmciUpLinkBridgePortHisStatsTable 1 }

    ZxGponOmciUpLinkBridgePortHisStatsEntry ::=
        SEQUENCE {
            zxGponOmciUpLinkBridgePortHisStatsIntervalEndTime               INTEGER,
            zxGponOmciUpLinkBridgePortHisStatsThresDataId                   INTEGER,
            zxGponOmciUpLinkBridgePortHisStatsForwardFrameCnt               Unsigned32,
            zxGponOmciUpLinkBridgePortHisStatsDelayExceedDiscardCnt         Unsigned32,
            zxGponOmciUpLinkBridgePortHisStatsMTUExceedDiscardCnt           Unsigned32,
            zxGponOmciUpLinkBridgePortHisStatsRxFrameCnt                    Unsigned32,
            zxGponOmciUpLinkBridgePortHisStatsRxDiscardCnt                  Unsigned32,
            zxGponOmciUpLinkBridgePortHisStatsEntryStatus                   RowStatus
        }

    zxGponOmciUpLinkBridgePortHisStatsIntervalEndTime OBJECT-TYPE
        SYNTAX      INTEGER
        MAX-ACCESS  read-only
        STATUS      current
        DESCRIPTION
        ""
        REFERENCE   "G.984.4 & G.983.2"
        ::= { zxGponOmciUpLinkBridgePortHisStatsEntry 1 }
        
    zxGponOmciUpLinkBridgePortHisStatsThresDataId OBJECT-TYPE
        SYNTAX      INTEGER
        MAX-ACCESS  read-only
        STATUS      current
        DESCRIPTION
        ""
        REFERENCE   "G.984.4 & G.983.2"
        ::= { zxGponOmciUpLinkBridgePortHisStatsEntry 2 }

    zxGponOmciUpLinkBridgePortHisStatsForwardFrameCnt OBJECT-TYPE
        SYNTAX      Unsigned32
        MAX-ACCESS  read-only
        STATUS      current
        DESCRIPTION
        ""
        REFERENCE   "G.984.4 & G.983.2"
        ::= { zxGponOmciUpLinkBridgePortHisStatsEntry 3 }
        
    zxGponOmciUpLinkBridgePortHisStatsDelayExceedDiscardCnt OBJECT-TYPE
        SYNTAX      Unsigned32
        MAX-ACCESS  read-only
        STATUS      current
        DESCRIPTION
        ""
        REFERENCE   "G.984.4 & G.983.2"
        ::= { zxGponOmciUpLinkBridgePortHisStatsEntry 4 }
        
    zxGponOmciUpLinkBridgePortHisStatsMTUExceedDiscardCnt OBJECT-TYPE
        SYNTAX      Unsigned32
        MAX-ACCESS  read-only
        STATUS      current
        DESCRIPTION
        ""
        REFERENCE   "G.984.4 & G.983.2"
        ::= { zxGponOmciUpLinkBridgePortHisStatsEntry 5 }
        
    zxGponOmciUpLinkBridgePortHisStatsRxFrameCnt OBJECT-TYPE
        SYNTAX      Unsigned32
        MAX-ACCESS  read-only
        STATUS      current
        DESCRIPTION
        ""
        REFERENCE   "G.984.4 & G.983.2"
        ::= { zxGponOmciUpLinkBridgePortHisStatsEntry 6 }
        
    zxGponOmciUpLinkBridgePortHisStatsRxDiscardCnt OBJECT-TYPE
        SYNTAX      Unsigned32
        MAX-ACCESS  read-only
        STATUS      current
        DESCRIPTION
        ""
        REFERENCE   "G.984.4 & G.983.2"
        ::= { zxGponOmciUpLinkBridgePortHisStatsEntry 7 }
        
    zxGponOmciUpLinkBridgePortHisStatsEntryStatus OBJECT-TYPE
        SYNTAX      RowStatus
        MAX-ACCESS  read-only
        STATUS      current
        DESCRIPTION
        ""
        REFERENCE   "G.984.4 & G.983.2"
        ::= { zxGponOmciUpLinkBridgePortHisStatsEntry 8 }
        
--FEC History Statics G984.4_9.2.11 
    zxGponOmciFecHisStatsTable    OBJECT-TYPE
        SYNTAX      SEQUENCE OF ZxGponOmciFecHisStatsEntry
        MAX-ACCESS  not-accessible
        STATUS      current
        DESCRIPTION
            "FEC performance monitoring history data."
        REFERENCE   "9.2.11  FEC performance monitoring history data."
        ::= { zxGponOmciStatistics 28 }

    zxGponOmciFecHisStatsEntry OBJECT-TYPE
        SYNTAX      ZxGponOmciFecHisStatsEntry
        MAX-ACCESS  not-accessible
        STATUS      current
        DESCRIPTION
            "It is entry in the zxGponOmciFecHisStatsTable."
        INDEX   { zxGponOltIndex, zxGponONTIndex }
        ::= { zxGponOmciFecHisStatsTable 1 }

    ZxGponOmciFecHisStatsEntry ::=
        SEQUENCE {
            zxGponOmciFecHisIntvlEndTime              INTEGER,
            zxGponOmciFecHisThresDataId               INTEGER,
            zxGponOmciFecHisCrctBytes                 Unsigned32,
            zxGponOmciFecHisCrctCodeWords             Unsigned32,
            zxGponOmciFecHisUcrctCodeWords            Unsigned32,
            zxGponOmciFecHisTotalCodeWords            Unsigned32,
            zxGponOmciFecHisFecSeconds                Unsigned32
        }

    zxGponOmciFecHisIntvlEndTime OBJECT-TYPE
        SYNTAX      INTEGER(0..255)
        MAX-ACCESS  read-only
        STATUS      current
        DESCRIPTION
        "This attribute identifies the most recently finished 15-minute 
        interval."
        REFERENCE   "G.984.4"
        ::= { zxGponOmciFecHisStatsEntry 1 } 
        
    zxGponOmciFecHisThresDataId OBJECT-TYPE
        SYNTAX      INTEGER(0..65535)
        MAX-ACCESS  read-only
        STATUS      current
        DESCRIPTION
        "This attribute points to an instance of the threshold data 1 managed
         entity that contains PM threshold values. Since no threshold value 
         attribute number exceeds 7, a threshold data 2 ME is optional."
        REFERENCE   "G.984.4"
        ::= { zxGponOmciFecHisStatsEntry 2 }   
        
    zxGponOmciFecHisCrctBytes OBJECT-TYPE
        SYNTAX      Unsigned32
        MAX-ACCESS  read-only
        STATUS      current
        DESCRIPTION
        "This attribute counts the number of bytes that were corrected by the 
        FEC function."
        REFERENCE   "G.984.4"
        ::= { zxGponOmciFecHisStatsEntry 3 } 
                    
    zxGponOmciFecHisCrctCodeWords OBJECT-TYPE
        SYNTAX      Unsigned32
        MAX-ACCESS  read-only
        STATUS      current
        DESCRIPTION
        "This attribute counts the code words that were corrected by the FEC
         function."
        REFERENCE   "G.984.4"
        ::= { zxGponOmciFecHisStatsEntry 4 }   
                  
    zxGponOmciFecHisUcrctCodeWords OBJECT-TYPE
        SYNTAX      Unsigned32
        MAX-ACCESS  read-only
        STATUS      current
        DESCRIPTION
        "This attribute counts the code words that were not corrected by
         the FEC function."
        REFERENCE   "G.984.4"
        ::= { zxGponOmciFecHisStatsEntry 5 } 
                    
    zxGponOmciFecHisTotalCodeWords OBJECT-TYPE
        SYNTAX      Unsigned32
        MAX-ACCESS  read-only
        STATUS      current
        DESCRIPTION
        "This attribute counts the total received code words."
        REFERENCE   "G.984.4"
        ::= { zxGponOmciFecHisStatsEntry 6 } 
                    
    zxGponOmciFecHisFecSeconds OBJECT-TYPE
        SYNTAX      Unsigned32
        MAX-ACCESS  read-only
        STATUS      current
        DESCRIPTION
        "This attribute counts seconds during which there was a forward error
         correction anomaly."
        REFERENCE   "G.984.4"
        ::= { zxGponOmciFecHisStatsEntry 7 }           

--CES history data
    zxGponOmciCESHisStatsTable    OBJECT-TYPE
        SYNTAX      SEQUENCE OF ZxGponOmciCESHisStatsEntry
        MAX-ACCESS  not-accessible
        STATUS      current
        DESCRIPTION
            "Performance monitoring history data of Physical path termination point CES UNI."
        REFERENCE
           "G.984.4, CES physical interface performance monitoring history data,
        Pseudowire performance monitoring history data"
        ::= { zxGponOmciStatistics 33 }
        
    zxGponOmciCESHisStatsEntry    OBJECT-TYPE
        SYNTAX      ZxGponOmciCESHisStatsEntry
        MAX-ACCESS  not-accessible
        STATUS      current
        DESCRIPTION
            "It is entry in the zxGponOmciCESStatsTable."
        INDEX   { zxGponOltIndex, zxGponONTIndex, zxGponUNIIndex }
        ::= { zxGponOmciCESHisStatsTable 1 }
    
    ZxGponOmciCESHisStatsEntry ::=
        SEQUENCE {
            zxGponOmciCESHisStatsIntervalEndTime               INTEGER,
            zxGponOmciCESHisStatsThresholdDataId               INTEGER,
            zxGponOmciCESHisStatsDownPkts                      Unsigned32,
            zxGponOmciCESHisStatsUpPkts                        Unsigned32,
            zxGponOmciCESHisStatsDownMissingPkts               Unsigned32,
            zxGponOmciCESHisStatsDownReorderedPkts             Unsigned32,
            zxGponOmciCESHisStatsDownMisorderedPkts            Unsigned32,
            zxGponOmciCESHisStatsDownBufUnderrunOrOverrunPkts  Unsigned32,
            zxGponOmciCESHisStatsDownMalformedPkts             Unsigned32,
            zxGponOmciCESHisStatsDownStrayPkts                 Unsigned32,
            zxGponOmciCESHisStatsDownRemotePktLoss             Unsigned32,
            zxGponOmciCESHisStatsUpTDMLbitPkts                 Unsigned32,
            zxGponOmciCESHisStatsDownErrSeconds                Unsigned32,
            zxGponOmciCESHisStatsDownSeverelyErrSeconds        Unsigned32,
            zxGponOmciCESHisStatsDownUnavailableSeconds        Unsigned32,
--            zxGponOmciCESHisStatsUpErrSeconds                  Unsigned32,
--            zxGponOmciCESHisStatsUpSeverelyErrSeconds          Unsigned32,
--            zxGponOmciCESHisStatsUpBurstErrSeconds             Unsigned32,
--            zxGponOmciCESHisStatsUpUnavailableSeconds          Unsigned32,
--            zxGponOmciCESHisStatsUpControlledSlipSeconds       Unsigned32,
            zxGponOmciCESHisStatsEntryStatus                   RowStatus
        }

    zxGponOmciCESHisStatsIntervalEndTime   OBJECT-TYPE
        SYNTAX      INTEGER
        MAX-ACCESS  read-only
        STATUS      current
        DESCRIPTION
        ""
        REFERENCE   "G.984.4, Pseudowire performance monitoring history data"
        ::= { zxGponOmciCESHisStatsEntry 1 }

    zxGponOmciCESHisStatsThresholdDataId   OBJECT-TYPE
        SYNTAX      INTEGER
        MAX-ACCESS  read-only
        STATUS      current
        DESCRIPTION
        ""
        REFERENCE   "G.984.4, Pseudowire performance monitoring history data"
        ::= { zxGponOmciCESHisStatsEntry 2 }

    zxGponOmciCESHisStatsDownPkts   OBJECT-TYPE
        SYNTAX      Unsigned32
        MAX-ACCESS  read-only
        STATUS      current
        DESCRIPTION
        ""
        REFERENCE   "G.984.4, Pseudowire performance monitoring history data"
        ::= { zxGponOmciCESHisStatsEntry 3 }

    zxGponOmciCESHisStatsUpPkts   OBJECT-TYPE
        SYNTAX      Unsigned32
        MAX-ACCESS  read-only
        STATUS      current
        DESCRIPTION
        ""
        REFERENCE   "G.984.4, Pseudowire performance monitoring history data"
        ::= { zxGponOmciCESHisStatsEntry 4 }

    zxGponOmciCESHisStatsDownMissingPkts   OBJECT-TYPE
        SYNTAX      Unsigned32
        MAX-ACCESS  read-only
        STATUS      current
        DESCRIPTION
        ""
        REFERENCE   "G.984.4, Pseudowire performance monitoring history data"
        ::= { zxGponOmciCESHisStatsEntry 5 }

    zxGponOmciCESHisStatsDownReorderedPkts   OBJECT-TYPE
        SYNTAX      Unsigned32
        MAX-ACCESS  read-only
        STATUS      current
        DESCRIPTION
        ""
        REFERENCE   "G.984.4, Pseudowire performance monitoring history data"
        ::= { zxGponOmciCESHisStatsEntry 6 }

    zxGponOmciCESHisStatsDownMisorderedPkts   OBJECT-TYPE
        SYNTAX      Unsigned32
        MAX-ACCESS  read-only
        STATUS      current
        DESCRIPTION
        ""
        REFERENCE   "G.984.4, Pseudowire performance monitoring history data"
        ::= { zxGponOmciCESHisStatsEntry 7 }

    zxGponOmciCESHisStatsDownBufUnderrunOrOverrunPkts   OBJECT-TYPE
        SYNTAX      Unsigned32
        MAX-ACCESS  read-only
        STATUS      current
        DESCRIPTION
        ""
        REFERENCE   "G.984.4, Pseudowire performance monitoring history data"
        ::= { zxGponOmciCESHisStatsEntry 8 }

    zxGponOmciCESHisStatsDownMalformedPkts   OBJECT-TYPE
        SYNTAX      Unsigned32
        MAX-ACCESS  read-only
        STATUS      current
        DESCRIPTION
        ""
        REFERENCE   "G.984.4, Pseudowire performance monitoring history data"
        ::= { zxGponOmciCESHisStatsEntry 9 }

    zxGponOmciCESHisStatsDownStrayPkts   OBJECT-TYPE
        SYNTAX      Unsigned32
        MAX-ACCESS  read-only
        STATUS      current
        DESCRIPTION
        ""
        REFERENCE   "G.984.4, Pseudowire performance monitoring history data"
        ::= { zxGponOmciCESHisStatsEntry 10 }

    zxGponOmciCESHisStatsDownRemotePktLoss   OBJECT-TYPE
        SYNTAX      Unsigned32
        MAX-ACCESS  read-only
        STATUS      current
        DESCRIPTION
        ""
        REFERENCE   "G.984.4, Pseudowire performance monitoring history data"
        ::= { zxGponOmciCESHisStatsEntry 11 }

    zxGponOmciCESHisStatsUpTDMLbitPkts   OBJECT-TYPE
        SYNTAX      Unsigned32
        MAX-ACCESS  read-only
        STATUS      current
        DESCRIPTION
        ""
        REFERENCE   "G.984.4, Pseudowire performance monitoring history data"
        ::= { zxGponOmciCESHisStatsEntry 12 }

    zxGponOmciCESHisStatsDownErrSeconds   OBJECT-TYPE
        SYNTAX      Unsigned32
        MAX-ACCESS  read-only
        STATUS      current
        DESCRIPTION
        ""
        REFERENCE   "G.984.4, Pseudowire performance monitoring history data"
        ::= { zxGponOmciCESHisStatsEntry 13 }

    zxGponOmciCESHisStatsDownSeverelyErrSeconds   OBJECT-TYPE
        SYNTAX      Unsigned32
        MAX-ACCESS  read-only
        STATUS      current
        DESCRIPTION
        ""
        REFERENCE   "G.984.4, Pseudowire performance monitoring history data"
        ::= { zxGponOmciCESHisStatsEntry 14 }

    zxGponOmciCESHisStatsDownUnavailableSeconds   OBJECT-TYPE
        SYNTAX      Unsigned32
        MAX-ACCESS  read-only
        STATUS      current
        DESCRIPTION
        ""
        REFERENCE   "G.984.4, Pseudowire performance monitoring history data"
        ::= { zxGponOmciCESHisStatsEntry 15 }

--    zxGponOmciCESHisStatsUpErrSeconds   OBJECT-TYPE
--        SYNTAX      Unsigned32
--        MAX-ACCESS  read-only
--        STATUS      current
--        DESCRIPTION
--        ""
--        REFERENCE   "G.984.4, CES physical interface performance monitoring history data"
--        ::= { zxGponOmciCESHisStatsEntry 16 }
--
--    zxGponOmciCESHisStatsUpSeverelyErrSeconds   OBJECT-TYPE
--        SYNTAX      Unsigned32
--        MAX-ACCESS  read-only
--        STATUS      current
--        DESCRIPTION
--        ""
--        REFERENCE   "G.984.4, CES physical interface performance monitoring history data"
--        ::= { zxGponOmciCESHisStatsEntry 17 }
--
--    zxGponOmciCESHisStatsUpBurstErrSeconds   OBJECT-TYPE
--        SYNTAX      Unsigned32
--        MAX-ACCESS  read-only
--        STATUS      current
--        DESCRIPTION
--        ""
--        REFERENCE   "G.984.4, CES physical interface performance monitoring history data"
--        ::= { zxGponOmciCESHisStatsEntry 18 }
--
--    zxGponOmciCESHisStatsUpUnavailableSeconds   OBJECT-TYPE
--        SYNTAX      Unsigned32
--        MAX-ACCESS  read-only
--        STATUS      current
--        DESCRIPTION
--        ""
--        REFERENCE   "G.984.4, CES physical interface performance monitoring history data"
--        ::= { zxGponOmciCESHisStatsEntry 19 }
--
--    zxGponOmciCESHisStatsUpControlledSlipSeconds   OBJECT-TYPE
--        SYNTAX      Unsigned32
--        MAX-ACCESS  read-only
--        STATUS      current
--        DESCRIPTION
--        ""
--        REFERENCE   "G.984.4, CES physical interface performance monitoring history data"
--        ::= { zxGponOmciCESHisStatsEntry 20 }
        
    zxGponOmciCESHisStatsEntryStatus OBJECT-TYPE
        SYNTAX      RowStatus
        MAX-ACCESS  read-only
        STATUS      current
        DESCRIPTION
        ""
        REFERENCE   "G.984.4"
        ::= { zxGponOmciCESHisStatsEntry 25 }

--Private Eth History Statistics
    zxGponOmciPrivateEthHisStatsTable    OBJECT-TYPE
        SYNTAX      SEQUENCE OF ZxGponOmciPrivateEthHisStatsEntry
        MAX-ACCESS  not-accessible
        STATUS      current
        DESCRIPTION
            ""
        REFERENCE   "Vender specific Ethernet performance
                     Ethernet performance monitoring history data 4"
        ::= { zxGponOmciStatistics 34 }

    zxGponOmciPrivateEthHisStatsEntry OBJECT-TYPE
        SYNTAX      ZxGponOmciPrivateEthHisStatsEntry
        MAX-ACCESS  not-accessible
        STATUS      current
        DESCRIPTION
            "It is entry in the zxGponOmciPrivateEthHisStatsTable."
        INDEX   { zxGponOltIndex, zxGponONTIndex, zxGponUNIIndex }
        ::= { zxGponOmciPrivateEthHisStatsTable 1 }

    ZxGponOmciPrivateEthHisStatsEntry ::=
        SEQUENCE {
            zxGponOmciPrivateEthHisStatsIntervalEndTime  INTEGER,
            zxGponOmciPrivateEthHisStatsThresDataId      INTEGER,
            zxGponOmciPrivateEthHisStatsRxBroadcast      Unsigned32,
            zxGponOmciPrivateEthHisStatsRxUnicast        Unsigned32,
            zxGponOmciPrivateEthHisStatsRxMulticast      Unsigned32,
            zxGponOmciPrivateEthHisStatsRxDiscarded      Unsigned32,
            zxGponOmciPrivateEthHisStatsTxBroadcast      Unsigned32,
            zxGponOmciPrivateEthHisStatsTxUnicast        Unsigned32,
            zxGponOmciPrivateEthHisStatsTxMulticast      Unsigned32,
            zxGponOmciPrivateEthHisStatsTxDiscarded      Unsigned32,
            zxGponOmciPrivateEthHisStatsTxPauseFrames    Unsigned32,
            zxGponOmciPrivateEthHisStatsRxPauseFrames    Unsigned32,
            zxGponOmciPrivateEthHisStatsTxErroredOctets  Unsigned32,
            zxGponOmciPrivateEthHisStatsRxErroredOctets  Unsigned32,
            zxGponOmciPrivateEthHisStatsEntryStatus      RowStatus
        }

    zxGponOmciPrivateEthHisStatsIntervalEndTime OBJECT-TYPE
        SYNTAX      INTEGER
        MAX-ACCESS  read-only
        STATUS      current
        DESCRIPTION
        ""
        REFERENCE   "G.984.4"
        ::= { zxGponOmciPrivateEthHisStatsEntry 1 }

    zxGponOmciPrivateEthHisStatsThresDataId OBJECT-TYPE
        SYNTAX      INTEGER
        MAX-ACCESS  read-only
        STATUS      current
        DESCRIPTION
        ""
        REFERENCE   "G.984.4"
        ::= { zxGponOmciPrivateEthHisStatsEntry 2 }

    zxGponOmciPrivateEthHisStatsRxBroadcast OBJECT-TYPE
        SYNTAX      Unsigned32
        MAX-ACCESS  read-only
        STATUS      current
        DESCRIPTION
        ""
        REFERENCE   "G.984.4 Ethernet performance monitoring history data"
        ::= { zxGponOmciPrivateEthHisStatsEntry 3 }

    zxGponOmciPrivateEthHisStatsRxUnicast OBJECT-TYPE
        SYNTAX      Unsigned32
        MAX-ACCESS  read-only
        STATUS      current
        DESCRIPTION
        ""
        REFERENCE   "G.984.4 Ethernet performance monitoring history data"
        ::= { zxGponOmciPrivateEthHisStatsEntry 4 }

    zxGponOmciPrivateEthHisStatsRxMulticast OBJECT-TYPE
        SYNTAX      Unsigned32
        MAX-ACCESS  read-only
        STATUS      current
        DESCRIPTION
        ""
        REFERENCE   "G.984.4 Ethernet performance monitoring history data"
        ::= { zxGponOmciPrivateEthHisStatsEntry 5 }
        
    zxGponOmciPrivateEthHisStatsRxDiscarded OBJECT-TYPE
        SYNTAX      Unsigned32
        MAX-ACCESS  read-only
        STATUS      current
        DESCRIPTION
        ""
        REFERENCE   "G.984.4 Ethernet performance monitoring history data"
        ::= { zxGponOmciPrivateEthHisStatsEntry 6 }
        
    zxGponOmciPrivateEthHisStatsTxBroadcast OBJECT-TYPE
        SYNTAX      Unsigned32
        MAX-ACCESS  read-only
        STATUS      current
        DESCRIPTION
        ""
        REFERENCE   "G.984.4 Ethernet performance monitoring history data"
        ::= { zxGponOmciPrivateEthHisStatsEntry 7 }

    zxGponOmciPrivateEthHisStatsTxUnicast OBJECT-TYPE
        SYNTAX      Unsigned32
        MAX-ACCESS  read-only
        STATUS      current
        DESCRIPTION
        ""
        REFERENCE   "G.984.4 Ethernet performance monitoring history data"
        ::= { zxGponOmciPrivateEthHisStatsEntry 8 }
        
    zxGponOmciPrivateEthHisStatsTxMulticast OBJECT-TYPE
        SYNTAX      Unsigned32
        MAX-ACCESS  read-only
        STATUS      current
        DESCRIPTION
        ""
        REFERENCE   "G.984.4 Ethernet performance monitoring history data"
        ::= { zxGponOmciPrivateEthHisStatsEntry 9 }

    zxGponOmciPrivateEthHisStatsTxDiscarded OBJECT-TYPE
        SYNTAX      Unsigned32
        MAX-ACCESS  read-only
        STATUS      current
        DESCRIPTION
        ""
        REFERENCE   "G.984.4 Ethernet performance monitoring history data"
        ::= { zxGponOmciPrivateEthHisStatsEntry 10 }
        
    zxGponOmciPrivateEthHisStatsTxPauseFrames OBJECT-TYPE
        SYNTAX      Unsigned32
        MAX-ACCESS  read-only
        STATUS      current
        DESCRIPTION
        ""
        REFERENCE   "G.984.4 Ethernet performance monitoring history data"
        ::= { zxGponOmciPrivateEthHisStatsEntry 11 }
    
    zxGponOmciPrivateEthHisStatsRxPauseFrames OBJECT-TYPE
        SYNTAX      Unsigned32
        MAX-ACCESS  read-only
        STATUS      current
        DESCRIPTION
        ""
        REFERENCE   "G.984.4 Ethernet performance monitoring history data"
        ::= { zxGponOmciPrivateEthHisStatsEntry 12 }
        
    zxGponOmciPrivateEthHisStatsTxErroredOctets OBJECT-TYPE
        SYNTAX      Unsigned32
        MAX-ACCESS  read-only
        STATUS      current
        DESCRIPTION
        ""
        REFERENCE   "G.984.4 Ethernet performance monitoring history data"
        ::= { zxGponOmciPrivateEthHisStatsEntry 13 }
        
    zxGponOmciPrivateEthHisStatsRxErroredOctets OBJECT-TYPE
        SYNTAX      Unsigned32
        MAX-ACCESS  read-only
        STATUS      current
        DESCRIPTION
        ""
        REFERENCE   "G.984.4 Ethernet performance monitoring history data"
        ::= { zxGponOmciPrivateEthHisStatsEntry 14 }        

    zxGponOmciPrivateEthHisStatsEntryStatus OBJECT-TYPE
        SYNTAX      RowStatus
        MAX-ACCESS  read-only
        STATUS      current
        DESCRIPTION
        "This attribute specifies the action of this entry."
        REFERENCE   "G.984.4"
        ::= { zxGponOmciPrivateEthHisStatsEntry 20 }

--OMCI statistics threshold
    zxGponOmciStatsThresholdTable    OBJECT-TYPE
        SYNTAX      SEQUENCE OF ZxGponOmciStatsThresholdEntry
        MAX-ACCESS  not-accessible
        STATUS      current
        DESCRIPTION
            ""
        REFERENCE   "G.984.4 Performance monitoring history data"
        ::= { zxGponOmciStatistics 41 }
        
    zxGponOmciStatsThresholdEntry OBJECT-TYPE
        SYNTAX      ZxGponOmciStatsThresholdEntry
        MAX-ACCESS  not-accessible
        STATUS      current
        DESCRIPTION
            "It is entry in the zxGponOmciStatsThresholdEntry."
        INDEX   {zxGponOmciStatsThresholdType, zxGponOmciStatsThresholdId}
        ::= { zxGponOmciStatsThresholdTable 1 } 

    ZxGponOmciStatsThresholdEntry ::=
        SEQUENCE {
            zxGponOmciStatsThresholdType                  INTEGER,
            zxGponOmciStatsThresholdId                    INTEGER,
            zxGponOmciStatsThresholdName                  OCTET STRING,
            zxGponOmciStatsThresValue1                    Unsigned32,
            zxGponOmciStatsThresValue2                    Unsigned32,
            zxGponOmciStatsThresValue3                    Unsigned32,
            zxGponOmciStatsThresValue4                    Unsigned32,
            zxGponOmciStatsThresValue5                    Unsigned32,
            zxGponOmciStatsThresValue6                    Unsigned32,
            zxGponOmciStatsThresValue7                    Unsigned32,
            zxGponOmciStatsThresValue8                    Unsigned32,
            zxGponOmciStatsThresValue9                    Unsigned32,
            zxGponOmciStatsThresValue10                   Unsigned32,
            zxGponOmciStatsThresValue11                   Unsigned32,
            zxGponOmciStatsThresValue12                   Unsigned32,
            zxGponOmciStatsThresValue13                   Unsigned32,
            zxGponOmciStatsThresValue14                   Unsigned32,
            zxGponOmciStatsThresValue15                   Unsigned32,
            zxGponOmciStatsThresValue16                   Unsigned32,
            zxGponOmciStatsThresValue17                   Unsigned32,
            zxGponOmciStatsThresValue18                   Unsigned32,
            zxGponOmciStatsThresValue19                   Unsigned32,
            zxGponOmciStatsThresValue20                   Unsigned32,
            zxGponOmciStatsThresRefCnt                    INTEGER,
            zxGponOmciStatsThresEntryStatus               RowStatus
        }
     zxGponOmciStatsThresholdType OBJECT-TYPE
        SYNTAX      INTEGER
        MAX-ACCESS  not-accessible
        STATUS      current
        DESCRIPTION
            "This attribute indicates the type of OMCI statistics threshold data.
            1 eth
            2 ces
            3 gem port
            4 bridge port
            5 radius
            6 dot1x
            
            For eth, there are 19 threshold data as follows:
               fcs-err value1
               excessive-collision value2
               late-collision value3
               too-long value4
               rx-buf-overflow value5
               tx-buf-overflow value6
               single-collision value7
               multi-collisions value8
               sqe value9
               deferred-tx value10
               internal-mac-tx-err value11
               internal-mac-rx-err value12
               carrier-sense-err value13
               alignment-err value14
               pppoe-filtered value15
               drop-events value16
               undersize value17
               fragments value18
               jabbers value19
            For ces, there are 10 threshold data as follows:
               down-missing value1
               down-reordered value2
               down-misordered value3
               down-buffer-underrun-overrun value4
               down-malformed value5
               down-stray value6
               down-remote-loss value7
               down-es value8
               down-ses value9
               down-uas value10
            For gem port, there are 3 threshold data as follows:
               lost-packets value1
               misinserted-packets value2
               impaired-blocks value3
            For bridge port, there are 3 threshold data as follows:
               delay-exceeded-discard value1
               mtu-exceeded-discard value2
               received-and-discarded value3
            For radius, there are 2 threshold data as follows:
               retransmission-access-request value1
               received-invalid-radius value2
            For dot1x, there are 2 threshold data as follows:
               received-EAPOL-invalid-frames value1
               received-EAP-length-error-frames value2
            "
        ::= { zxGponOmciStatsThresholdEntry 1}
        
    zxGponOmciStatsThresholdId OBJECT-TYPE
        SYNTAX      INTEGER
        MAX-ACCESS  not-accessible
        STATUS      current
        DESCRIPTION
        "This attribute provides a unique number for each instance of this managed entity.  
        (R, Set-by-create) (mandatory) (4 bytes)"
        ::= { zxGponOmciStatsThresholdEntry 2 }
        
    zxGponOmciStatsThresholdName OBJECT-TYPE
        SYNTAX      OCTET STRING(SIZE(1..63))
        MAX-ACCESS  read-write
        STATUS      current
        DESCRIPTION
        "This attribute provides a unique name for each instance of this managed entity.  
        (R, Set-by-create) (mandatory) (2 bytes)"
        ::= { zxGponOmciStatsThresholdEntry 3 }

    zxGponOmciStatsThresValue1 OBJECT-TYPE
        SYNTAX      Unsigned32
        MAX-ACCESS  read-write
        STATUS      current
        DESCRIPTION
        ""
        REFERENCE   "Threshold data value"
        ::= { zxGponOmciStatsThresholdEntry 4 }

    zxGponOmciStatsThresValue2 OBJECT-TYPE
        SYNTAX      Unsigned32
        MAX-ACCESS  read-write
        STATUS      current
        DESCRIPTION
        ""
        REFERENCE   "Threshold data value"
        ::= { zxGponOmciStatsThresholdEntry 5 }

    zxGponOmciStatsThresValue3 OBJECT-TYPE
        SYNTAX      Unsigned32
        MAX-ACCESS  read-write
        STATUS      current
        DESCRIPTION
        ""
        REFERENCE   "Threshold data value"
        ::= { zxGponOmciStatsThresholdEntry 6 }

    zxGponOmciStatsThresValue4 OBJECT-TYPE
        SYNTAX      Unsigned32
        MAX-ACCESS  read-write
        STATUS      current
        DESCRIPTION
        ""
        REFERENCE   "Threshold data value"
        ::= { zxGponOmciStatsThresholdEntry 7 }

    zxGponOmciStatsThresValue5 OBJECT-TYPE
        SYNTAX      Unsigned32
        MAX-ACCESS  read-write
        STATUS      current
        DESCRIPTION
        ""
        REFERENCE   "Threshold data value"
        ::= { zxGponOmciStatsThresholdEntry 8 }

    zxGponOmciStatsThresValue6 OBJECT-TYPE
        SYNTAX      Unsigned32
        MAX-ACCESS  read-write
        STATUS      current
        DESCRIPTION
        ""
        REFERENCE   "Threshold data value"
        ::= { zxGponOmciStatsThresholdEntry 9 }

    zxGponOmciStatsThresValue7 OBJECT-TYPE
        SYNTAX      Unsigned32
        MAX-ACCESS  read-write
        STATUS      current
        DESCRIPTION
        ""
        REFERENCE   "Threshold data value"
        ::= { zxGponOmciStatsThresholdEntry 10 }

    zxGponOmciStatsThresValue8 OBJECT-TYPE
        SYNTAX      Unsigned32
        MAX-ACCESS  read-write
        STATUS      current
        DESCRIPTION
        ""
        REFERENCE   "Threshold data value"
        ::= { zxGponOmciStatsThresholdEntry 11 }

    zxGponOmciStatsThresValue9 OBJECT-TYPE
        SYNTAX      Unsigned32
        MAX-ACCESS  read-write
        STATUS      current
        DESCRIPTION
        ""
        REFERENCE   "Threshold data value"
        ::= { zxGponOmciStatsThresholdEntry 12 }

    zxGponOmciStatsThresValue10 OBJECT-TYPE
        SYNTAX      Unsigned32
        MAX-ACCESS  read-write
        STATUS      current
        DESCRIPTION
        ""
        REFERENCE   "Threshold data value"
        ::= { zxGponOmciStatsThresholdEntry 13 }

    zxGponOmciStatsThresValue11 OBJECT-TYPE
        SYNTAX      Unsigned32
        MAX-ACCESS  read-write
        STATUS      current
        DESCRIPTION
        ""
        REFERENCE   "Threshold data value"
        ::= { zxGponOmciStatsThresholdEntry 14 }

    zxGponOmciStatsThresValue12 OBJECT-TYPE
        SYNTAX      Unsigned32
        MAX-ACCESS  read-write
        STATUS      current
        DESCRIPTION
        ""
        REFERENCE   "Threshold data value"
        ::= { zxGponOmciStatsThresholdEntry 15 }

    zxGponOmciStatsThresValue13 OBJECT-TYPE
        SYNTAX      Unsigned32
        MAX-ACCESS  read-write
        STATUS      current
        DESCRIPTION
        ""
        REFERENCE   "Threshold data value"
        ::= { zxGponOmciStatsThresholdEntry 16 }

    zxGponOmciStatsThresValue14 OBJECT-TYPE
        SYNTAX      Unsigned32
        MAX-ACCESS  read-write
        STATUS      current
        DESCRIPTION
        ""
        REFERENCE   "Threshold data value"
        ::= { zxGponOmciStatsThresholdEntry 17 }

    zxGponOmciStatsThresValue15 OBJECT-TYPE
        SYNTAX      Unsigned32
        MAX-ACCESS  read-write
        STATUS      current
        DESCRIPTION
        ""
        REFERENCE   "Threshold data value"
        ::= { zxGponOmciStatsThresholdEntry 18 }

    zxGponOmciStatsThresValue16 OBJECT-TYPE
        SYNTAX      Unsigned32
        MAX-ACCESS  read-write
        STATUS      current
        DESCRIPTION
        ""
        REFERENCE   "Threshold data value"
        ::= { zxGponOmciStatsThresholdEntry 19 }

    zxGponOmciStatsThresValue17 OBJECT-TYPE
        SYNTAX      Unsigned32
        MAX-ACCESS  read-write
        STATUS      current
        DESCRIPTION
        ""
        REFERENCE   "Threshold data value"
        ::= { zxGponOmciStatsThresholdEntry 20 }

    zxGponOmciStatsThresValue18 OBJECT-TYPE
        SYNTAX      Unsigned32
        MAX-ACCESS  read-write
        STATUS      current
        DESCRIPTION
        ""
        REFERENCE   "Threshold data value"
        ::= { zxGponOmciStatsThresholdEntry 21 }

    zxGponOmciStatsThresValue19 OBJECT-TYPE
        SYNTAX      Unsigned32
        MAX-ACCESS  read-write
        STATUS      current
        DESCRIPTION
        ""
        REFERENCE   "Threshold data value"
        ::= { zxGponOmciStatsThresholdEntry 22 }

    zxGponOmciStatsThresValue20 OBJECT-TYPE
        SYNTAX      Unsigned32
        MAX-ACCESS  read-write
        STATUS      current
        DESCRIPTION
        ""
        REFERENCE   "Threshold data value"
        ::= { zxGponOmciStatsThresholdEntry 23 }

        
    zxGponOmciStatsThresRefCnt OBJECT-TYPE
        SYNTAX      INTEGER
        MAX-ACCESS  read-only
        STATUS      current
        DESCRIPTION
        "Forbidden to delete table entry if not equal zero."
        ::= { zxGponOmciStatsThresholdEntry 24 }
             
    zxGponOmciStatsThresEntryStatus OBJECT-TYPE
        SYNTAX      RowStatus
        MAX-ACCESS  read-write
        STATUS      current
        DESCRIPTION
        "This attribute specifies the action of this entry."
        REFERENCE   "G.984.4"
        ::= { zxGponOmciStatsThresholdEntry 30 }



--radius current pm
    zxGponOmciRadiusStatsTable    OBJECT-TYPE
        SYNTAX      SEQUENCE OF ZxGponOmciRadiusStatsEntry
        MAX-ACCESS  not-accessible
        STATUS      current
        DESCRIPTION
            ""
        REFERENCE   "G.984.4 9.3.17    Radius performance monitoring history data"
        ::= { zxGponOmciStatistics 15 }

    zxGponOmciRadiusStatsEntry OBJECT-TYPE
        SYNTAX      ZxGponOmciRadiusStatsEntry
        MAX-ACCESS  not-accessible
        STATUS      current
        DESCRIPTION
            "It is entry in the zxGponOmciRadiusStatsTable."
        INDEX   { zxGponOltIndex, zxGponONTIndex }
        ::= { zxGponOmciRadiusStatsTable 1 }

    ZxGponOmciRadiusStatsEntry ::=
        SEQUENCE {
            zxGponOmciRadiusStatsIntervalEndTime              INTEGER,
            zxGponOmciRadiusStatsThresDataId                  INTEGER,
            zxGponOmciRadiusStatsTxAccessReqPkts              Unsigned32,
            zxGponOmciRadiusStatsReTxAccessReqPkts            Unsigned32,
            zxGponOmciRadiusStatsRxAccessChallengePkts        Unsigned32,
            zxGponOmciRadiusStatsRxAccessAcceptPkts           Unsigned32,
            zxGponOmciRadiusStatsRxAccessRejectPkts           Unsigned32,
            zxGponOmciRadiusStatsRxInvalidRadiusPkts          Unsigned32,
            zxGponOmciRadiusStatsEntryStatus                  RowStatus
        }

    zxGponOmciRadiusStatsIntervalEndTime OBJECT-TYPE
        SYNTAX      INTEGER
        MAX-ACCESS  read-only
        STATUS      current
        DESCRIPTION
        ""
        REFERENCE   "G.984.4"
        ::= { zxGponOmciRadiusStatsEntry 1 }

    zxGponOmciRadiusStatsThresDataId OBJECT-TYPE
        SYNTAX      INTEGER
        MAX-ACCESS  read-write
        STATUS      current
        DESCRIPTION
        ""
        REFERENCE   "G.984.4"
        ::= { zxGponOmciRadiusStatsEntry 2 }

    zxGponOmciRadiusStatsTxAccessReqPkts OBJECT-TYPE
        SYNTAX      Unsigned32
        MAX-ACCESS  read-only
        STATUS      current
        DESCRIPTION
        ""
        REFERENCE   "G.984.4 Radius performance monitoring history data"
        ::= { zxGponOmciRadiusStatsEntry 3 }

    zxGponOmciRadiusStatsReTxAccessReqPkts OBJECT-TYPE
        SYNTAX      Unsigned32
        MAX-ACCESS  read-only
        STATUS      current
        DESCRIPTION
        ""
        REFERENCE   "G.984.4 Radius performance monitoring history data"
        ::= { zxGponOmciRadiusStatsEntry 4 }

    zxGponOmciRadiusStatsRxAccessChallengePkts OBJECT-TYPE
        SYNTAX      Unsigned32
        MAX-ACCESS  read-only
        STATUS      current
        DESCRIPTION
        ""
        REFERENCE   "G.984.4 Radius performance monitoring history data"
        ::= { zxGponOmciRadiusStatsEntry 5 }
        
    zxGponOmciRadiusStatsRxAccessAcceptPkts OBJECT-TYPE
        SYNTAX      Unsigned32
        MAX-ACCESS  read-only
        STATUS      current
        DESCRIPTION
        ""
        REFERENCE   "G.984.4 Radius performance monitoring history data"
        ::= { zxGponOmciRadiusStatsEntry 6 }
        
    zxGponOmciRadiusStatsRxAccessRejectPkts OBJECT-TYPE
        SYNTAX      Unsigned32
        MAX-ACCESS  read-only
        STATUS      current
        DESCRIPTION
        ""
        REFERENCE   "G.984.4 Radius performance monitoring history data"
        ::= { zxGponOmciRadiusStatsEntry 7 }

    zxGponOmciRadiusStatsRxInvalidRadiusPkts OBJECT-TYPE
        SYNTAX      Unsigned32
        MAX-ACCESS  read-only
        STATUS      current
        DESCRIPTION
        ""
        REFERENCE   "G.984.4 Radius performance monitoring history data"
        ::= { zxGponOmciRadiusStatsEntry 8 }
        
    zxGponOmciRadiusStatsEntryStatus OBJECT-TYPE
        SYNTAX      RowStatus
        MAX-ACCESS  read-write
        STATUS      current
        DESCRIPTION
        "This attribute specifies the action of this entry."
        REFERENCE   "G.984.4"
        ::= { zxGponOmciRadiusStatsEntry 9 }

--dot1x current pm
    zxGponOmciDot1xStatsTable    OBJECT-TYPE
        SYNTAX      SEQUENCE OF ZxGponOmciDot1xStatsEntry
        MAX-ACCESS  not-accessible
        STATUS      current
        DESCRIPTION
            ""
        REFERENCE   "G.984.4 9.3.17    Dot1x performance monitoring history data"
        ::= { zxGponOmciStatistics 16 }

    zxGponOmciDot1xStatsEntry OBJECT-TYPE
        SYNTAX      ZxGponOmciDot1xStatsEntry
        MAX-ACCESS  not-accessible
        STATUS      current
        DESCRIPTION
            "It is entry in the zxGponOmciDot1xStatsTable."
        INDEX   { zxGponOltIndex, zxGponONTIndex, zxGponPortDot1xUniType, zxGponUNIIndex }
        ::= { zxGponOmciDot1xStatsTable 1 }

    ZxGponOmciDot1xStatsEntry ::=
        SEQUENCE {
            zxGponOmciDot1xStatsIntervalEndTime              INTEGER,
            zxGponOmciDot1xStatsThresDataId                  INTEGER,
            zxGponOmciDot1xStatsRxEAPOLFrames                Unsigned32,
            zxGponOmciDot1xStatsTxEAPOLFrames                Unsigned32,
            zxGponOmciDot1xStatsRxEAPOLStartFrames           Unsigned32,
            zxGponOmciDot1xStatsRxEAPOLLogOffFrames          Unsigned32,
            zxGponOmciDot1xStatsRxEAPOLInvalidFrames         Unsigned32,
            zxGponOmciDot1xStatsRxEAPRespIdFrames            Unsigned32,
            zxGponOmciDot1xStatsRxEAPRespFrames              Unsigned32,
            zxGponOmciDot1xStatsTxEAPReqIdFrames             Unsigned32,
            zxGponOmciDot1xStatsTxEAPReqFrames               Unsigned32,
            zxGponOmciDot1xStatsRxEAPLenErrFrames            Unsigned32,
            zxGponOmciDot1xStatsAutoEAPSuccessFrames         Unsigned32,
            zxGponOmciDot1xStatsAutoEAPFailureFrames         Unsigned32,
            zxGponOmciDot1xStatsEntryStatus                  RowStatus
        }

    zxGponOmciDot1xStatsIntervalEndTime OBJECT-TYPE
        SYNTAX      INTEGER
        MAX-ACCESS  read-only
        STATUS      current
        DESCRIPTION
        ""
        REFERENCE   "G.984.4"
        ::= { zxGponOmciDot1xStatsEntry 1 }

    zxGponOmciDot1xStatsThresDataId OBJECT-TYPE
        SYNTAX      INTEGER
        MAX-ACCESS  read-write
        STATUS      current
        DESCRIPTION
        ""
        REFERENCE   "G.984.4"
        ::= { zxGponOmciDot1xStatsEntry 2 }

    zxGponOmciDot1xStatsRxEAPOLFrames OBJECT-TYPE
        SYNTAX      Unsigned32
        MAX-ACCESS  read-only
        STATUS      current
        DESCRIPTION
        ""
        REFERENCE   "G.984.4 Dot1x performance monitoring history data"
        ::= { zxGponOmciDot1xStatsEntry 3 }

    zxGponOmciDot1xStatsTxEAPOLFrames OBJECT-TYPE
        SYNTAX      Unsigned32
        MAX-ACCESS  read-only
        STATUS      current
        DESCRIPTION
        ""
        REFERENCE   "G.984.4 Dot1x performance monitoring history data"
        ::= { zxGponOmciDot1xStatsEntry 4 }

    zxGponOmciDot1xStatsRxEAPOLStartFrames OBJECT-TYPE
        SYNTAX      Unsigned32
        MAX-ACCESS  read-only
        STATUS      current
        DESCRIPTION
        ""
        REFERENCE   "G.984.4 Dot1x performance monitoring history data"
        ::= { zxGponOmciDot1xStatsEntry 5 }
        
    zxGponOmciDot1xStatsRxEAPOLLogOffFrames OBJECT-TYPE
        SYNTAX      Unsigned32
        MAX-ACCESS  read-only
        STATUS      current
        DESCRIPTION
        ""
        REFERENCE   "G.984.4 Dot1x performance monitoring history data"
        ::= { zxGponOmciDot1xStatsEntry 6 }
        
    zxGponOmciDot1xStatsRxEAPOLInvalidFrames OBJECT-TYPE
        SYNTAX      Unsigned32
        MAX-ACCESS  read-only
        STATUS      current
        DESCRIPTION
        ""
        REFERENCE   "G.984.4 Dot1x performance monitoring history data"
        ::= { zxGponOmciDot1xStatsEntry 7 }

    zxGponOmciDot1xStatsRxEAPRespIdFrames OBJECT-TYPE
        SYNTAX      Unsigned32
        MAX-ACCESS  read-only
        STATUS      current
        DESCRIPTION
        ""
        REFERENCE   "G.984.4 Dot1x performance monitoring history data"
        ::= { zxGponOmciDot1xStatsEntry 8 }

    zxGponOmciDot1xStatsRxEAPRespFrames OBJECT-TYPE
        SYNTAX      Unsigned32
        MAX-ACCESS  read-only
        STATUS      current
        DESCRIPTION
        ""
        REFERENCE   "G.984.4 Dot1x performance monitoring history data"
        ::= { zxGponOmciDot1xStatsEntry 9 }

    zxGponOmciDot1xStatsTxEAPReqIdFrames OBJECT-TYPE
        SYNTAX      Unsigned32
        MAX-ACCESS  read-only
        STATUS      current
        DESCRIPTION
        ""
        REFERENCE   "G.984.4 Dot1x performance monitoring history data"
        ::= { zxGponOmciDot1xStatsEntry 10 }

    zxGponOmciDot1xStatsTxEAPReqFrames OBJECT-TYPE
        SYNTAX      Unsigned32
        MAX-ACCESS  read-only
        STATUS      current
        DESCRIPTION
        ""
        REFERENCE   "G.984.4 Dot1x performance monitoring history data"
        ::= { zxGponOmciDot1xStatsEntry 11 }

    zxGponOmciDot1xStatsRxEAPLenErrFrames OBJECT-TYPE
        SYNTAX      Unsigned32
        MAX-ACCESS  read-only
        STATUS      current
        DESCRIPTION
        ""
        REFERENCE   "G.984.4 Dot1x performance monitoring history data"
        ::= { zxGponOmciDot1xStatsEntry 12 }

    zxGponOmciDot1xStatsAutoEAPSuccessFrames OBJECT-TYPE
        SYNTAX      Unsigned32
        MAX-ACCESS  read-only
        STATUS      current
        DESCRIPTION
        ""
        REFERENCE   "G.984.4 Dot1x performance monitoring history data"
        ::= { zxGponOmciDot1xStatsEntry 13 }

    zxGponOmciDot1xStatsAutoEAPFailureFrames OBJECT-TYPE
        SYNTAX      Unsigned32
        MAX-ACCESS  read-only
        STATUS      current
        DESCRIPTION
        ""
        REFERENCE   "G.984.4 Dot1x performance monitoring history data"
        ::= { zxGponOmciDot1xStatsEntry 14 }
        
    zxGponOmciDot1xStatsEntryStatus OBJECT-TYPE
        SYNTAX      RowStatus
        MAX-ACCESS  read-write
        STATUS      current
        DESCRIPTION
        "This attribute specifies the action of this entry."
        REFERENCE   "G.984.4"
        ::= { zxGponOmciDot1xStatsEntry 15 }
        
--FEC Current Statics G984.4_9.2.11 
    zxGponOmciFecCurrStatsTable    OBJECT-TYPE
        SYNTAX      SEQUENCE OF ZxGponOmciFecCurrStatsEntry
        MAX-ACCESS  not-accessible
        STATUS      current
        DESCRIPTION
            "FEC performance monitoring current data"
        REFERENCE   "9.2.11  FEC performance monitoring history data."
        ::= { zxGponOmciStatistics 18 }

    zxGponOmciFecCurrStatsEntry OBJECT-TYPE
        SYNTAX      ZxGponOmciFecCurrStatsEntry
        MAX-ACCESS  not-accessible
        STATUS      current
        DESCRIPTION
            "It is entry in the zxGponOmciFecCurrStatsTable."
        INDEX   { zxGponOltIndex, zxGponONTIndex }
        ::= { zxGponOmciFecCurrStatsTable 1 }

    ZxGponOmciFecCurrStatsEntry ::=
        SEQUENCE {
            zxGponOmciFecCurrIntvlEndTime              INTEGER,
            zxGponOmciFecCurrThresDataId               INTEGER,
            zxGponOmciFecCurrCrctBytes                 Unsigned32,
            zxGponOmciFecCurrCrctCodeWords             Unsigned32,
            zxGponOmciFecCurrUcrctCodeWords            Unsigned32,
            zxGponOmciFecCurrTotalCodeWords            Unsigned32,
            zxGponOmciFecCurrFecSeconds                Unsigned32,
            zxGponOmciFecCurrEntryStatus               RowStatus
        }

    zxGponOmciFecCurrIntvlEndTime OBJECT-TYPE
        SYNTAX      INTEGER(0..255)
        MAX-ACCESS  read-only
        STATUS      current
        DESCRIPTION
        "This attribute identifies the most recently finished 15-minute 
        interval."
        REFERENCE   "G.984.4"
        ::= { zxGponOmciFecCurrStatsEntry 1 } 
        
    zxGponOmciFecCurrThresDataId OBJECT-TYPE
        SYNTAX      INTEGER(0..65535)
        MAX-ACCESS  read-create
        STATUS      current
        DESCRIPTION
        "This attribute points to an instance of the threshold data 1 managed
         entity that contains PM threshold values. Since no threshold value 
         attribute number exceeds 7, a threshold data 2 ME is optional."
        REFERENCE   "G.984.4"
        ::= { zxGponOmciFecCurrStatsEntry 2 }   
        
    zxGponOmciFecCurrCrctBytes OBJECT-TYPE
        SYNTAX      Unsigned32
        MAX-ACCESS  read-only
        STATUS      current
        DESCRIPTION
        "This attribute counts the number of bytes that were corrected by the 
        FEC function."
        REFERENCE   "G.984.4"
        ::= { zxGponOmciFecCurrStatsEntry 3 } 
                    
    zxGponOmciFecCurrCrctCodeWords OBJECT-TYPE
        SYNTAX      Unsigned32
        MAX-ACCESS  read-only
        STATUS      current
        DESCRIPTION
        "This attribute counts the code words that were corrected by the FEC
         function."
        REFERENCE   "G.984.4"
        ::= { zxGponOmciFecCurrStatsEntry 4 }   
                  
    zxGponOmciFecCurrUcrctCodeWords OBJECT-TYPE
        SYNTAX      Unsigned32
        MAX-ACCESS  read-only
        STATUS      current
        DESCRIPTION
        "This attribute counts the code words that were not corrected by
         the FEC function."
        REFERENCE   "G.984.4"
        ::= { zxGponOmciFecCurrStatsEntry 5 } 
                    
    zxGponOmciFecCurrTotalCodeWords OBJECT-TYPE
        SYNTAX      Unsigned32
        MAX-ACCESS  read-only
        STATUS      current
        DESCRIPTION
        "This attribute counts the total received code words."
        REFERENCE   "G.984.4"
        ::= { zxGponOmciFecCurrStatsEntry 6 } 
                    
    zxGponOmciFecCurrFecSeconds OBJECT-TYPE
        SYNTAX      Unsigned32
        MAX-ACCESS  read-only
        STATUS      current
        DESCRIPTION
        "This attribute counts seconds during which there was a forward error
         correction anomaly."
        REFERENCE   "G.984.4"
        ::= { zxGponOmciFecCurrStatsEntry 7 }                    
        
    zxGponOmciFecCurrEntryStatus OBJECT-TYPE
        SYNTAX      RowStatus
        MAX-ACCESS  read-create
        STATUS      current
        DESCRIPTION 
        "The row status of this entry.The zxGponOmciFecCurrThresDataId need to 
        be configured when add a row to the entry. When add or delete rows in 
        zxGponOmciFecCurrStatsTable,The corresponding entry in 
        zxGponOmciFecHisStatsTable synchronization also be added or deleted."
        ::= { zxGponOmciFecCurrStatsEntry 30 }           
        

--radius history pm
    zxGponOmciRadiusHistStatsTable    OBJECT-TYPE
        SYNTAX      SEQUENCE OF ZxGponOmciRadiusHistStatsEntry
        MAX-ACCESS  not-accessible
        STATUS      current
        DESCRIPTION
            ""
        REFERENCE   "G.984.4 9.3.17    Radius performance monitoring history data"
        ::= { zxGponOmciStatistics 35 }

    zxGponOmciRadiusHistStatsEntry OBJECT-TYPE
        SYNTAX      ZxGponOmciRadiusHistStatsEntry
        MAX-ACCESS  not-accessible
        STATUS      current
        DESCRIPTION
            "It is entry in the zxGponOmciRadiusHistStatsTable."
        INDEX   { zxGponOltIndex, zxGponONTIndex }
        ::= { zxGponOmciRadiusHistStatsTable 1 }

    ZxGponOmciRadiusHistStatsEntry ::=
        SEQUENCE {
            zxGponOmciRadiusHistStatsIntervalEndTime              INTEGER,
            zxGponOmciRadiusHistStatsThresDataId                  INTEGER,
            zxGponOmciRadiusHistStatsTxAccessReqPkts              Unsigned32,
            zxGponOmciRadiusHistStatsReTxAccessReqPkts            Unsigned32,
            zxGponOmciRadiusHistStatsRxAccessChallengePkts        Unsigned32,
            zxGponOmciRadiusHistStatsRxAccessAcceptPkts           Unsigned32,
            zxGponOmciRadiusHistStatsRxAccessRejectPkts           Unsigned32,
            zxGponOmciRadiusHistStatsRxInvalidRadiusPkts          Unsigned32
        }

    zxGponOmciRadiusHistStatsIntervalEndTime OBJECT-TYPE
        SYNTAX      INTEGER
        MAX-ACCESS  read-only
        STATUS      current
        DESCRIPTION
        ""
        REFERENCE   "G.984.4"
        ::= { zxGponOmciRadiusHistStatsEntry 1 }

    zxGponOmciRadiusHistStatsThresDataId OBJECT-TYPE
        SYNTAX      INTEGER
        MAX-ACCESS  read-only
        STATUS      current
        DESCRIPTION
        ""
        REFERENCE   "G.984.4"
        ::= { zxGponOmciRadiusHistStatsEntry 2 }

    zxGponOmciRadiusHistStatsTxAccessReqPkts OBJECT-TYPE
        SYNTAX      Unsigned32
        MAX-ACCESS  read-only
        STATUS      current
        DESCRIPTION
        ""
        REFERENCE   "G.984.4 Radius performance monitoring history data"
        ::= { zxGponOmciRadiusHistStatsEntry 3 }

    zxGponOmciRadiusHistStatsReTxAccessReqPkts OBJECT-TYPE
        SYNTAX      Unsigned32
        MAX-ACCESS  read-only
        STATUS      current
        DESCRIPTION
        ""
        REFERENCE   "G.984.4 Radius performance monitoring history data"
        ::= { zxGponOmciRadiusHistStatsEntry 4 }

    zxGponOmciRadiusHistStatsRxAccessChallengePkts OBJECT-TYPE
        SYNTAX      Unsigned32
        MAX-ACCESS  read-only
        STATUS      current
        DESCRIPTION
        ""
        REFERENCE   "G.984.4 Radius performance monitoring history data"
        ::= { zxGponOmciRadiusHistStatsEntry 5 }
        
    zxGponOmciRadiusHistStatsRxAccessAcceptPkts OBJECT-TYPE
        SYNTAX      Unsigned32
        MAX-ACCESS  read-only
        STATUS      current
        DESCRIPTION
        ""
        REFERENCE   "G.984.4 Radius performance monitoring history data"
        ::= { zxGponOmciRadiusHistStatsEntry 6 }
        
    zxGponOmciRadiusHistStatsRxAccessRejectPkts OBJECT-TYPE
        SYNTAX      Unsigned32
        MAX-ACCESS  read-only
        STATUS      current
        DESCRIPTION
        ""
        REFERENCE   "G.984.4 Radius performance monitoring history data"
        ::= { zxGponOmciRadiusHistStatsEntry 7 }

    zxGponOmciRadiusHistStatsRxInvalidRadiusPkts OBJECT-TYPE
        SYNTAX      Unsigned32
        MAX-ACCESS  read-only
        STATUS      current
        DESCRIPTION
        ""
        REFERENCE   "G.984.4 Radius performance monitoring history data"
        ::= { zxGponOmciRadiusHistStatsEntry 8 }

--dot1x history pm
    zxGponOmciDot1xHistStatsTable    OBJECT-TYPE
        SYNTAX      SEQUENCE OF ZxGponOmciDot1xHistStatsEntry
        MAX-ACCESS  not-accessible
        STATUS      current
        DESCRIPTION
            ""
        REFERENCE   "G.984.4 9.3.17    Dot1x performance monitoring history data"
        ::= { zxGponOmciStatistics 36 }

    zxGponOmciDot1xHistStatsEntry OBJECT-TYPE
        SYNTAX      ZxGponOmciDot1xHistStatsEntry
        MAX-ACCESS  not-accessible
        STATUS      current
        DESCRIPTION
            "It is entry in the zxGponOmciDot1xHistStatsTable."
        INDEX   { zxGponOltIndex, zxGponONTIndex, zxGponPortDot1xUniType, zxGponUNIIndex }
        ::= { zxGponOmciDot1xHistStatsTable 1 }

    ZxGponOmciDot1xHistStatsEntry ::=
        SEQUENCE {
            zxGponOmciDot1xHistStatsIntervalEndTime              INTEGER,
            zxGponOmciDot1xHistStatsThresDataId                  INTEGER,
            zxGponOmciDot1xHistStatsRxEAPOLFrames                Unsigned32,
            zxGponOmciDot1xHistStatsTxEAPOLFrames                Unsigned32,
            zxGponOmciDot1xHistStatsRxEAPOLStartFrames           Unsigned32,
            zxGponOmciDot1xHistStatsRxEAPOLLogOffFrames          Unsigned32,
            zxGponOmciDot1xHistStatsRxEAPOLInvalidFrames         Unsigned32,
            zxGponOmciDot1xHistStatsRxEAPRespIdFrames            Unsigned32,
            zxGponOmciDot1xHistStatsRxEAPRespFrames              Unsigned32,
            zxGponOmciDot1xHistStatsTxEAPReqIdFrames             Unsigned32,
            zxGponOmciDot1xHistStatsTxEAPReqFrames               Unsigned32,
            zxGponOmciDot1xHistStatsRxEAPLenErrFrames            Unsigned32,
            zxGponOmciDot1xHistStatsAutoEAPSuccessFrames         Unsigned32,
            zxGponOmciDot1xHistStatsAutoEAPFailureFrames         Unsigned32
        }

    zxGponOmciDot1xHistStatsIntervalEndTime OBJECT-TYPE
        SYNTAX      INTEGER
        MAX-ACCESS  read-only
        STATUS      current
        DESCRIPTION
        ""
        REFERENCE   "G.984.4"
        ::= { zxGponOmciDot1xHistStatsEntry 1 }

    zxGponOmciDot1xHistStatsThresDataId OBJECT-TYPE
        SYNTAX      INTEGER
        MAX-ACCESS  read-only
        STATUS      current
        DESCRIPTION
        ""
        REFERENCE   "G.984.4"
        ::= { zxGponOmciDot1xHistStatsEntry 2 }

    zxGponOmciDot1xHistStatsRxEAPOLFrames OBJECT-TYPE
        SYNTAX      Unsigned32
        MAX-ACCESS  read-only
        STATUS      current
        DESCRIPTION
        ""
        REFERENCE   "G.984.4 Dot1x performance monitoring history data"
        ::= { zxGponOmciDot1xHistStatsEntry 3 }

    zxGponOmciDot1xHistStatsTxEAPOLFrames OBJECT-TYPE
        SYNTAX      Unsigned32
        MAX-ACCESS  read-only
        STATUS      current
        DESCRIPTION
        ""
        REFERENCE   "G.984.4 Dot1x performance monitoring history data"
        ::= { zxGponOmciDot1xHistStatsEntry 4 }

    zxGponOmciDot1xHistStatsRxEAPOLStartFrames OBJECT-TYPE
        SYNTAX      Unsigned32
        MAX-ACCESS  read-only
        STATUS      current
        DESCRIPTION
        ""
        REFERENCE   "G.984.4 Dot1x performance monitoring history data"
        ::= { zxGponOmciDot1xHistStatsEntry 5 }
        
    zxGponOmciDot1xHistStatsRxEAPOLLogOffFrames OBJECT-TYPE
        SYNTAX      Unsigned32
        MAX-ACCESS  read-only
        STATUS      current
        DESCRIPTION
        ""
        REFERENCE   "G.984.4 Dot1x performance monitoring history data"
        ::= { zxGponOmciDot1xHistStatsEntry 6 }
        
    zxGponOmciDot1xHistStatsRxEAPOLInvalidFrames OBJECT-TYPE
        SYNTAX      Unsigned32
        MAX-ACCESS  read-only
        STATUS      current
        DESCRIPTION
        ""
        REFERENCE   "G.984.4 Dot1x performance monitoring history data"
        ::= { zxGponOmciDot1xHistStatsEntry 7 }

    zxGponOmciDot1xHistStatsRxEAPRespIdFrames OBJECT-TYPE
        SYNTAX      Unsigned32
        MAX-ACCESS  read-only
        STATUS      current
        DESCRIPTION
        ""
        REFERENCE   "G.984.4 Dot1x performance monitoring history data"
        ::= { zxGponOmciDot1xHistStatsEntry 8 }

    zxGponOmciDot1xHistStatsRxEAPRespFrames OBJECT-TYPE
        SYNTAX      Unsigned32
        MAX-ACCESS  read-only
        STATUS      current
        DESCRIPTION
        ""
        REFERENCE   "G.984.4 Dot1x performance monitoring history data"
        ::= { zxGponOmciDot1xHistStatsEntry 9 }

    zxGponOmciDot1xHistStatsTxEAPReqIdFrames OBJECT-TYPE
        SYNTAX      Unsigned32
        MAX-ACCESS  read-only
        STATUS      current
        DESCRIPTION
        ""
        REFERENCE   "G.984.4 Dot1x performance monitoring history data"
        ::= { zxGponOmciDot1xHistStatsEntry 10 }

    zxGponOmciDot1xHistStatsTxEAPReqFrames OBJECT-TYPE
        SYNTAX      Unsigned32
        MAX-ACCESS  read-only
        STATUS      current
        DESCRIPTION
        ""
        REFERENCE   "G.984.4 Dot1x performance monitoring history data"
        ::= { zxGponOmciDot1xHistStatsEntry 11 }

    zxGponOmciDot1xHistStatsRxEAPLenErrFrames OBJECT-TYPE
        SYNTAX      Unsigned32
        MAX-ACCESS  read-only
        STATUS      current
        DESCRIPTION
        ""
        REFERENCE   "G.984.4 Dot1x performance monitoring history data"
        ::= { zxGponOmciDot1xHistStatsEntry 12 }

    zxGponOmciDot1xHistStatsAutoEAPSuccessFrames OBJECT-TYPE
        SYNTAX      Unsigned32
        MAX-ACCESS  read-only
        STATUS      current
        DESCRIPTION
        ""
        REFERENCE   "G.984.4 Dot1x performance monitoring history data"
        ::= { zxGponOmciDot1xHistStatsEntry 13 }

    zxGponOmciDot1xHistStatsAutoEAPFailureFrames OBJECT-TYPE
        SYNTAX      Unsigned32
        MAX-ACCESS  read-only
        STATUS      current
        DESCRIPTION
        ""
        REFERENCE   "G.984.4 Dot1x performance monitoring history data"
        ::= { zxGponOmciDot1xHistStatsEntry 14 }


----------------------------------------------------------
--gemport QoS data 
--Add by Fancx 20090805
----------------------------------------------------------
    zxGponGemPortTrafficLimitTable    OBJECT-TYPE
        SYNTAX      SEQUENCE OF ZxGponGemPortTrafficLimitEntry
        MAX-ACCESS  not-accessible
        STATUS      current
        DESCRIPTION
            ""
        REFERENCE   "G.984.4/9.11.1 & 9.11.2    Traffic management/Priority queue-G & Traffic scheduler-G"
        ::= { zxGponTrafficMgmt 31 }

    zxGponGemPortTrafficLimitEntry OBJECT-TYPE
        SYNTAX      ZxGponGemPortTrafficLimitEntry
        MAX-ACCESS  not-accessible
        STATUS      current
        DESCRIPTION
            "It is entry in the zxGponGemPortTrafficLimitTable."
        INDEX   { zxGponOltIndex, zxGponONTIndex, zxGponGemPortIndex }
        ::= { zxGponGemPortTrafficLimitTable 1 }

    ZxGponGemPortTrafficLimitEntry ::=
        SEQUENCE {
            zxGponGemPortUpTrafficLimitProfile        Unsigned32,
            zxGponGemPortDownTrafficLimitProfile      Unsigned32                 
        }

        
    zxGponGemPortUpTrafficLimitProfile OBJECT-TYPE
        SYNTAX      Unsigned32
        MAX-ACCESS  read-write
        STATUS      current
        DESCRIPTION
        "This attribute points to the instance of the GEM traffic descriptor managed entity 
        that contains the upstream traffic parameters used for this GEM port network CTP ME."
        REFERENCE   "G.984.4 9.2.3 GEM port network CTP"
        ::= { zxGponGemPortTrafficLimitEntry 1 }
        
    zxGponGemPortDownTrafficLimitProfile OBJECT-TYPE
        SYNTAX      Unsigned32
        MAX-ACCESS  read-write
        STATUS      current
        DESCRIPTION
        "This attribute points to the instance of the priority queue-G used for this GEM port network CTP 
        in the downstream direction. "
        REFERENCE   "G.984.4 9.2.3 GEM port network CTP"
        ::= { zxGponGemPortTrafficLimitEntry 2 }        

 
----------------------------------------------------------
--traffic descriptor data 
----------------------------------------------------------        
    zxGponGemTrafficProfileTable    OBJECT-TYPE
        SYNTAX      SEQUENCE OF ZxGponGemTrafficProfileEntry
        MAX-ACCESS  not-accessible
        STATUS      current
        DESCRIPTION
            "The traffic descriptor allows for traffic management. 
            A priority controlled ONT can point from a MAC bridge port 
            configuration data ME to a GEM traffic descriptor in order 
            to implement traffic management (marking, policing). 
            A rate controlled ONT can point to a GEM traffic descriptor 
            from either a MAC bridge port configuration data ME or 
            GEM port network CTP to implement traffic management (marking, shaping)."
        REFERENCE   "G.984.4/9.11.3    Traffic Descriptor"
        ::= { zxGponTrafficMgmt 32 }

    zxGponGemTrafficProfileEntry OBJECT-TYPE
        SYNTAX      ZxGponGemTrafficProfileEntry
        MAX-ACCESS  not-accessible
        STATUS      current
        DESCRIPTION
            "It is entry in the zxGponGemTrafficProfileTable."
        INDEX   { zxGponGemTrafficProfileId }
        ::= { zxGponGemTrafficProfileTable 1 }

    ZxGponGemTrafficProfileEntry ::=
        SEQUENCE {
            zxGponGemTrafficProfileId            Unsigned32,
            zxGponGemTrafficProfileName            DisplayString,     
            zxGponGemTrafficProfileCir            Unsigned32,
            zxGponGemTrafficProfilePir            Unsigned32,
            zxGponGemTrafficProfileCbs            Unsigned32,
            zxGponGemTrafficProfilePbs            Unsigned32,
            zxGponGemTrafficProfileColourMode        INTEGER,
            zxGponGemTrafficProfileInColourMarkMode    INTEGER,
            zxGponGemTrafficProfileOutColourMarkMode    INTEGER,
            zxGponGemTrafficProfileMeterType        INTEGER,
            zxGponGemTrafficProfileRefCnt        Unsigned32,
            zxGponGemTrafficProfileEntryStatus        RowStatus     
        }
        
        
    zxGponGemTrafficProfileId OBJECT-TYPE
        SYNTAX      Unsigned32
        MAX-ACCESS  not-accessible
        STATUS      current
        DESCRIPTION
        "Traffic Descriptor Profile ID"
        REFERENCE   ""
        ::= { zxGponGemTrafficProfileEntry 1 }   
        
    zxGponGemTrafficProfileName OBJECT-TYPE
        SYNTAX      DisplayString(SIZE(1..64))
        MAX-ACCESS  read-write
        STATUS      current
        DESCRIPTION
        "Traffic Descriptor Profile Name"
        REFERENCE   ""
        ::= { zxGponGemTrafficProfileEntry 2 }             

    zxGponGemTrafficProfileCir OBJECT-TYPE
        SYNTAX      Unsigned32
        MAX-ACCESS  read-write
        STATUS      current
        DESCRIPTION
        "This attribute specifies committed information rate, in byte/s. "
        REFERENCE   "G.984.4 9.11.3 GEM traffic descriptor"
        ::= { zxGponGemTrafficProfileEntry 3 }
        
    zxGponGemTrafficProfilePir OBJECT-TYPE
        SYNTAX      Unsigned32
        MAX-ACCESS  read-write
        STATUS      current
        DESCRIPTION
        "This attribute specifies peak information rate, in byte/s."
        REFERENCE   "G.984.4 9.11.3 GEM traffic descriptor"
        ::= { zxGponGemTrafficProfileEntry 4 }

    zxGponGemTrafficProfileCbs OBJECT-TYPE
        SYNTAX      Unsigned32
        MAX-ACCESS  read-write
        STATUS      current
        DESCRIPTION
        "This attribute specifies committed block size, in bytes. "
        REFERENCE   "G.984.4 9.11.3 GEM traffic descriptor"
        ::= { zxGponGemTrafficProfileEntry 5 }

    zxGponGemTrafficProfilePbs OBJECT-TYPE
        SYNTAX      Unsigned32
        MAX-ACCESS  read-write
        STATUS      current
        DESCRIPTION
        "This attribute specifies peak block size, in bytes. "
        REFERENCE   "G.984.4 9.11.3 GEM traffic descriptor"
        ::= { zxGponGemTrafficProfileEntry 6 }

    zxGponGemTrafficProfileColourMode OBJECT-TYPE
        SYNTAX      INTEGER{
                    colourblind(1),
                    colouraware(2)
                    }
        MAX-ACCESS  read-write
        STATUS      current
        DESCRIPTION
        "This attribute specifies whether the colour marking algorithm 
        considers pre-existing marking on ingress packets (colour-aware) 
        or ignores it (colour-blind). If colour-aware, packets can only 
        be demoted (from green to yellow or red, or from yellow to red). "
        REFERENCE   "G.984.4 9.11.3 GEM traffic descriptor"
        ::= { zxGponGemTrafficProfileEntry 7 }
        
    zxGponGemTrafficProfileInColourMarkMode OBJECT-TYPE
        SYNTAX      INTEGER{
                    nomarking(1),
                    dei(2),
                    pcp8p0d(3),
                    pcp7p1d(4),
                    pcp6p2d(5),
                    pcp5p3d(6),
                    dscpaf(7)
                    }
        MAX-ACCESS  read-write
        STATUS      current
        DESCRIPTION
        "This attribute is meaningful in colour-aware mode. 
        It specifies how the pre-existing drop precedence is 
        marked on ingress packets. For DEI and PCP marking, 
        a drop eligible indicator is equivalent to yellow colour, 
        otherwise the colour is green. For DSCP AF marking, 
        the lowest drop precedence is equivalent to green, 
        otherwise the colour is yellow."
        REFERENCE   "G.984.4 9.11.3 GEM traffic descriptor"
        ::= { zxGponGemTrafficProfileEntry 8 }        

    zxGponGemTrafficProfileOutColourMarkMode OBJECT-TYPE
        SYNTAX      INTEGER{
                    nomarking(1),
                    internalmarking(2),
                    dei(3),
                    pcp8p0d(4),
                    pcp7p1d(5),
                    pcp6p2d(6),
                    pcp5p3d(7),
                    dscpaf(8)
                    }
        MAX-ACCESS  read-write
        STATUS      current
        DESCRIPTION
        "This attribute specifies how drop precedence is to be 
        marked by the ONT on egress packets. If set to internal 
        marking only, the externally visible packet contents are 
        not modified, but the packet is identified in a vendor-specific 
        local way that indicates its colour to the priority queue-G ME. 
        It is possible for the egress marking to differ from the ingress 
        marking; for example ingress PCP marking could be translated to 
        DEI egress marking."
        REFERENCE   "G.984.4 9.11.3 GEM traffic descriptor"
        ::= { zxGponGemTrafficProfileEntry 9 } 
        
    zxGponGemTrafficProfileMeterType OBJECT-TYPE
        SYNTAX      INTEGER{
                    notspecified(1),
                    rfc4115(2),
                    rfc2698(3)
                    }
        MAX-ACCESS  read-write
        STATUS      current
        DESCRIPTION
        "This attribute specifies the algorithm used to determine the colour of the packet. "
        REFERENCE   "G.984.4 9.11.3 GEM traffic descriptor"
        ::= { zxGponGemTrafficProfileEntry 10 }

    zxGponGemTrafficProfileRefCnt OBJECT-TYPE
        SYNTAX      Unsigned32
        MAX-ACCESS  read-only
        STATUS      current
        DESCRIPTION
        ""
        REFERENCE   ""
        ::= { zxGponGemTrafficProfileEntry 11 }

    zxGponGemTrafficProfileEntryStatus OBJECT-TYPE
        SYNTAX      RowStatus
        MAX-ACCESS  read-write
        STATUS      current
        DESCRIPTION
        ""
        REFERENCE   ""
        ::= { zxGponGemTrafficProfileEntry 31 }    

----------------------------------------------------------
--onu capability data 
----------------------------------------------------------        
    zxGponONTCapabilityTable    OBJECT-TYPE
        SYNTAX      SEQUENCE OF ZxGponONTCapabilityEntry
        MAX-ACCESS  not-accessible
        STATUS      current
        DESCRIPTION
            "This table specifies the capability of ONU capability."
        REFERENCE   ""
        ::= { zxGponONTEquipMgmt 9 }

    zxGponONTCapabilityEntry OBJECT-TYPE
        SYNTAX      ZxGponONTCapabilityEntry
        MAX-ACCESS  not-accessible
        STATUS      current
        DESCRIPTION
            "It is entry in the zxGponONTCapabilityTable."
        INDEX   { zxGponOltIndex, zxGponONTIndex }
        ::= { zxGponONTCapabilityTable 1 }

     ZxGponONTCapabilityEntry ::=
        SEQUENCE {
        zxGponOnuTcontNum                INTEGER,
        zxGponOnuTotalPrioQueueNum            INTEGER,     
        zxGponOnuUpPrioQueueNum                INTEGER,
        zxGponOnuDownPrioQueueNum            INTEGER,
        zxGponOnuTrafficSchedulerNum            INTEGER,
        zxGponOnuTrafficManagementOption        INTEGER,
        zxGponOnuTotalUniNum                INTEGER,
        zxGponOnuEthUniNum                INTEGER,
        zxGponOnuCesUniNum                INTEGER,
        zxGponOnuPotsUniNum                INTEGER,
        zxGponOnuVideoUniNum                INTEGER,
        zxGponOnuIpHostNum                INTEGER     
        }

      zxGponOnuTcontNum OBJECT-TYPE
          SYNTAX      INTEGER
          MAX-ACCESS  read-only
          STATUS      current
          DESCRIPTION 
          "This attribute reports the number of TCONT. "
          ::= { zxGponONTCapabilityEntry 1 }        

      zxGponOnuTotalPrioQueueNum OBJECT-TYPE
          SYNTAX      INTEGER
          MAX-ACCESS  read-only
          STATUS      current
          DESCRIPTION
          " This attribute reports the total number of priority queues 
          that are not associated with a circuit pack, but with the 
          ONT in its entirety. "
          REFERENCE   "G.984.4 9.1.2"
          ::= { zxGponONTCapabilityEntry 2 }  

      zxGponOnuUpPrioQueueNum OBJECT-TYPE
          SYNTAX      INTEGER
          MAX-ACCESS  read-only
          STATUS      current
          DESCRIPTION
          "This attribute reports the total number of up priority queues. "
          ::= { zxGponONTCapabilityEntry 3 }

      zxGponOnuDownPrioQueueNum OBJECT-TYPE
          SYNTAX      INTEGER
          MAX-ACCESS  read-only
          STATUS      current
          DESCRIPTION
          "This attribute reports the total number of down priority queues. "
          ::= { zxGponONTCapabilityEntry 4 }

      zxGponOnuTrafficSchedulerNum OBJECT-TYPE
          SYNTAX      INTEGER
          MAX-ACCESS  read-only
          STATUS      current
          DESCRIPTION
          " This attribute reports the total number of traffic schedulers 
          that are not associated with a circuit pack, but with the 
          ONT in its entirety."
          REFERENCE   "G.984.4 9.1.2"
          ::= { zxGponONTCapabilityEntry 5 }
          
      zxGponOnuTrafficManagementOption OBJECT-TYPE
          SYNTAX      INTEGER{
                      prioctrl(1),
                      ratectrl(2)
                      }
          MAX-ACCESS  read-only
          STATUS      current
          DESCRIPTION
          " This attribute identifies the upstream traffic management function 
          implemented in the ONT. "
          REFERENCE   "G.984.4 9.1.1"
          ::= { zxGponONTCapabilityEntry 6 }
          
      zxGponOnuTotalUniNum OBJECT-TYPE
          SYNTAX      INTEGER
          MAX-ACCESS  read-only
          STATUS      current
          DESCRIPTION
          "This attribute identifies the total number of UNI. "
          ::= { zxGponONTCapabilityEntry 7 }
          
      zxGponOnuEthUniNum OBJECT-TYPE
          SYNTAX      INTEGER
          MAX-ACCESS  read-only
          STATUS      current
          DESCRIPTION
          "This attribute identifies the number of ethernet UNI. "
          ::= { zxGponONTCapabilityEntry 8 }
          
      zxGponOnuCesUniNum OBJECT-TYPE
          SYNTAX      INTEGER
          MAX-ACCESS  read-only
          STATUS      current
          DESCRIPTION
          "This attribute identifies the number of CES UNI. "
          ::= { zxGponONTCapabilityEntry 9 }
          
      zxGponOnuPotsUniNum OBJECT-TYPE
          SYNTAX      INTEGER
          MAX-ACCESS  read-only
          STATUS      current
          DESCRIPTION
          "This attribute identifies the number of POTS UNI. "
          ::= { zxGponONTCapabilityEntry 10 }
          
      zxGponOnuVideoUniNum OBJECT-TYPE
          SYNTAX      INTEGER
          MAX-ACCESS  read-only
          STATUS      current
          DESCRIPTION
          "This attribute identifies the number of video UNI. "
          ::= { zxGponONTCapabilityEntry 11 }
          
      zxGponOnuIpHostNum OBJECT-TYPE
          SYNTAX      INTEGER
          MAX-ACCESS  read-only
          STATUS      current
          DESCRIPTION
          "This attribute identifies the number of IP host. "
          ::= { zxGponONTCapabilityEntry 12 }

    zxGponONTSysTable    OBJECT-TYPE
        SYNTAX      SEQUENCE OF ZxGponONTSysEntry
        MAX-ACCESS  not-accessible
        STATUS      current
        DESCRIPTION
            ""
        REFERENCE   ""
        ::= { zxGponONTEquipMgmt 10 }

    zxGponONTSysEntry OBJECT-TYPE
        SYNTAX      ZxGponONTSysEntry
        MAX-ACCESS  not-accessible
        STATUS      current
        DESCRIPTION
            "It is entry in the zxGponONTSysTable."
        INDEX   { zxGponOltIndex, zxGponONTIndex }
        ::= { zxGponONTSysTable 1 }

     ZxGponONTSysEntry ::=
        SEQUENCE {
            zxGponOmciOnuSysCpuLoad                 INTEGER,
            zxGponOmciOnuSysMemUsage                INTEGER,     
            zxGponOmciOnuSysCpuLoadThreshold        INTEGER,
            zxGponOmciOnuSysMemUsageThreshold       INTEGER
        }

     zxGponOmciOnuSysCpuLoad OBJECT-TYPE
          SYNTAX      INTEGER
          MAX-ACCESS  read-only
          STATUS      current
          DESCRIPTION
          "CPU usage of ONU in percent."
          REFERENCE   ""
          ::= { zxGponONTSysEntry 1 }
          
     zxGponOmciOnuSysMemUsage OBJECT-TYPE
          SYNTAX      INTEGER
          MAX-ACCESS  read-only
          STATUS      current
          DESCRIPTION
          "Memory usage of ONU in percent."
          REFERENCE   ""
          ::= { zxGponONTSysEntry 2 }
          
     zxGponOmciOnuSysCpuLoadThreshold OBJECT-TYPE
          SYNTAX      INTEGER(0..100)
          MAX-ACCESS  read-write
          STATUS      current
          DESCRIPTION
          "Alarm threshold of CPU usage."
          REFERENCE   ""
          ::= { zxGponONTSysEntry 3 }

     zxGponOmciOnuSysMemUsageThreshold OBJECT-TYPE
          SYNTAX      INTEGER(0..100)
          MAX-ACCESS  read-write
          STATUS      current
          DESCRIPTION
          "Alarm threshold of Memory usage."
          REFERENCE   ""
          ::= { zxGponONTSysEntry 4 }

END
