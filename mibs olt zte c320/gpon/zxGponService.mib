-- *****************************************************************
-- ZTE GPON MIB
--
-- 09-27-2006
--
-- Copyright(c) 2006 ZTE Corporation
-- All rights reserved.
-- *****************************************************************

ZXGPON-SERVICE-MIB DEFINITIONS ::= BEGIN 
    IMPORTS 
        enterprises                      FROM RFC1155-SMI
        RowStatus                        FROM SNMPv2-TC
        TruthValue                       FROM SNMPv2-TC
        Unsigned32                       FROM SNMPv2-SMI
        Counter64                        FROM SNMPv2-SMI
        IpAddress                        FROM SNMPv2-SMI
        Integer32                        FROM SNMPv2-SMI
        DateAndTime                      FROM SNMPv2-TC
        MacAddress                       FROM SNMPv2-TC
        TEXTUAL-CONVENTION               FROM SNMPv2-TC
        MODULE-IDENTITY                  FROM SNMPv2-SMI
        OBJECT-TYPE                      FROM SNMPv2-SMI
        NOTIFICATION-TYPE                FROM SNMPv2-SMI
        Gauge32                          FROM SNMPv2-SMI
        DisplayString                    FROM SNMPv2-TC
        ifIndex                          FROM RFC1213-MIB
        zxGponUNIIndex                   FROM ZXGPON-ONTMGMT-MIB;
    zxEnterpriseMib   OBJECT IDENTIFIER ::= { enterprises 3902}
    zxPON             OBJECT IDENTIFIER ::= { zxEnterpriseMib 1012}

    zxGponRootMib MODULE-IDENTITY 
        LAST-UPDATED "200609270000Z"  -- September 27, 2006"
        ORGANIZATION 
            "ZTE Corp."
        CONTACT-INFO 
            "ZTE GPON Working Group: 
            http://www.zte.com.cn
            e-mail:
            guo.hongjian@zte.com.cn
            "
        DESCRIPTION
            "The MIB module for defining ZXGPON base OID. OID programming:
             zxGponRootMib 1     , index(zxGponMgmtIndex)
             zxGponRootMib 2-5   , reserve
             zxGponRootMib 6     , Absolut private MIB(zxGponAbsPrivate)
             zxGponRootMib 7-9   , reserve
             zxGponRootMib 10    , Standard global MIB(zxGponStandardGlobal)
             zxGponRootMib 11    , Private global MIB(zxGponPrivateGlobal)
             zxGponRootMib 12    , Standard OLT MIB(zxGponStandardOlt)
             zxGponRootMib 13    , Private OLT MIB(zxGponPrivateOlt)
             zxGponRootMib 14-20 , reserve
             zxGponRootMib 21    , ONT equipment management(zxGponOntEquipMgmt)
             zxGponRootMib 22    , ANI management(zxGponAniMgmt)
             zxGponRootMib 23    , UNI Management(zxGponUniMgmt)
             zxGponRootMib 24    , Connection Management(zxGponConnMgmt)
             zxGponRootMib 25    , Traffic management(zxGponTrafficMgmt)
             zxGponRootMib 26    , Profile management(zxGponProfileMgmt)
             zxGponRootMib 27    , Standard ONU MIB(zxGponStandardOnu)
             zxGponRootMib 28    , Private ONU MIB(zxGponPrivateOnu)
             zxGponRootMib 30    , Service management MIB(zxGponServiceMgmt)
             zxGponRootMib 45    , Private TRAP MIB(zxGponTraps)
             zxGponRootMib 100   , Dummy MIB indicating the termination of gpon mibs(zxGponTermination)
             
             zxGponUniMgmt 1-5   , reserve
             zxGponUniMgmt 6     , Video Service MIB(zxGponUniVideoService)
             zxGponUniMgmt 7     , TDM Service MIB(zxGponUniTdmService)
             zxGponUniMgmt 8     , Ethernet Service MIB(zxGponUniEthService)
             zxGponUniMgmt 9     , CES MIB(zxGponUniCesService)
            "
   
        REVISION    "200609270000Z"  -- September 27, 2006"
        DESCRIPTION "Initial version, published as ZTE enterprises MIB."
   
        ::= { zxPON 3 }

    zxGponTermination    OBJECT IDENTIFIER ::= { zxGponRootMib 100}
    
    zxGponTerminationDummy OBJECT-TYPE
        SYNTAX      INTEGER
        MAX-ACCESS  read-only
        STATUS      current
        DESCRIPTION
                "The dummy object indicats the termination of all gpon mibs."
        ::= { zxGponTermination 1 }   

    zxGponMgmtIndex    OBJECT IDENTIFIER ::= { zxGponRootMib 1}
    zxAnGponRevision     OBJECT-TYPE 
       SYNTAX           BITS 
           {
               gemportUpQueue(0),
               onuSnAndPwBind(1),
               onuSourceMacFilter(2),
               onuOmciBandwidth(3),
               onuEnableWithSn(4),
               onuFec(5),
               onuRegistration(6),
               voipServiceProvisioningByProfile(7),
               macBridgePortTrafficDescriptor(8),
               trafficProfileCbsAndPbs(9)
           } 
       MAX-ACCESS       read-only
       STATUS           current
       DESCRIPTION      "Module revision flag."
       ::=  {  zxGponRootMib  2  }

    OntVendorId ::= TEXTUAL-CONVENTION
        STATUS       current
        DESCRIPTION
            "Represents the vendor of the ONT."
        SYNTAX       OCTET STRING (SIZE (4))

    OntVersionId ::= TEXTUAL-CONVENTION
        STATUS       current
        DESCRIPTION
            "Represents the version of the ONT."
        SYNTAX       OCTET STRING (SIZE (14))

    OntSerialNumber ::= TEXTUAL-CONVENTION
        STATUS       current
        DESCRIPTION
            "Represents the unique for each ONT."
        SYNTAX       OCTET STRING (SIZE (8))

    OntEquipmentId ::= TEXTUAL-CONVENTION
        STATUS       current
        DESCRIPTION
            "Represents the specific type of ONT."
        SYNTAX       OCTET STRING (SIZE (20))

    ZxGponRecordName ::= TEXTUAL-CONVENTION
        STATUS       current
        DESCRIPTION
            "Represents the specific type of templet."
        SYNTAX       OCTET STRING (SIZE (0..64))
    
    ZxOntList ::= TEXTUAL-CONVENTION
        STATUS      current
        DESCRIPTION
            "The first octet indicates one PON OLT ID number, and 
             Each four octets indicates one ONT/ONU ID number 
             that thses ONTs belong to the PON OLT, with from the
             second octet to fifth octect specifying first ONT/ONU,
             from the sixth octet to ninth octet specifying second
             ONT/ONU, etc. example, PON OLT 1, ONT 1 ONT 100, ONT 333,
             it is that '0100000001000000640000014D'."
        SYNTAX      OCTET STRING(SIZE (0..256))

    ZxPortIdList ::= TEXTUAL-CONVENTION
        STATUS      current
        DESCRIPTION
            "The first octet indicates one PON OLT ID number, and 
             Each four octets indicates one PortId number that thses 
             PortIds belong to the PON OLT, with from the second octet 
             to fifth octect specifying first PortId Number, from the 
             sixth octet to ninth octet specifying second PortId Number,
             etc. example, PON OLT 1, PortId 1 - PortId 3, it is that 
             '01000000010000000200000003'."
        SYNTAX      OCTET STRING(SIZE (0..256))

    ZxIndexList ::= TEXTUAL-CONVENTION
        STATUS      current
        DESCRIPTION
            "Each four octets indicates one table index number, with from
             the first octet to fourth octect specifying first index Number,
             from the fifth octet to eighth octet specifying second index Number,
             etc. example, index 1, index 10000, index 245678, it is that '00000001
             000027100003BFAE'."
        SYNTAX      OCTET STRING(SIZE (0..256))

    -- OLT and ONU Index table
    -- Only PONC board agent
    
    zxGponOltOnuTable OBJECT-TYPE
        SYNTAX      SEQUENCE OF ZxGponOltOnuEntry
        MAX-ACCESS  not-accessible
        STATUS      current
        DESCRIPTION
            "OLT and ONU table."
        ::= { zxGponMgmtIndex 1 }

    zxGponOltOnuEntry OBJECT-TYPE
        SYNTAX      ZxGponOltOnuEntry
        MAX-ACCESS  not-accessible
        STATUS      current
        DESCRIPTION
            "An entry in the OLT and ONU table."
        INDEX   { zxGponMgmtPonOltId, zxGponMgmtPonOnuId }
        ::= { zxGponOltOnuTable 1 }

    ZxGponOltOnuEntry ::=
        SEQUENCE {
            zxGponMgmtPonOltId               INTEGER,
            zxGponMgmtPonOnuId               INTEGER,
            zxGponMgmtPonEntryStatus         RowStatus
        }
        
    zxGponMgmtPonOltId OBJECT-TYPE
        SYNTAX      INTEGER
        MAX-ACCESS  read-only
        STATUS      current
        DESCRIPTION
            "OLT identifier, from 1 to N.
            bit 31~28?atype(1)
            bit 27~24?ashelf(0)
            bit 23~16?aslotId
            bit 16~8?aoltId
            bit 7~0?areserved(0)"
        ::= { zxGponOltOnuEntry 1}

    zxGponMgmtPonOnuId OBJECT-TYPE
        SYNTAX      INTEGER
        MAX-ACCESS  read-only
        STATUS      current
        DESCRIPTION
            "an ONU in an OLT, from 1 to M."
        ::= { zxGponOltOnuEntry 2}

    zxGponMgmtPonEntryStatus OBJECT-TYPE
        SYNTAX      RowStatus
        MAX-ACCESS  read-create
        STATUS      current
        DESCRIPTION
            ""
        ::= { zxGponOltOnuEntry 3}
        
--zxGponPrivateGlobal.mi2
    zxGponPrivateGlobal OBJECT IDENTIFIER ::= { zxGponRootMib 11 }

    zxGponOltDevInfoTable OBJECT-TYPE
        SYNTAX      SEQUENCE OF ZxGponOltDevInfoEntry
        MAX-ACCESS  not-accessible
        STATUS      current
        DESCRIPTION
            ""
        ::= { zxGponPrivateGlobal 1 }

    zxGponOltDevInfoEntry OBJECT-TYPE
        SYNTAX      ZxGponOltDevInfoEntry
        MAX-ACCESS  not-accessible
        STATUS      current
        DESCRIPTION
            "It is entry in the zxGponOltDevInfoTable."
        INDEX   { zxGponMgmtPonOltId }
        ::= { zxGponOltDevInfoTable 1 }
        
    ZxGponOltDevInfoEntry ::=
        SEQUENCE {
            zxGponDbaEnable              TruthValue
        }

    zxGponDbaEnable OBJECT-TYPE
        SYNTAX      TruthValue
        MAX-ACCESS  read-write
        STATUS      current
        DESCRIPTION
                "Enable or disable DBA on this olt ."
        ::= { zxGponOltDevInfoEntry 1 }
        
    zxGponFECTable OBJECT-TYPE
        SYNTAX      SEQUENCE OF ZxGponFECEntry
        MAX-ACCESS  not-accessible
        STATUS      current
        DESCRIPTION
            ""
        ::= { zxGponPrivateGlobal 3 }

    zxGponFECEntry OBJECT-TYPE
        SYNTAX      ZxGponFECEntry
        MAX-ACCESS  not-accessible
        STATUS      current
        DESCRIPTION
            "It is entry in the zxGponFECTable."
        INDEX   { zxGponMgmtPonOltId }
        ::= { zxGponFECTable 1 }
        
    ZxGponFECEntry ::=
        SEQUENCE {
            zxGponFECMode              INTEGER
        }

    zxGponFECMode OBJECT-TYPE
        SYNTAX      INTEGER{
                    none(1),
                    downstream(2),
                    upstream(3),
                    bidirection(4)
                    }
        MAX-ACCESS  read-write
        STATUS      current
        DESCRIPTION
                "Indicates the FEC mode on this olt ."
        ::= { zxGponFECEntry 1 }
        
    zxGponRTDTable OBJECT-TYPE
        SYNTAX      SEQUENCE OF ZxGponRTDEntry
        MAX-ACCESS  not-accessible
        STATUS      current
        DESCRIPTION
            ""
        ::= { zxGponPrivateGlobal 4 }

    zxGponRTDEntry OBJECT-TYPE
        SYNTAX      ZxGponRTDEntry
        MAX-ACCESS  not-accessible
        STATUS      current
        DESCRIPTION
            "It is entry in the zxGponRTDTable."
        INDEX   { zxGponMgmtPonOltId, zxGponMgmtPonOnuId }
        ::= { zxGponRTDTable 1 }
        
    ZxGponRTDEntry ::=
        SEQUENCE {
            zxGponRTDEqd              INTEGER,
            zxGponRTDDistance         INTEGER
        }

    zxGponRTDEqd OBJECT-TYPE
        SYNTAX      INTEGER
        MAX-ACCESS  read-only
        STATUS      current
        DESCRIPTION
                "Equalized delay of onu."
        ::= { zxGponRTDEntry 1 }
        
    zxGponRTDDistance OBJECT-TYPE
        SYNTAX      INTEGER
        MAX-ACCESS  read-only
        STATUS      current
        DESCRIPTION
                "Distance of onu."
        ::= { zxGponRTDEntry 2 }

    zxGponRangeTable OBJECT-TYPE
        SYNTAX      SEQUENCE OF ZxGponRangeEntry
        MAX-ACCESS  not-accessible
        STATUS      current
        DESCRIPTION
            ""
        ::= { zxGponPrivateGlobal 5 }

    zxGponRangeEntry OBJECT-TYPE
        SYNTAX      ZxGponRangeEntry
        MAX-ACCESS  not-accessible
        STATUS      current
        DESCRIPTION
            "It is entry in the zxGponRangeTable."
        INDEX   { zxGponMgmtPonOltId }
        ::= { zxGponRangeTable 1 }
        
    ZxGponRangeEntry ::=
        SEQUENCE {
            zxGponRangeMode              INTEGER,
            zxGponRangeBase              INTEGER,
            zxGponRangeDiff              INTEGER,
            zxGponRangeCapability        INTEGER
        }

    zxGponRangeMode OBJECT-TYPE
        SYNTAX      INTEGER{
                    mode0(1),
                    mode1(2),
                    mode2(3)
                    }
        MAX-ACCESS  read-write
        STATUS      current
        DESCRIPTION
                "Indicates the range mode of this olt .
                mode0(1): 0  - 20 km
                mode1(2): 20 - 40 km
                mode2(3): 40 - 60 km"
        ::= { zxGponRangeEntry 1 }
        
    zxGponRangeBase OBJECT-TYPE
        SYNTAX      INTEGER
        UNITS       "100m"
        MAX-ACCESS  read-write
        STATUS      current
        DESCRIPTION
                "It indicates value of the base distance of the range.
                 The distance of the range is [zxGponRangeBase,zxGponRangeBase + zxGponRangeDiff],
                 The max distance of the range is 60km"
        ::= { zxGponRangeEntry 2 }
    
    zxGponRangeDiff OBJECT-TYPE
        SYNTAX      INTEGER
        UNITS       "100m"
        MAX-ACCESS  read-write
        STATUS      current
        DESCRIPTION
                "It indicates the distance of the range coverage area."
        ::= { zxGponRangeEntry 3 }  
        
    zxGponRangeCapability OBJECT-TYPE
        SYNTAX      INTEGER{
                    fixed(1),
                    step(2)
                    }
        MAX-ACCESS  read-only
        STATUS      current
        DESCRIPTION
                "Indicates the range capability.
                fixed(1): zxGponRangeMode working,only support 0-20,20-40,40-60
                step(2): zxGponRangeBase and zxGponRangeDiff working"
        ::= { zxGponRangeEntry 4 }       
               

--- SCB controled
   
  zxGponGetValidIdxTable OBJECT-TYPE
        SYNTAX      SEQUENCE OF ZxGponGetValidIdxEntry
        MAX-ACCESS  not-accessible
        STATUS      current
        DESCRIPTION
            "This table represents current valid index table."
        ::= { zxGponPrivateGlobal 16 }

    zxGponGetValidIdxEntry OBJECT-TYPE
        SYNTAX      ZxGponGetValidIdxEntry
        MAX-ACCESS  not-accessible
        STATUS      current
        DESCRIPTION
            "It provide a current valid index entry."
        INDEX   { zxGponGetValidIdxTableNameIdx, zxGponMgmtPonOltId, zxGponMgmtPonOnuId, zxGponGemPortIdx }
        ::= { zxGponGetValidIdxTable 1 }

    ZxGponGetValidIdxEntry ::=
        SEQUENCE {
            zxGponGetValidIdxTableNameIdx INTEGER,
            zxGponGetValidIdxvalue        INTEGER
        }

    zxGponGetValidIdxTableNameIdx       OBJECT-TYPE
      SYNTAX      INTEGER
      MAX-ACCESS  not-accessible
      STATUS      current 
      DESCRIPTION 
        "It is a table name ID, specifical number denotes one table.
         Only these tables are valid in which it is only one integer index.
         GPON_TBLID_BWPROFILE             1
         GPON_TBLID_THRESPROFILE          2
         GPON_TBLID_TRAFFICPROFILE        3
         GPON_TBLID_FLOWCLASSPROFILE      4
         GPON_TBLID_CLASSRULEPROFILE      5
         GPON_TBLID_TRAFFICMGMTUNIT       6
         GPON_TBLID_GEMPORT               7
         GPON_TBLID_FLOW                  8
         GPON_TBLID_VOIPMEDIAPROFILE      9
         GPON_TBLID_DIALPLANTABLE         10
         GPON_TBLID_FILTERRULE            11
         GPON_TBLID_TREATRULE             12
         GPON_TBLID_PWPROFILE             13
         GPON_TBLID_SCHPROFILE            14
         GPON_TBLID_IGMPPROFILE           15
         "
      REFERENCE   "N/A"
      ::= { zxGponGetValidIdxEntry 1 }

    zxGponGetValidIdxvalue       OBJECT-TYPE
      SYNTAX      INTEGER
      MAX-ACCESS  read-only
      STATUS      current 
      DESCRIPTION 
        "It is a valid in the table."
      REFERENCE   "N/A"
      ::= { zxGponGetValidIdxEntry 2 }
   
       zxGponSlotOpticalDetectInfoTable OBJECT-TYPE
        SYNTAX      SEQUENCE OF ZxGponSlotOpticalDetectInfoEntry
        MAX-ACCESS  not-accessible
        STATUS      current
        DESCRIPTION
            ""
        ::= { zxGponPrivateGlobal 25}

    zxGponSlotOpticalDetectInfoEntry OBJECT-TYPE
        SYNTAX      ZxGponSlotOpticalDetectInfoEntry
        MAX-ACCESS  not-accessible
        STATUS      current
        DESCRIPTION
            ""
        INDEX   { zxGponMgmtPonSlotId }
        ::= {zxGponSlotOpticalDetectInfoTable 1 }

    ZxGponSlotOpticalDetectInfoEntry ::=
          SEQUENCE {
            zxGponMgmtPonSlotId          INTEGER,
              zxGponSlotOpticalDetect           TruthValue
              }
       
      zxGponMgmtPonSlotId       OBJECT-TYPE
      SYNTAX      INTEGER
      MAX-ACCESS  not-accessible
      STATUS      current 
      DESCRIPTION 
        "slot id(1-6,9-14)"
      REFERENCE   "N/A"
      ::= { zxGponSlotOpticalDetectInfoEntry 1 }
          
    zxGponSlotOpticalDetect       OBJECT-TYPE
      SYNTAX      TruthValue
      MAX-ACCESS  read-write
      STATUS      current 
      DESCRIPTION 
        "enable/disable pon Optical-Always-On detection."
      REFERENCE   "N/A"
      ::= { zxGponSlotOpticalDetectInfoEntry 2 }

  
--zxGponStandardOlt.mi2
    zxGponStandardOlt OBJECT IDENTIFIER ::= { zxGponRootMib 12 }

    zxGponOltStatisticInfoTable OBJECT-TYPE
        SYNTAX      SEQUENCE OF ZxGponOltStatisticInfoEntry
        MAX-ACCESS  not-accessible
        STATUS      current
        DESCRIPTION
            "" 
        REFERENCE
            ""
        ::= { zxGponStandardOlt 2 }

    zxGponOltStatisticInfoEntry OBJECT-TYPE
        SYNTAX      ZxGponOltStatisticInfoEntry
        MAX-ACCESS  not-accessible
        STATUS      current
        DESCRIPTION
            ""
        INDEX   { zxGponMgmtPonOltId }
        ::= { zxGponOltStatisticInfoTable 1 }

    ZxGponOltStatisticInfoEntry ::=
        SEQUENCE {
            zxGponOltStatisticInfoSuperframeCounter Counter64,
            zxGponOltStatisticInfoBIPCounter        Counter64
        }

   zxGponOltStatisticInfoSuperframeCounter OBJECT-TYPE
        SYNTAX      Counter64
        MAX-ACCESS  read-only
        STATUS      current
        DESCRIPTION
            "To provide error tolerance, the OLT must implement a local superframe counter"
        ::= { zxGponOltStatisticInfoEntry 1}

   zxGponOltStatisticInfoBIPCounter OBJECT-TYPE
        SYNTAX      Counter64
        MAX-ACCESS  read-only
        STATUS      current
        DESCRIPTION
            "The received BIP8 is compared with the calculated BIP8 on the received stream. In case 
             of a difference ERR counter is incremented"
        ::= { zxGponOltStatisticInfoEntry 2}

    zxGponFindOnuTimerTable OBJECT-TYPE
        SYNTAX      SEQUENCE OF ZxGponFindOnuTimerEntry
        MAX-ACCESS  not-accessible
        STATUS      current
        DESCRIPTION
            "" 
        REFERENCE
            ""
        ::= { zxGponStandardOlt 7 }

    zxGponFindOnuTimerEntry OBJECT-TYPE
        SYNTAX      ZxGponFindOnuTimerEntry
        MAX-ACCESS  not-accessible
        STATUS      current
        DESCRIPTION
            ""
        INDEX   { zxGponMgmtPonOltId }
        ::= { zxGponFindOnuTimerTable 1 }

    ZxGponFindOnuTimerEntry ::=
        SEQUENCE {
            zxGPonFindOnuTimerNewOnt          INTEGER,
            zxGponFindOnuTimerMissingOnt      INTEGER,
            zxGPonFindOnuTimerOpenWindowFrame INTEGER
        }

   zxGPonFindOnuTimerNewOnt OBJECT-TYPE
        SYNTAX      INTEGER
        MAX-ACCESS  read-write
        STATUS      current
        DESCRIPTION
            ""
        ::= { zxGponFindOnuTimerEntry 1}

   zxGponFindOnuTimerMissingOnt OBJECT-TYPE
        SYNTAX      INTEGER
        MAX-ACCESS  read-write
        STATUS      current
        DESCRIPTION
            ""
        ::= { zxGponFindOnuTimerEntry 2}

   zxGPonFindOnuTimerOpenWindowFrame OBJECT-TYPE
        SYNTAX      INTEGER
        MAX-ACCESS  read-write
        STATUS      current
        DESCRIPTION
            ""
        ::= { zxGponFindOnuTimerEntry 3}

  zxGponOltPmStatisRealtimeInfoTable OBJECT-TYPE
        SYNTAX      SEQUENCE OF ZxGponOltPmStatisRealtimeInfoEntry
        MAX-ACCESS  not-accessible
        STATUS      current
        DESCRIPTION
            "" 
        REFERENCE
            ""
        ::= { zxGponStandardOlt 13 }

    zxGponOltPmStatisRealtimeInfoEntry OBJECT-TYPE
        SYNTAX      ZxGponOltPmStatisRealtimeInfoEntry
        MAX-ACCESS  not-accessible
        STATUS      current
        DESCRIPTION
            ""
        INDEX   { zxGponMgmtPonOltId }
        ::= { zxGponOltPmStatisRealtimeInfoTable 1 }

    ZxGponOltPmStatisRealtimeInfoEntry ::=
        SEQUENCE {
            zxGponOltPmStatisInfoCorrectNonIdleGemFramesUpstream     Unsigned32,
            zxGponOltPmStatisInfoCorrectIdleGemFramesUpstream        Unsigned32,
            zxGponOltPmStatisInfoErroredGemFramesUpstream            Unsigned32,
            zxGponOltPmStatisInfoGemPayloadBytesUpstream             Unsigned32,
            zxGponOltPmStatisInfoCorrectEthernetFramesUpstream       Unsigned32,
            zxGponOltPmStatisInfoErroredEthernetFramesUpstream       Unsigned32,
            zxGponOltPmStatisInfoTotalOmciFramesUpstream             Unsigned32,
            zxGponOltPmStatisInfoERR                                 Unsigned32,
            zxGponOltPmStatisInfoREI                                 Unsigned32,
            zxGponOltPmStatisInfoValidEthernetPacketDownstream       Unsigned32,
            zxGponOltPmStatisInfoCpuPacketDownstream                 Unsigned32,
            zxGponOltPmStatisInfoPloamDownstream                     Unsigned32,
            zxGponOltPmStatisInfoPloamUpstream                       Unsigned32,
            zxGponOltPmStatisInfoInvalidPacketUpstream               Unsigned32,
            zxGponOltPmFecCorrectedBytes                             Unsigned32,
            zxGponOltPmFecCorrectedWords                             Unsigned32,
            zxGponOltPmFecUncorrectedWords                           Unsigned32,
            zxGponOltPmFecTotalRxWords                               Unsigned32,
            zxGponOltPmBipErrBits                                    Unsigned32,
            zxGponOltPmCrcErrPkts                                    Unsigned32,
            zxGponOltPmBipCorrectedBits                              Unsigned32
        }

   zxGponOltPmStatisInfoCorrectNonIdleGemFramesUpstream OBJECT-TYPE
        SYNTAX      Unsigned32
        MAX-ACCESS  read-only
        STATUS      current
        DESCRIPTION
            ""
        ::= { zxGponOltPmStatisRealtimeInfoEntry 1}

   zxGponOltPmStatisInfoCorrectIdleGemFramesUpstream OBJECT-TYPE
        SYNTAX      Unsigned32
        MAX-ACCESS  read-only
        STATUS      current
        DESCRIPTION
            ""
        ::= { zxGponOltPmStatisRealtimeInfoEntry 2}

   zxGponOltPmStatisInfoErroredGemFramesUpstream OBJECT-TYPE
        SYNTAX      Unsigned32
        MAX-ACCESS  read-only
        STATUS      current
        DESCRIPTION
            ""
        ::= { zxGponOltPmStatisRealtimeInfoEntry 3}

   zxGponOltPmStatisInfoGemPayloadBytesUpstream OBJECT-TYPE
        SYNTAX      Unsigned32
        MAX-ACCESS  read-only
        STATUS      current
        DESCRIPTION
            ""
        ::= { zxGponOltPmStatisRealtimeInfoEntry 4}

   zxGponOltPmStatisInfoCorrectEthernetFramesUpstream OBJECT-TYPE
        SYNTAX      Unsigned32
        MAX-ACCESS  read-only
        STATUS      current
        DESCRIPTION
            ""
        ::= { zxGponOltPmStatisRealtimeInfoEntry 5}

   zxGponOltPmStatisInfoErroredEthernetFramesUpstream OBJECT-TYPE
        SYNTAX      Unsigned32
        MAX-ACCESS  read-only
        STATUS      current
        DESCRIPTION
            ""
        ::= { zxGponOltPmStatisRealtimeInfoEntry 6}

   zxGponOltPmStatisInfoTotalOmciFramesUpstream OBJECT-TYPE
        SYNTAX      Unsigned32
        MAX-ACCESS  read-only
        STATUS      current
        DESCRIPTION
            ""
        ::= { zxGponOltPmStatisRealtimeInfoEntry 7}

   zxGponOltPmStatisInfoERR OBJECT-TYPE
        SYNTAX      Unsigned32
        MAX-ACCESS  read-only
        STATUS      current
        DESCRIPTION
            ""
        ::= { zxGponOltPmStatisRealtimeInfoEntry 8}

   zxGponOltPmStatisInfoREI OBJECT-TYPE
        SYNTAX      Unsigned32
        MAX-ACCESS  read-only
        STATUS      current
        DESCRIPTION
            ""
        ::= { zxGponOltPmStatisRealtimeInfoEntry 9}

   zxGponOltPmStatisInfoValidEthernetPacketDownstream OBJECT-TYPE
        SYNTAX      Unsigned32
        MAX-ACCESS  read-only
        STATUS      current
        DESCRIPTION
            ""
        ::= { zxGponOltPmStatisRealtimeInfoEntry 10}

   zxGponOltPmStatisInfoCpuPacketDownstream OBJECT-TYPE
        SYNTAX      Unsigned32
        MAX-ACCESS  read-only
        STATUS      current
        DESCRIPTION
            ""
        ::= { zxGponOltPmStatisRealtimeInfoEntry 11}

   zxGponOltPmStatisInfoPloamDownstream OBJECT-TYPE
        SYNTAX      Unsigned32
        MAX-ACCESS  read-only
        STATUS      current
        DESCRIPTION
            ""
        ::= { zxGponOltPmStatisRealtimeInfoEntry 12}

   zxGponOltPmStatisInfoPloamUpstream OBJECT-TYPE
        SYNTAX      Unsigned32
        MAX-ACCESS  read-only
        STATUS      current
        DESCRIPTION
            ""
        ::= { zxGponOltPmStatisRealtimeInfoEntry 13}

   zxGponOltPmStatisInfoInvalidPacketUpstream OBJECT-TYPE
        SYNTAX      Unsigned32
        MAX-ACCESS  read-only
        STATUS      current
        DESCRIPTION
            ""
        ::= { zxGponOltPmStatisRealtimeInfoEntry 14}
        
   zxGponOltPmFecCorrectedBytes OBJECT-TYPE
        SYNTAX      Unsigned32
        MAX-ACCESS  read-only
        STATUS      current
        DESCRIPTION
            "Errored bytes which have been corrected by FEC on PON port."
        ::= { zxGponOltPmStatisRealtimeInfoEntry 15}
    
   zxGponOltPmFecCorrectedWords  OBJECT-TYPE
        SYNTAX      Unsigned32
        MAX-ACCESS  read-only
        STATUS      current
        DESCRIPTION
            "Errored codewords which have been corrected by FEC on PON port."
        ::= { zxGponOltPmStatisRealtimeInfoEntry 16}
        
    zxGponOltPmFecUncorrectedWords  OBJECT-TYPE
        SYNTAX      Unsigned32
        MAX-ACCESS  read-only
        STATUS      current
        DESCRIPTION
          "Errored codewords which haven't been corrected by FEC on PON port."
        ::= { zxGponOltPmStatisRealtimeInfoEntry 17}

   zxGponOltPmFecTotalRxWords OBJECT-TYPE
        SYNTAX      Unsigned32
        MAX-ACCESS  read-only
        STATUS      current
        DESCRIPTION
            "Received codewords by FEC on PON port."
        ::= { zxGponOltPmStatisRealtimeInfoEntry 18}
        
   zxGponOltPmBipErrBits OBJECT-TYPE
        SYNTAX      Unsigned32
        MAX-ACCESS  read-only
        STATUS      current
        DESCRIPTION
            "Errored bits by BIP on PON port."
        ::= { zxGponOltPmStatisRealtimeInfoEntry 19}   
        
   zxGponOltPmCrcErrPkts OBJECT-TYPE
        SYNTAX      Unsigned32
        MAX-ACCESS  read-only
        STATUS      current
        DESCRIPTION
            "Errored packets by CRC on PON port."
        ::= { zxGponOltPmStatisRealtimeInfoEntry 20}    

   zxGponOltPmBipCorrectedBits OBJECT-TYPE
        SYNTAX      Unsigned32
        MAX-ACCESS  read-only
        STATUS      current
        DESCRIPTION
            "The total count of BIP corrected bits on PON port."
        ::= { zxGponOltPmStatisRealtimeInfoEntry 21}   

    zxGponOltPmStatisHistoryInfoTable OBJECT-TYPE
        SYNTAX      SEQUENCE OF ZxGponOltPmStatisHistoryInfoEntry
        MAX-ACCESS  not-accessible
        STATUS      current
        DESCRIPTION
            "" 
        REFERENCE
            ""
        ::= { zxGponStandardOlt 14 }

    zxGponOltPmStatisHistoryInfoEntry OBJECT-TYPE
        SYNTAX      ZxGponOltPmStatisHistoryInfoEntry
        MAX-ACCESS  not-accessible
        STATUS      current
        DESCRIPTION
            ""
        INDEX   { zxGponMgmtPonOltId }
        ::= { zxGponOltPmStatisHistoryInfoTable 1 }

    ZxGponOltPmStatisHistoryInfoEntry ::=
        SEQUENCE {
            zxGponOltPmStatisHistoryInfoCorrectNonIdleGemFramesUpstream                Unsigned32,
            zxGponOltPmStatisHistoryInfoCorrectIdleGemFramesUpstream         Unsigned32,
            zxGponOltPmStatisHistoryInfoErroredGemFramesUpstream       Unsigned32,
            zxGponOltPmStatisHistoryInfoGemPayloadBytesUpstream             Unsigned32,
            zxGponOltPmStatisHistoryInfoCorrectEthernetFramesUpstream          Unsigned32,
            zxGponOltPmStatisHistoryInfoErroredEthernetFramesUpstream                Unsigned32,
            zxGponOltPmStatisHistoryInfoTotalOmciFramesUpstream             Unsigned32,
            zxGponOltPmStatisHistoryInfoERR             Unsigned32,
            zxGponOltPmStatisHistoryInfoREI               Unsigned32,
            zxGponOltPmStatisHistoryInfoValidEthernetPacketDownstream               Unsigned32,
            zxGponOltPmStatisHistoryInfoCpuPacketDownstream            Unsigned32,
            zxGponOltPmStatisHistoryInfoPloamDownstream            Unsigned32,
            zxGponOltPmStatisHistoryInfoPloamUpstream                    Unsigned32,
            zxGponOltPmStatisHistoryInfoInvalidPacketUpstream                 Unsigned32
        }

   zxGponOltPmStatisHistoryInfoCorrectNonIdleGemFramesUpstream OBJECT-TYPE
        SYNTAX      Unsigned32
        MAX-ACCESS  read-only
        STATUS      current
        DESCRIPTION
            ""
        ::= { zxGponOltPmStatisHistoryInfoEntry 1}

   zxGponOltPmStatisHistoryInfoCorrectIdleGemFramesUpstream OBJECT-TYPE
        SYNTAX      Unsigned32
        MAX-ACCESS  read-only
        STATUS      current
        DESCRIPTION
            ""
        ::= { zxGponOltPmStatisHistoryInfoEntry 2}

   zxGponOltPmStatisHistoryInfoErroredGemFramesUpstream OBJECT-TYPE
        SYNTAX      Unsigned32
        MAX-ACCESS  read-only
        STATUS      current
        DESCRIPTION
            ""
        ::= { zxGponOltPmStatisHistoryInfoEntry 3}

   zxGponOltPmStatisHistoryInfoGemPayloadBytesUpstream OBJECT-TYPE
        SYNTAX      Unsigned32
        MAX-ACCESS  read-only
        STATUS      current
        DESCRIPTION
            ""
        ::= { zxGponOltPmStatisHistoryInfoEntry 4}

   zxGponOltPmStatisHistoryInfoCorrectEthernetFramesUpstream OBJECT-TYPE
        SYNTAX      Unsigned32
        MAX-ACCESS  read-only
        STATUS      current
        DESCRIPTION
            ""
        ::= { zxGponOltPmStatisHistoryInfoEntry 5}

   zxGponOltPmStatisHistoryInfoErroredEthernetFramesUpstream OBJECT-TYPE
        SYNTAX      Unsigned32
        MAX-ACCESS  read-only
        STATUS      current
        DESCRIPTION
            ""
        ::= { zxGponOltPmStatisHistoryInfoEntry 6}

   zxGponOltPmStatisHistoryInfoTotalOmciFramesUpstream OBJECT-TYPE
        SYNTAX      Unsigned32
        MAX-ACCESS  read-only
        STATUS      current
        DESCRIPTION
            ""
        ::= { zxGponOltPmStatisHistoryInfoEntry 7}

   zxGponOltPmStatisHistoryInfoERR OBJECT-TYPE
        SYNTAX      Unsigned32
        MAX-ACCESS  read-only
        STATUS      current
        DESCRIPTION
            ""
        ::= { zxGponOltPmStatisHistoryInfoEntry 8}

   zxGponOltPmStatisHistoryInfoREI OBJECT-TYPE
        SYNTAX      Unsigned32
        MAX-ACCESS  read-only
        STATUS      current
        DESCRIPTION
            ""
        ::= { zxGponOltPmStatisHistoryInfoEntry 9}

   zxGponOltPmStatisHistoryInfoValidEthernetPacketDownstream OBJECT-TYPE
        SYNTAX      Unsigned32
        MAX-ACCESS  read-only
        STATUS      current
        DESCRIPTION
            ""
        ::= { zxGponOltPmStatisHistoryInfoEntry 10}

   zxGponOltPmStatisHistoryInfoCpuPacketDownstream OBJECT-TYPE
        SYNTAX      Unsigned32
        MAX-ACCESS  read-only
        STATUS      current
        DESCRIPTION
            ""
        ::= { zxGponOltPmStatisHistoryInfoEntry 11}

   zxGponOltPmStatisHistoryInfoPloamDownstream OBJECT-TYPE
        SYNTAX      Unsigned32
        MAX-ACCESS  read-only
        STATUS      current
        DESCRIPTION
            ""
        ::= { zxGponOltPmStatisHistoryInfoEntry 12}

   zxGponOltPmStatisHistoryInfoPloamUpstream OBJECT-TYPE
        SYNTAX      Unsigned32
        MAX-ACCESS  read-only
        STATUS      current
        DESCRIPTION
            ""
        ::= { zxGponOltPmStatisHistoryInfoEntry 13}

   zxGponOltPmStatisHistoryInfoInvalidPacketUpstream OBJECT-TYPE
        SYNTAX      Unsigned32
        MAX-ACCESS  read-only
        STATUS      current
        DESCRIPTION
            ""
        ::= { zxGponOltPmStatisHistoryInfoEntry 14}

--zxGponPrivateOlt.mi2
    VlanId ::= TEXTUAL-CONVENTION
        STATUS      current
        DESCRIPTION
            "A 12-bit VLAN ID used in the VLAN Tag header."
        SYNTAX      INTEGER (1..4094)

    zxGponPrivateOlt OBJECT IDENTIFIER ::= { zxGponRootMib 13 }

    zxGponOltPonInfoTable OBJECT-TYPE
        SYNTAX      SEQUENCE OF ZxGponOltPonInfoEntry
        MAX-ACCESS  not-accessible
        STATUS      current
        DESCRIPTION
            "" 
        REFERENCE
            "G.984.3"
        ::= { zxGponPrivateOlt 1 }

    zxGponOltPonInfoEntry OBJECT-TYPE
        SYNTAX      ZxGponOltPonInfoEntry
        MAX-ACCESS  not-accessible
        STATUS      current
        DESCRIPTION
            ""
        INDEX   { zxGponMgmtPonOltId }
        ::= { zxGponOltPonInfoTable 1 }

    ZxGponOltPonInfoEntry ::=
        SEQUENCE {
            zxGponOltPonName             OCTET STRING,
            zxGponOltPonDescription      OCTET STRING,
            zxGPonOltPonOntDefaultState  INTEGER,
            zxGPonOltPonOntDefaultPwMode INTEGER,
            zxGPonOltPonOntDefaultPw     OCTET STRING,
            zxGPonOltPonOntAuthMode      INTEGER,
            zxGPonOltPonOntSnAuthMode    INTEGER,
            zxGPonOltPonOntSnMask        OCTET STRING,
            zxGponOltPonOmccPortBase     INTEGER,
            zxGPonOltPonAdminState       INTEGER,
            zxGPonOltPonOperState        INTEGER,
            zxGponOltPonSupportMaxOnts   INTEGER,
            zxGponOltPonRealLegalOnts    INTEGER,
            zxGponOltPonRealIllegalOnts  INTEGER,
            zxGponOltPonSupportMaxTConts  INTEGER,
            zxGponOltPonRealUsedTConts   INTEGER,
            zxGponOltPonAgingTime           INTEGER,
            zxGponOltPonUnauthOnuAgingTime  INTEGER
        }

   zxGponOltPonName OBJECT-TYPE
        SYNTAX      OCTET STRING(SIZE(128))
        MAX-ACCESS  read-write
        STATUS      current
        DESCRIPTION
            ""
        ::= { zxGponOltPonInfoEntry 1}

   zxGponOltPonDescription OBJECT-TYPE
        SYNTAX      OCTET STRING(SIZE(127))
        MAX-ACCESS  read-write
        STATUS      current
        DESCRIPTION
            "The definition size of description does not include the termination."
        ::= { zxGponOltPonInfoEntry 2}

   zxGPonOltPonOntDefaultState OBJECT-TYPE
        SYNTAX      INTEGER{
                    deactive(1),
                    omciready(2)
                    }
        MAX-ACCESS  read-write
        STATUS      current
        DESCRIPTION
            ""
        ::= { zxGponOltPonInfoEntry 3}

   zxGPonOltPonOntDefaultPwMode OBJECT-TYPE
        SYNTAX      INTEGER{
                    nonePw(1),
                    force(2)
                    }
        MAX-ACCESS  read-write
        STATUS      current
        DESCRIPTION
            ""
        ::= { zxGponOltPonInfoEntry 4}

   zxGPonOltPonOntDefaultPw OBJECT-TYPE
        SYNTAX      OCTET STRING(SIZE(10))
        MAX-ACCESS  read-write
        STATUS      current
        DESCRIPTION
            ""
        ::= { zxGponOltPonInfoEntry 5}

   zxGPonOltPonOntAuthMode OBJECT-TYPE
        SYNTAX      INTEGER{
                    sn(1),
                    regid(2)
                    }
        MAX-ACCESS  read-write
        STATUS      current
        DESCRIPTION
            ""
        ::= { zxGponOltPonInfoEntry 6}

   zxGPonOltPonOntSnAuthMode OBJECT-TYPE
        SYNTAX      INTEGER{
                    learn(1),
                    provision(2)
                    }
        MAX-ACCESS  read-write
        STATUS      current
        DESCRIPTION
            ""
        ::= { zxGponOltPonInfoEntry 7}

   zxGPonOltPonOntSnMask OBJECT-TYPE
        SYNTAX      OCTET STRING (SIZE (8))
        MAX-ACCESS  read-write
        STATUS      current
        DESCRIPTION
            ""
        ::= { zxGponOltPonInfoEntry 8}

   zxGponOltPonOmccPortBase OBJECT-TYPE
        SYNTAX      INTEGER
        MAX-ACCESS  read-write
        STATUS      current
        DESCRIPTION
            ""
        ::= { zxGponOltPonInfoEntry 9}

   zxGPonOltPonAdminState OBJECT-TYPE
        SYNTAX      INTEGER{
                    enable(1),
                    disable(2)
                    }
        MAX-ACCESS  read-write
        STATUS      current
        DESCRIPTION
            ""
        DEFVAL { disable }
        ::= { zxGponOltPonInfoEntry 10}
    
   zxGPonOltPonOperState OBJECT-TYPE
        SYNTAX      INTEGER{
                    enable(1),
                    disable(2)
                    }
        MAX-ACCESS  read-only
        STATUS      current
        DESCRIPTION
            ""
        DEFVAL { disable }
        ::= { zxGponOltPonInfoEntry 11}

   zxGponOltPonSupportMaxOnts OBJECT-TYPE
        SYNTAX      INTEGER
        MAX-ACCESS  read-only
        STATUS      current
        DESCRIPTION
            ""
        ::= { zxGponOltPonInfoEntry 12}

   zxGponOltPonRealLegalOnts OBJECT-TYPE
        SYNTAX      INTEGER
        MAX-ACCESS  read-only
        STATUS      current
        DESCRIPTION
            ""
        ::= { zxGponOltPonInfoEntry 13}

   zxGponOltPonRealIllegalOnts OBJECT-TYPE
        SYNTAX      INTEGER
        MAX-ACCESS  read-only
        STATUS      current
        DESCRIPTION
            ""
        ::= { zxGponOltPonInfoEntry 14}
    
   zxGponOltPonSupportMaxTConts OBJECT-TYPE
        SYNTAX      INTEGER
        MAX-ACCESS  read-only
        STATUS      current
        DESCRIPTION
            ""
        ::= { zxGponOltPonInfoEntry 15}

   zxGponOltPonRealUsedTConts OBJECT-TYPE
        SYNTAX      INTEGER
        MAX-ACCESS  read-only
        STATUS      current
        DESCRIPTION
            ""
        ::= { zxGponOltPonInfoEntry 16}

   zxGponOltPonAgingTime OBJECT-TYPE
        SYNTAX      INTEGER
        MAX-ACCESS  read-write
        STATUS      current
        DESCRIPTION
            ""
        ::= { zxGponOltPonInfoEntry 17}

    zxGponOltPonUnauthOnuAgingTime OBJECT-TYPE
        SYNTAX      INTEGER(2..3600)
        UNITS        "seconds"
        MAX-ACCESS  read-write
        STATUS      current
        DESCRIPTION
            "The aging time of unauthorized ONU. 
             When the online time of unauthorized ONU for more than
              'zxGponOltPonUnauthOnuAgingTime', the OLT will delete
              the unauthorized ONU record from the unauthorized ONU table."
        DEFVAL {300}
        ::= { zxGponOltPonInfoEntry 21}        

    zxGponOltMgmtOperTable OBJECT-TYPE
        SYNTAX      SEQUENCE OF ZxGponOltMgmtOperEntry
        MAX-ACCESS  not-accessible
        STATUS      current
        DESCRIPTION
            "" 
        REFERENCE
            "G.984.3"
        ::= { zxGponPrivateOlt 2 }

    zxGponOltMgmtOperEntry OBJECT-TYPE
        SYNTAX      ZxGponOltMgmtOperEntry
        MAX-ACCESS  not-accessible
        STATUS      current
        DESCRIPTION
            ""
        INDEX   { zxGponMgmtPonOltId }
        ::= { zxGponOltMgmtOperTable 1 }

    ZxGponOltMgmtOperEntry ::=
        SEQUENCE {
            zxGponOltReset                  TruthValue,
            zxGponOltOff                    TruthValue,
            zxGponOltOpticalDetectOnce      TruthValue
        }

   zxGponOltReset OBJECT-TYPE
        SYNTAX      TruthValue
        MAX-ACCESS  read-write
        STATUS      current
        DESCRIPTION
            ""
        ::= { zxGponOltMgmtOperEntry 1}

   zxGponOltOff OBJECT-TYPE
        SYNTAX      TruthValue
        MAX-ACCESS  read-write
        STATUS      current
        DESCRIPTION
            ""
        ::= { zxGponOltMgmtOperEntry 2}
   
   zxGponOltOpticalDetectOnce OBJECT-TYPE
        SYNTAX      TruthValue
        MAX-ACCESS  read-write
        STATUS      current
        DESCRIPTION
            "excute olt Optical-Always-ON detect once."
        ::= { zxGponOltMgmtOperEntry 3}



    zxGponUnCfgSnOntInfoTable OBJECT-TYPE
        SYNTAX      SEQUENCE OF ZxGponUnCfgSnOntInfoEntry
        MAX-ACCESS  not-accessible
        STATUS      current
        DESCRIPTION
            "" 
        REFERENCE
            "G.984.3"
        ::= { zxGponPrivateOlt 3 }

    zxGponUnCfgSnOntInfoEntry OBJECT-TYPE
        SYNTAX      ZxGponUnCfgSnOntInfoEntry
        MAX-ACCESS  not-accessible
        STATUS      current
        DESCRIPTION
            ""
        INDEX   { zxGponMgmtPonOltId, zxGponUnCfgSnIdx }
        ::= { zxGponUnCfgSnOntInfoTable 1 }

    ZxGponUnCfgSnOntInfoEntry ::=
        SEQUENCE {
            zxGponUnCfgSnIdx                      INTEGER,
            zxGponUnCfgSnOntSN                    OntSerialNumber,
            zxGponUnCfgSnOntRID                   OCTET STRING,
            zxGponUnCfgSnOntRtd                   INTEGER,
            zxGponUnCfgSnOntPsw                   OCTET STRING,
            zxGponUnCfgSnOntState                 INTEGER,
            zxGponUnCfgSnOntTime                  DateAndTime,
            zxGponUnCfgOntLoid                    DisplayString,
            zxGponUnCfgOntLoidPassword            DisplayString,
            zxGponUnCfgOntType                    DisplayString,
            zxGponUnCfgOntSoftwareVersion         DisplayString
        }

   zxGponUnCfgSnIdx OBJECT-TYPE
        SYNTAX      INTEGER
        MAX-ACCESS  not-accessible
        STATUS      current
        DESCRIPTION
            ""
        ::= { zxGponUnCfgSnOntInfoEntry 1}
    
   zxGponUnCfgSnOntSN OBJECT-TYPE
        SYNTAX      OntSerialNumber(SIZE (8))
        MAX-ACCESS  read-only
        STATUS      current
        DESCRIPTION
            ""
        ::= { zxGponUnCfgSnOntInfoEntry 2}
    
   zxGponUnCfgSnOntRID OBJECT-TYPE
        SYNTAX      OCTET STRING(SIZE(4))
        MAX-ACCESS  read-only
        STATUS      current
        DESCRIPTION
            "The register ID of the unconfigured ONT."
        ::= { zxGponUnCfgSnOntInfoEntry 3}

   zxGponUnCfgSnOntRtd OBJECT-TYPE
        SYNTAX      INTEGER
        MAX-ACCESS  read-only
        STATUS      current
        DESCRIPTION
            "The RTD after ranging."
        ::= { zxGponUnCfgSnOntInfoEntry 4}

   zxGponUnCfgSnOntPsw OBJECT-TYPE
        SYNTAX      OCTET STRING(SIZE(10))
        MAX-ACCESS  read-only
        STATUS      current
        DESCRIPTION
            "The password reported by the ONT."
        ::= { zxGponUnCfgSnOntInfoEntry 5}
        
   zxGponUnCfgSnOntState OBJECT-TYPE
        SYNTAX      INTEGER{
                    o1-initial(1),
                    o2-standby(2),
                    o3-powersetup(3),
                    o4-serialnumber(4),
                    o5-ranging(5),
                    o6-operation(6),
                    o7-popup(7)
                    }
        MAX-ACCESS  read-only
        STATUS      current
        DESCRIPTION
            ""
        ::= { zxGponUnCfgSnOntInfoEntry 6}

   zxGponUnCfgSnOntTime OBJECT-TYPE
        SYNTAX      DateAndTime(SIZE(8))
        MAX-ACCESS  read-only
        STATUS      current
        DESCRIPTION
            ""
        ::= { zxGponUnCfgSnOntInfoEntry 7}

   zxGponUnCfgOntLoid OBJECT-TYPE
        SYNTAX      DisplayString(SIZE(0 .. 24))
        MAX-ACCESS  read-only
        STATUS      current
        DESCRIPTION
            "This attribute identifies the LOID of the ONT."
        ::= { zxGponUnCfgSnOntInfoEntry 8}

   zxGponUnCfgOntLoidPassword OBJECT-TYPE
        SYNTAX      DisplayString(SIZE(0 .. 12))
        MAX-ACCESS  read-only
        STATUS      current
        DESCRIPTION
            "This attribute identifies the LOID password of the ONT."
        ::= { zxGponUnCfgSnOntInfoEntry 9}

   zxGponUnCfgOntType OBJECT-TYPE
        SYNTAX      DisplayString(SIZE(0 .. 14))
        MAX-ACCESS  read-only
        STATUS      current
        DESCRIPTION
            "This attribute identifies the type of the ONT."
        ::= { zxGponUnCfgSnOntInfoEntry 10}

   zxGponUnCfgOntSoftwareVersion OBJECT-TYPE
        SYNTAX      DisplayString(SIZE(0 .. 14))
        MAX-ACCESS  read-only
        STATUS      current
        DESCRIPTION
            "This attribute identifies the version of the ONT."
        ::= { zxGponUnCfgSnOntInfoEntry 11}

   zxGponOltScbPortTable OBJECT-TYPE
        SYNTAX      SEQUENCE OF ZxGponOltScbPortEntry
        MAX-ACCESS  not-accessible
        STATUS      current
        DESCRIPTION
            "Configure SCB PORTID table." 
        ::= { zxGponPrivateOlt 18 }

    zxGponOltScbPortEntry OBJECT-TYPE
        SYNTAX      ZxGponOltScbPortEntry
        MAX-ACCESS  not-accessible
        STATUS      current
        DESCRIPTION
            ""
        INDEX   { zxGponMgmtPonOltId }
        ::= { zxGponOltScbPortTable 1 }

    ZxGponOltScbPortEntry ::=
        SEQUENCE {
            zxGponScbPort   INTEGER
          }

   zxGponScbPort OBJECT-TYPE
        SYNTAX      INTEGER(65..4095)
        MAX-ACCESS  read-write
        STATUS      current
        DESCRIPTION
            ""
        ::= { zxGponOltScbPortEntry 1} 

   
   zxGponOltEthSwitchTable OBJECT-TYPE
        SYNTAX      SEQUENCE OF ZxGponOltEthSwitchEntry
        MAX-ACCESS  not-accessible
        STATUS      current
        DESCRIPTION
            "ETH SWITCH PROTECT STATE table." 
        ::= { zxGponPrivateOlt 15 }

    zxGponOltEthSwitchEntry OBJECT-TYPE
        SYNTAX      ZxGponOltEthSwitchEntry
        MAX-ACCESS  not-accessible
        STATUS      current
        DESCRIPTION
            ""
        INDEX   { zxGponMgmtPonOltId }
        ::= { zxGponOltEthSwitchTable 1 }

    ZxGponOltEthSwitchEntry ::=
        SEQUENCE {
            zxGponEthSwitchProtectState   INTEGER
          }

   zxGponEthSwitchProtectState OBJECT-TYPE
        SYNTAX      INTEGER(0..1)
        MAX-ACCESS  read-write
        STATUS      current
        DESCRIPTION
            "0:DISABLE 1:ENABLE"
        ::= { zxGponOltEthSwitchEntry 1}
   
--zxGponOntEquipMgmt.mi2
    zxGponOntEquipMgmt OBJECT IDENTIFIER ::= { zxGponRootMib 21 }



    zxGponOntAlarmTable OBJECT-TYPE
        SYNTAX      SEQUENCE OF ZxGponOntAlarmEntry
        MAX-ACCESS  not-accessible
        STATUS      current
        DESCRIPTION
            "This alarm is used to notify the managed system when a
             failure has been detected or cleared."
        REFERENCE
            "G.984.4 Section 9.1.1"
        ::= { zxGponOntEquipMgmt 2 }

    zxGponOntAlarmEntry OBJECT-TYPE
        SYNTAX      ZxGponOntAlarmEntry
        MAX-ACCESS  not-accessible
        STATUS      current
        DESCRIPTION
            "An entry in the ONT equipment alarm information table."
        INDEX   { zxGponMgmtPonOltId, zxGponMgmtPonOnuId }
        ::= { zxGponOntAlarmTable 1 }

    ZxGponOntAlarmEntry ::=
        SEQUENCE {
            zxGponOntEquipmentAlarm              TruthValue,
            zxGponOntEquipmentAlarmMask          TruthValue,
            zxGponOntPoweringAlarm               TruthValue,
            zxGponOntPoweringAlarmMask           TruthValue,
            zxGponOntBatteryMissing              TruthValue,
            zxGponOntBatteryMissingMask          TruthValue,
            zxGponOntBatteryFailure              TruthValue,
            zxGponOntBatteryFailureMask          TruthValue,
            zxGponOntBatteryLow                  TruthValue,
            zxGponOntBatteryLowMask              TruthValue,
            zxGponOntPhysicalIntrusionAlarm      TruthValue,
            zxGponOntPhysicalIntrusionAlarmMask  TruthValue,
            zxGponOntONTSelfTestFailure          TruthValue,
            zxGponOntONTSelfTestFailureMask      TruthValue
        }

    zxGponOntEquipmentAlarm OBJECT-TYPE
        SYNTAX      TruthValue
        MAX-ACCESS  read-only
        STATUS      current
        DESCRIPTION
            "It is used to Indicate a functional failure on an internal interface.
             When this is true(1) the failure exists; When false(2), the failure is
             not exist."
        REFERENCE
            "G.984.4 Section 9.1.1"
        ::= { zxGponOntAlarmEntry 1}

    zxGponOntEquipmentAlarmMask OBJECT-TYPE
        SYNTAX      TruthValue
        MAX-ACCESS  read-write
        STATUS      current
        DESCRIPTION
            "Indicates whether the occurence of zxGponOntEquipmentAlarm alarm
             should result in NE generated by the agent layer. When this is false(2) 
             it should be generated; When true(1), not generated."
        REFERENCE
            "G.984.4 Section 9.1.1"
        DEFVAL  { false }
        ::= { zxGponOntAlarmEntry 2}

    zxGponOntPoweringAlarm OBJECT-TYPE
        SYNTAX      TruthValue
        MAX-ACCESS  read-only
        STATUS      current
        DESCRIPTION
            "It is used to Indicate Loss of external power.
             When this is true(1) the failure exists; When false(2), the failure is
             not exist."
        REFERENCE
            "G.984.4 Section 9.1.1"
        ::= { zxGponOntAlarmEntry 3}

    zxGponOntPoweringAlarmMask OBJECT-TYPE
        SYNTAX      TruthValue
        MAX-ACCESS  read-write
        STATUS      current
        DESCRIPTION
            "Indicates whether the occurence of zxGponOntPoweringAlarm alarm
             should result in NE generated by the agent layer. When this is false(2) 
             it should be generated; When true(1), not generated."
        REFERENCE
            "G.984.4 Section 9.1.1"
        DEFVAL  { false }
        ::= { zxGponOntAlarmEntry 4}

    zxGponOntBatteryMissing OBJECT-TYPE
        SYNTAX      TruthValue
        MAX-ACCESS  read-only
        STATUS      current
        DESCRIPTION
            "It is used to Indicate Battery is provisioned but missing.
             When this is true(1) the failure exists; When false(2), the failure is
             not exist."
        REFERENCE
            "G.984.4 Section 9.1.1"
        ::= { zxGponOntAlarmEntry 5}

    zxGponOntBatteryMissingMask OBJECT-TYPE
        SYNTAX      TruthValue
        MAX-ACCESS  read-write
        STATUS      current
        DESCRIPTION
            "Indicates whether the occurence of zxGponOntBatteryMissing alarm
             should result in NE generated by the agent layer. When this is false(2) 
             it should be generated; When true(1), not generated."
        REFERENCE
            "G.984.4 Section 9.1.1"
        DEFVAL  { false }
        ::= { zxGponOntAlarmEntry 6}

    zxGponOntBatteryFailure OBJECT-TYPE
        SYNTAX      TruthValue
        MAX-ACCESS  read-only
        STATUS      current
        DESCRIPTION
            "It is used to Indicate Battery is provisioned and present but cannot recharge.
             When this is true(1) the failure exists; When false(2), the failure is
             not exist."
        REFERENCE
            "G.984.4 Section 9.1.1"
        ::= { zxGponOntAlarmEntry 7}

    zxGponOntBatteryFailureMask OBJECT-TYPE
        SYNTAX      TruthValue
        MAX-ACCESS  read-write
        STATUS      current
        DESCRIPTION
            "Indicates whether the occurence of zxGponOntBatteryFailure alarm
             should result in NE generated by the agent layer. When this is false(2) 
             it should be generated; When true(1), not generated."
        REFERENCE
            "G.984.4 Section 9.1.1"
        DEFVAL  { false }
        ::= { zxGponOntAlarmEntry 8}

    zxGponOntBatteryLow OBJECT-TYPE
        SYNTAX      TruthValue
        MAX-ACCESS  read-only
        STATUS      current
        DESCRIPTION
            "It is used to Indicate battery is provisioned and present but its voltage is too low.
             When this is true(1) the failure exists; When false(2), the failure is
             not exist."
        REFERENCE
            "G.984.4 Section 9.1.1"
        ::= { zxGponOntAlarmEntry 9}

    zxGponOntBatteryLowMask OBJECT-TYPE
        SYNTAX      TruthValue
        MAX-ACCESS  read-write
        STATUS      current
        DESCRIPTION
            "Indicates whether the occurence of zxGponOntBatteryLow alarm
             should result in NE generated by the agent layer. When this is false(2) 
             it should be generated; When true(1), not generated."
        REFERENCE
            "G.984.4 Section 9.1.1"
        DEFVAL  { false }
        ::= { zxGponOntAlarmEntry 10}

    zxGponOntPhysicalIntrusionAlarm OBJECT-TYPE
        SYNTAX      TruthValue
        MAX-ACCESS  read-only
        STATUS      current
        DESCRIPTION
            "It is used to Indicate Applies if the ONT is supported with detection such as door or box open.
             When this is true(1) the failure exists; When false(2), the failure is
             not exist."
        REFERENCE
            "G.984.4 Section 9.1.1"
        ::= { zxGponOntAlarmEntry 11}

    zxGponOntPhysicalIntrusionAlarmMask OBJECT-TYPE
        SYNTAX      TruthValue
        MAX-ACCESS  read-write
        STATUS      current
        DESCRIPTION
            "Indicates whether the occurence of zxGponOntPhysicalIntrusionAlarm alarm
             should result in NE generated by the agent layer. When this is false(2) 
             it should be generated; When true(1), not generated."
        REFERENCE
            "G.984.4 Section 9.1.1"
        DEFVAL  { false }
        ::= { zxGponOntAlarmEntry 12}

    zxGponOntONTSelfTestFailure OBJECT-TYPE
        SYNTAX      TruthValue
        MAX-ACCESS  read-only
        STATUS      current
        DESCRIPTION
            "It is used to Indicate ONT has failed autonomous self test.
             When this is true(1) the failure exists; When false(2), the failure is
             not exist."
        REFERENCE
            "G.984.4 Section 9.1.1"
        ::= { zxGponOntAlarmEntry 13}

    zxGponOntONTSelfTestFailureMask OBJECT-TYPE
        SYNTAX      TruthValue
        MAX-ACCESS  read-write
        STATUS      current
        DESCRIPTION
            "Indicates whether the occurence of zxGponOntONTSelfTestFailure alarm
             should result in NE generated by the agent layer. When this is false(2) 
             it should be generated; When true(1), not generated."
        REFERENCE
            "G.984.4 Section 9.1.1"
        DEFVAL  { false }
        ::= { zxGponOntAlarmEntry 14}

    zxGponOntActionsTable OBJECT-TYPE
        SYNTAX      SEQUENCE OF ZxGponOntActionsEntry
        MAX-ACCESS  not-accessible
        STATUS      current
        DESCRIPTION
            "Acts the ONT table."
        REFERENCE
            "G.984.4 Section 9.1.1"
        ::= { zxGponOntEquipMgmt 3 }

    zxGponOntActionsEntry OBJECT-TYPE
        SYNTAX      ZxGponOntActionsEntry
        MAX-ACCESS  not-accessible
        STATUS      current
        DESCRIPTION
            "An entry in the ONT equipment Actions table."
        INDEX   { zxGponMgmtPonOltId, zxGponMgmtPonOnuId }
        ::= { zxGponOntActionsTable 1 }

    ZxGponOntActionsEntry ::=
        SEQUENCE {
            zxGponOntReboot     INTEGER,
            zxGponOntTest       INTEGER,
            zxGponOntSyncTime   INTEGER,
            zxGponOntMibReset   INTEGER,
            zxGponOntTestResult INTEGER
        }

    zxGponOntReboot OBJECT-TYPE
        SYNTAX      INTEGER{
                    reboot(1)
                    }
        MAX-ACCESS  read-write
        STATUS      current
        DESCRIPTION
            "It is used to Reboot the ONT."
        REFERENCE
            "G.984.4 Section 9.1.1"
        ::= { zxGponOntActionsEntry 1}

    zxGponOntTest OBJECT-TYPE
        SYNTAX      INTEGER{
                    test(1)
                    }
        MAX-ACCESS  read-write
        STATUS      current
        DESCRIPTION
            "It is used to initiate an ONT self test. Test outcome is 'Pass' or 'Fail'."
        REFERENCE
            "G.984.4 Section 9.1.1"
        ::= { zxGponOntActionsEntry 2}

    zxGponOntSyncTime OBJECT-TYPE
        SYNTAX      INTEGER{
                    synctime(1)
                    }
        MAX-ACCESS  read-write
        STATUS      current
        DESCRIPTION
            "It is used to synchronize the start time of all Monitoring managed entities
             of the ONT with the reference time of the OLT and to reset the registers of 
             the Monitoring managed entities. The effect of this action is that all counters 
             of all Monitoring managed entities are set to 0x00 and restart counting. 
             Also, the value of the Interval End Time attribute of the Monitoring managed 
             entities is set to 0x00 and restarts counting."
        REFERENCE
            "G.984.4 Section 9.1.1"
        ::= { zxGponOntActionsEntry 3}

    zxGponOntMibReset OBJECT-TYPE
        SYNTAX      INTEGER{
                    mibRest(1)
                    }
        MAX-ACCESS  read-write
        STATUS      current
        DESCRIPTION
            "Reset the MIB data sync attributes to 0x00 and reset the MIB of the ONT to its default
             state. This default MIB consists of one instance of the ONT(ONTB)-PON managed entity, one 
             instance of the ONT Data managed entity, two instances of the Software Image managed 
             entity, zero or more instances of the Subscriber Line Cardholder managed entity, zero 
             or more instances of the PON IF Line Cardholder, and zero or more instances of the 
             Priority QueueG-PON(B-PON) managed entity (for the priority queues that reside in the ONT)."
        REFERENCE
            "G.983.2 Section 7.1.2"
        ::= { zxGponOntActionsEntry 4}
        
    zxGponOntTestResult OBJECT-TYPE
        SYNTAX      INTEGER
        MAX-ACCESS  read-only
        STATUS      current
        DESCRIPTION
            "Test outcome is 'Pass' or 'Fail'."
        REFERENCE
            "G.984.4 Section 9.1.1"
        ::= { zxGponOntActionsEntry 5}
--zxGponProfileMgmt.mi2
    zxGponProfileMgmt OBJECT IDENTIFIER ::= { zxGponRootMib 26 }
    zxAnGponPerfAlarmProfile OBJECT IDENTIFIER ::= { zxGponProfileMgmt 4}

    zxGponBandwidthProfileTable OBJECT-TYPE
        SYNTAX      SEQUENCE OF ZxGponBandwidthProfileEntry
        MAX-ACCESS  not-accessible
        STATUS      current
        DESCRIPTION
            "Bandwidth allocation for one T-CONT in some ONT.
             these bandwidths as following:
             fixed bandwidth        ab. FBW
             assured bandwidth      ab. ABW
             non-assured bandwidth  ab. NABW
             best effort bandwidth  ab. BEBW
             additional bandwidth   ab. AddBW
             guaranteed bandwidth   ab. GBW
             maximum bandwidth      ab. MaxBW
             minimum bandwidth      ab. MinBW
             AddBW = NABW + BEBW
             GBW   = FBW  + ABW
             MaxBW = GBW  + AddBW
             MinBW = FBW?
             NABW, BEBW, FBW and ABWare able to participate in DBA
             "
        ::= { zxGponProfileMgmt 1 }

    zxGponBandwidthProfileEntry OBJECT-TYPE
        SYNTAX      ZxGponBandwidthProfileEntry
        MAX-ACCESS  not-accessible
        STATUS      current
        DESCRIPTION
            "An entry in the Bandwidth profile table."
        INDEX   { zxGponBWProfileIndex }
        ::= { zxGponBandwidthProfileTable 1 }

    ZxGponBandwidthProfileEntry ::=
        SEQUENCE {
            zxGponBWProfileIndex       INTEGER,
            zxGponBWProfileName        ZxGponRecordName,
            zxGponBWProfileFixed       INTEGER,
            zxGponBWProfileAssured     INTEGER,
            zxGponBWProfileMaximum     INTEGER,
            zxGponBWProfileType        INTEGER,
            zxGponBWProfileRefCnt      INTEGER,
            zxGponBWProfileEntryStatus RowStatus
        }

    zxGponBWProfileIndex OBJECT-TYPE
        SYNTAX      INTEGER
        MAX-ACCESS  not-accessible
        STATUS      current
        DESCRIPTION
            "An arbitrary(unique) integer for identifiying an entry
             in the line card, from 1 to M, M is equal to 512."
        ::= { zxGponBandwidthProfileEntry 1}

    zxGponBWProfileName OBJECT-TYPE
        SYNTAX      ZxGponRecordName(SIZE (0..64))
        MAX-ACCESS  read-write
        STATUS      current
        DESCRIPTION
            "The Bandwidth Profile Name.It may be created/read/written/modified.
             Writing or modifing can be done all the time."
        ::= { zxGponBandwidthProfileEntry 2}

    zxGponBWProfileFixed OBJECT-TYPE
        SYNTAX      INTEGER
        MAX-ACCESS  read-write
        STATUS      current
        DESCRIPTION
            "The Fixed Bandwidth is entirely reserved and cyclically allocated in order
             to achieve a low traffic transfer delay.The unit of kbps.It may be created
             /read/written/modified. Guaranteed Bandwidth is the summation of Assured 
             Bandwidth and Fixed Bandwidth. Writing or modifing can be done when the 
             entry SHOULD NOT be used by any other entry."
        ::= { zxGponBandwidthProfileEntry 3}

    zxGponBWProfileAssured OBJECT-TYPE
        SYNTAX      INTEGER
        MAX-ACCESS  read-write
        STATUS      current
        DESCRIPTION
            "The Assured Bandwidth is bandwidth that is always available to the ONU/ONT if
             the T-CONT buffer is expected to have traffic to transmit. If the T-CONT buffer 
             does not have traffic to transmit, this bandwidth may be used by other T-CONTs.
             The unit of kbps. It may be created/read/written/modified. Guaranteed Bandwidth
             is the summation of Assured Bandwidth and Fixed Bandwidth. Writing or modifing 
             can be done when the entry SHOULD NOT be used by any other entry."
        ::= { zxGponBandwidthProfileEntry 4}

    zxGponBWProfileMaximum OBJECT-TYPE
        SYNTAX      INTEGER
        MAX-ACCESS  read-write
        STATUS      current
        DESCRIPTION
            "The Maximum Bandwidth.The unit of kbps.It may be created/read/written/modified. 
             Writing or modifing can be done when the entry SHOULD NOT be used by any other entry."
        ::= { zxGponBandwidthProfileEntry 5}

    zxGponBWProfileType OBJECT-TYPE
        SYNTAX      INTEGER{
                    type1(1),
                    type2(2),
                    type3(3),
                    type4(4),
                    type5(5)
                    }
        MAX-ACCESS  read-write
        STATUS      current
        DESCRIPTION
            "Type 1 is characterized by Fixed bandwidth only;
             Type 2 is characterized by Assured bandwidth only;
             Type 3 has Assured bandwidth and Non-assured bandwidth;
             Type 4 has Best-effort bandwidth only and does not have any Guaranteed bandwidth;
             Type 5 is the super set of all of types."
        ::= { zxGponBandwidthProfileEntry 6}
        
    zxGponBWProfileRefCnt OBJECT-TYPE
        SYNTAX      INTEGER
        MAX-ACCESS  read-only
        STATUS      current
        DESCRIPTION
            "Indicate the reference count of this BW profile."
        ::= { zxGponBandwidthProfileEntry 7}

    zxGponBWProfileEntryStatus OBJECT-TYPE
        SYNTAX      RowStatus
        MAX-ACCESS  read-create
        STATUS      current
        DESCRIPTION
            "The control that allows creation and deletion of entries. Deleting can be done
             when the entry SHOULD NOT be used by any other entry."
        ::= { zxGponBandwidthProfileEntry 8}

    zxGponTrafficProfileTable OBJECT-TYPE
        SYNTAX      SEQUENCE OF ZxGponTrafficProfileEntry
        MAX-ACCESS  not-accessible
        STATUS      current
        DESCRIPTION
            "Rate configuration for one traffic.
             As following:
             sustainable information rate      ab. SIR
             peak information rate             ab. PIR
             "
        ::= { zxGponProfileMgmt 2 }

    zxGponTrafficProfileEntry OBJECT-TYPE
        SYNTAX      ZxGponTrafficProfileEntry
        MAX-ACCESS  not-accessible
        STATUS      current
        DESCRIPTION
            "An entry in the Traffic profile table."
        INDEX   { zxGponTrafficProfileIndex }
        ::= { zxGponTrafficProfileTable 1 }

    ZxGponTrafficProfileEntry ::=
        SEQUENCE {
            zxGponTrafficProfileIndex       INTEGER,
            zxGponTrafficProfileName        ZxGponRecordName,
            zxGponTrafficProfileSir         INTEGER,
            zxGponTrafficProfilePir         INTEGER,
            zxGponTrafficProfileRefCnt      INTEGER,
            zxGponTrafficProfileEntryStatus RowStatus,
            zxGponTrafficProfileCbs         Integer32,
            zxGponTrafficProfilePbs         Integer32
        }

    zxGponTrafficProfileIndex OBJECT-TYPE
        SYNTAX      INTEGER
        MAX-ACCESS  not-accessible
        STATUS      current
        DESCRIPTION
            "An arbitrary(unique) integer for identifiying an entry
             in the line card, from 1 to M, M is equal to 512."
        ::= { zxGponTrafficProfileEntry 1}

    zxGponTrafficProfileName OBJECT-TYPE
        SYNTAX      ZxGponRecordName(SIZE (0..64))
        MAX-ACCESS  read-write
        STATUS      current
        DESCRIPTION
            "The Traffic Profile Name.It may be created/read/written/modified.
             Writing or modifing can be done all the time."
        ::= { zxGponTrafficProfileEntry 2}

    zxGponTrafficProfileSir OBJECT-TYPE
        SYNTAX      INTEGER
        MAX-ACCESS  read-write
        STATUS      current
        DESCRIPTION
            "The SIR is sustainable rate of the traffic. Writing or modifing can be done when the 
             entry SHOULD NOT be used by any other entry."
        ::= { zxGponTrafficProfileEntry 3}

    zxGponTrafficProfilePir OBJECT-TYPE
        SYNTAX      INTEGER
        MAX-ACCESS  read-write
        STATUS      current
        DESCRIPTION
            "The PIR is peak rate of the traffic. Writing or modifing can be done when the 
             entry SHOULD NOT be used by any other entry."
        ::= { zxGponTrafficProfileEntry 4}
        
    zxGponTrafficProfileRefCnt OBJECT-TYPE
        SYNTAX      INTEGER
        MAX-ACCESS  read-only
        STATUS      current
        DESCRIPTION
            "The reference count of this profile."
        ::= { zxGponTrafficProfileEntry 5}

    zxGponTrafficProfileEntryStatus OBJECT-TYPE
        SYNTAX      RowStatus
        MAX-ACCESS  read-create
        STATUS      current
        DESCRIPTION
            "The control that allows creation and deletion of entries. Deleting can be done
             when the entry SHOULD NOT be used by any other entry."
        ::= { zxGponTrafficProfileEntry 6}
        
    zxGponTrafficProfileCbs OBJECT-TYPE
        SYNTAX      Integer32(0..1023)
        UNITS       "kbytes"
        MAX-ACCESS  read-create
        STATUS      current
        DESCRIPTION
            "This attribute specifies committed block size. 
             The value 0 accepts the system default policy."
        DEFVAL    { 0 }
        ::= { zxGponTrafficProfileEntry 7}

    zxGponTrafficProfilePbs OBJECT-TYPE
        SYNTAX      Integer32(0..1023)
        UNITS       "kbytes"
        MAX-ACCESS  read-create
        STATUS      current
        DESCRIPTION
            "This attribute specifies peak block size. 
             The value 0 accepts the system default policy."
        DEFVAL    { 0 }
        ::= { zxGponTrafficProfileEntry 8}
                
    
    zxGponThresholdDataProfileTable OBJECT-TYPE
        SYNTAX      SEQUENCE OF ZxGponThresholdDataProfileEntry
        MAX-ACCESS  not-accessible
        STATUS      current
        DESCRIPTION
            "It represents threshold values for the performance monitoring parameters."
        REFERENCE
            "G.984.4 Section 9.1.8 Threshold Data 1 and Section 9.1.9 Threshold Data 2"
        ::= { zxGponProfileMgmt 3 }

    zxGponThresholdDataProfileEntry OBJECT-TYPE
        SYNTAX      ZxGponThresholdDataProfileEntry
        MAX-ACCESS  not-accessible
        STATUS      current
        DESCRIPTION
            "It provide a Threshold Data pointer."
        REFERENCE
            "G.984.4 Section 9.1.8 Threshold Data 1 and Section 9.1.9 Threshold Data 2"
        INDEX   { zxGponThresholdDataProfileIndex }
        ::= { zxGponThresholdDataProfileTable 1 }

    ZxGponThresholdDataProfileEntry ::=
        SEQUENCE {
            zxGponThresholdDataProfileIndex       INTEGER,
            zxGponThresholdDataProfileName        ZxGponRecordName,
            zxGponThresholdDataProfileVal1        Unsigned32,
            zxGponThresholdDataProfileVal2        Unsigned32,
            zxGponThresholdDataProfileVal3        Unsigned32,
            zxGponThresholdDataProfileVal4        Unsigned32,
            zxGponThresholdDataProfileVal5        Unsigned32,
            zxGponThresholdDataProfileVal6        Unsigned32,
            zxGponThresholdDataProfileVal7        Unsigned32,
            zxGponThresholdDataProfileVal8        Unsigned32,
            zxGponThresholdDataProfileVal9        Unsigned32,
            zxGponThresholdDataProfileVal10       Unsigned32,
            zxGponThresholdDataProfileVal11       Unsigned32,
            zxGponThresholdDataProfileVal12       Unsigned32,
            zxGponThresholdDataProfileVal13       Unsigned32,
            zxGponThresholdDataProfileVal14       Unsigned32,
            zxGponThresholdDataProfileRefCnt       INTEGER,
            zxGponThresholdDataProfileEntryStatus RowStatus
        }

    zxGponThresholdDataProfileIndex OBJECT-TYPE
        SYNTAX      INTEGER
        MAX-ACCESS  not-accessible
        STATUS      current
        DESCRIPTION
            "An arbitrary(unique) integer for identifiying an entry in the Threshold Data,
             from 1 to M, M is equal to 128."
        ::= { zxGponThresholdDataProfileEntry 1}

    zxGponThresholdDataProfileName OBJECT-TYPE
        SYNTAX      ZxGponRecordName(SIZE (0..64))
        MAX-ACCESS  read-write
        STATUS      current
        DESCRIPTION
            "The Threshold Data Templet Name.It may be created/read/written/modified.
             Writing or modifing can be done all the time."
        ::= { zxGponThresholdDataProfileEntry 2}

    zxGponThresholdDataProfileVal1 OBJECT-TYPE
        SYNTAX      Unsigned32
        MAX-ACCESS  read-write
        STATUS      current
        DESCRIPTION
            "It provides the associated threshold value for the 1st thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 3}

    zxGponThresholdDataProfileVal2 OBJECT-TYPE
        SYNTAX      Unsigned32
        MAX-ACCESS  read-write
        STATUS      current
        DESCRIPTION
            "It provides the associated threshold value for the 2nd thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 4}

    zxGponThresholdDataProfileVal3 OBJECT-TYPE
        SYNTAX      Unsigned32
        MAX-ACCESS  read-write
        STATUS      current
        DESCRIPTION
            "It provides the associated threshold value for the 3rd thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 5}

    zxGponThresholdDataProfileVal4 OBJECT-TYPE
        SYNTAX      Unsigned32
        MAX-ACCESS  read-write
        STATUS      current
        DESCRIPTION
            "It provides the associated threshold value for the 4th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 6}

    zxGponThresholdDataProfileVal5 OBJECT-TYPE
        SYNTAX      Unsigned32
        MAX-ACCESS  read-write
        STATUS      current
        DESCRIPTION
            "It provides the associated threshold value for the 5th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 7}

    zxGponThresholdDataProfileVal6 OBJECT-TYPE
        SYNTAX      Unsigned32
        MAX-ACCESS  read-write
        STATUS      current
        DESCRIPTION
            "It provides the associated threshold value for the 6th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 8}

    zxGponThresholdDataProfileVal7 OBJECT-TYPE
        SYNTAX      Unsigned32
        MAX-ACCESS  read-write
        STATUS      current
        DESCRIPTION
            "It provides the associated threshold value for the 7st thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 9}

    zxGponThresholdDataProfileVal8 OBJECT-TYPE
        SYNTAX      Unsigned32
        MAX-ACCESS  read-write
        STATUS      current
        DESCRIPTION
            "It provides the associated threshold value for the 8th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 10}

    zxGponThresholdDataProfileVal9 OBJECT-TYPE
        SYNTAX      Unsigned32
        MAX-ACCESS  read-write
        STATUS      current
        DESCRIPTION
            "It provides the associated threshold value for the 9th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 11}

    zxGponThresholdDataProfileVal10 OBJECT-TYPE
        SYNTAX      Unsigned32
        MAX-ACCESS  read-write
        STATUS      current
        DESCRIPTION
            "It provides the associated threshold value for the 10th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 12}

    zxGponThresholdDataProfileVal11 OBJECT-TYPE
        SYNTAX      Unsigned32
        MAX-ACCESS  read-write
        STATUS      current
        DESCRIPTION
            "It provides the associated threshold value for the 11th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 13}

    zxGponThresholdDataProfileVal12 OBJECT-TYPE
        SYNTAX      Unsigned32
        MAX-ACCESS  read-write
        STATUS      current
        DESCRIPTION
            "It provides the associated threshold value for the 12th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 14}

    zxGponThresholdDataProfileVal13 OBJECT-TYPE
        SYNTAX      Unsigned32
        MAX-ACCESS  read-write
        STATUS      current
        DESCRIPTION
            "It provides the associated threshold value for the 13th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 15}

    zxGponThresholdDataProfileVal14 OBJECT-TYPE
        SYNTAX      Unsigned32
        MAX-ACCESS  read-write
        STATUS      current
        DESCRIPTION
            "It provides the associated threshold value for the 14th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 16}
        
    zxGponThresholdDataProfileRefCnt OBJECT-TYPE
        SYNTAX      INTEGER
        MAX-ACCESS  read-only
        STATUS      current
        DESCRIPTION
            "The reference count of this profile."
        REFERENCE
            ""
        ::= { zxGponThresholdDataProfileEntry 17}

    zxGponThresholdDataProfileEntryStatus OBJECT-TYPE
        SYNTAX      RowStatus
        MAX-ACCESS  read-create
        STATUS      current
        DESCRIPTION
            "The control that allows creation and deletion of entries. Deleting can be done
             when the entry SHOULD NOT be used by any other entry."
        ::= { zxGponThresholdDataProfileEntry 18}
 
 
--------------------------------------------------------------------------------
-- zxAnGponPerfAlarmProfile
--------------------------------------------------------------------------------       
--------------------------------------------------------------------------------
-- zxGponOltPerfAlmProfileConfTable
--------------------------------------------------------------------------------

    zxGponOltPerfAlmProfileConfTable   OBJECT-TYPE
        SYNTAX      SEQUENCE OF ZxGponOltPerfAlmProfileConfEntry
        MAX-ACCESS  not-accessible
        STATUS      current
        DESCRIPTION 
             "The performance alarm threshold profile table of interfaces."             
        ::= { zxAnGponPerfAlarmProfile 1 }

    zxGponOltPerfAlmProfileConfEntry   OBJECT-TYPE
        SYNTAX      ZxGponOltPerfAlmProfileConfEntry
        MAX-ACCESS  not-accessible
        STATUS      current
        DESCRIPTION 
            "An entry in zxGponOltPerfAlmProfileConfTable.
            When a manager wants to create or modify an olt performance 
            alarm threshold item,it must comply with the multi-variables 
            usage rule that all the mib variables related to same 
            fuction must be in one snmp set operation, the variables have
            only one type: mandatory.
            
            Mandatory variables must be in the one snmp set operation.
                   
            To create an olt performance alarm threshold item on
            different level, alarm threshold ,restore threshold and 
            zxGponOltAlmPrfRowStatus should be in one snmp set operation.
            The alarm threshold and restore threshold variables in the 
            one snmp set operationshould be on same level.
            Such as:
            zxGponOltRiseAlmThresh and zxGponOltRiseAlmClrThresh,
            zxGponOltRiseWarnThresh and zxGponOltRiseWarnClrThresh,
            zxGponOltFallWarnThresh and zxGponOltFallWarnClrThresh,
            zxGponOltFallAlmThresh and zxGponOltFallAlmClrThresh.
            
            To modify an olt performance alarm threshold item on
            different level,alarm threshold and restore threshold
            should be also in the one snmp set 
            operation regardless of modifying alarm or restore threshold 
            value alone.
            The alarm threshold and restore threshold variables in the 
            one snmp set operationshould be on same level.
            Such as:
            zxGponOltRiseAlmThresh and zxGponOltRiseAlmClrThresh,
            zxGponOltRiseWarnThresh and zxGponOltRiseWarnClrThresh,
            zxGponOltFallWarnThresh and zxGponOltFallWarnClrThresh,
            zxGponOltFallAlmThresh and zxGponOltFallAlmClrThresh.
            
            To remove an olt performance alarm threshold item, only 
            zxGponOltAlmPrfRowStatus should be set to destroy(6) while all 
            levels of this onu performance alarm threshold item will be 
            removed."
        INDEX   { zxGponOltAlmProfileName, zxGponOltPerfVariable }
        ::= { zxGponOltPerfAlmProfileConfTable 1 }

    ZxGponOltPerfAlmProfileConfEntry ::= SEQUENCE {
        zxGponOltAlmProfileName              DisplayString,  
        zxGponOltPerfVariable                OBJECT IDENTIFIER,
        zxGponOltRiseAlmThresh               Counter64,
        zxGponOltRiseAlmClrThresh            Counter64,        
        zxGponOltRiseWarnThresh              Counter64,  
        zxGponOltRiseWarnClrThresh           Counter64,        
        zxGponOltFallWarnThresh              Counter64, 
        zxGponOltFallWarnClrThresh           Counter64, 
        zxGponOltFallAlmThresh               Counter64,
        zxGponOltFallAlmClrThresh            Counter64,
        zxGponOltThreshUsed                  BITS,
        zxGponOltAlmPrfRowStatus             RowStatus
        }

    zxGponOltAlmProfileName  OBJECT-TYPE 
        SYNTAX      DisplayString(SIZE (1 .. 32))
        MAX-ACCESS  not-accessible
        STATUS      current
        DESCRIPTION     
            "The profile name."
        ::= { zxGponOltPerfAlmProfileConfEntry 1 }
        
    zxGponOltPerfVariable  OBJECT-TYPE 
        SYNTAX      OBJECT IDENTIFIER
        MAX-ACCESS  not-accessible
        STATUS      current
        DESCRIPTION     
            "The object identifier of performance variables."
        ::= { zxGponOltPerfAlmProfileConfEntry 2 }
        
    zxGponOltRiseAlmThresh  OBJECT-TYPE 
        SYNTAX      Counter64
        MAX-ACCESS  read-create
        STATUS      current
        DESCRIPTION     
            "The threshold for rising alarm."
        ::= { zxGponOltPerfAlmProfileConfEntry 3 }

    zxGponOltRiseAlmClrThresh  OBJECT-TYPE 
        SYNTAX      Counter64
        MAX-ACCESS  read-create
        STATUS      current
        DESCRIPTION     
            "The threshold for rising alarm restore."
        ::= { zxGponOltPerfAlmProfileConfEntry 4 }

    zxGponOltRiseWarnThresh  OBJECT-TYPE 
        SYNTAX      Counter64
        MAX-ACCESS  read-create
        STATUS      current
        DESCRIPTION     
            "The threshold for rising warning."
        ::= { zxGponOltPerfAlmProfileConfEntry 5 }

    zxGponOltRiseWarnClrThresh  OBJECT-TYPE 
        SYNTAX      Counter64
        MAX-ACCESS  read-create
        STATUS      current
        DESCRIPTION     
            "The threshold for rising warning restore."
        ::= { zxGponOltPerfAlmProfileConfEntry 6 }
        
    zxGponOltFallWarnThresh  OBJECT-TYPE 
        SYNTAX      Counter64
        MAX-ACCESS  read-create
        STATUS      current
        DESCRIPTION     
            "The threshold for falling warning."
        ::= { zxGponOltPerfAlmProfileConfEntry 7 }

    zxGponOltFallWarnClrThresh  OBJECT-TYPE 
        SYNTAX      Counter64
        MAX-ACCESS  read-create
        STATUS      current
        DESCRIPTION     
            "The threshold for falling warning restore."
        ::= { zxGponOltPerfAlmProfileConfEntry 8 }        
        
    zxGponOltFallAlmThresh  OBJECT-TYPE 
        SYNTAX      Counter64
        MAX-ACCESS  read-create
        STATUS      current
        DESCRIPTION     
            "The threshold for falling alarm."
        ::= { zxGponOltPerfAlmProfileConfEntry 9 }

    zxGponOltFallAlmClrThresh  OBJECT-TYPE 
        SYNTAX      Counter64
        MAX-ACCESS  read-create
        STATUS      current
        DESCRIPTION     
            "The threshold for falling alarm restore."
        ::= { zxGponOltPerfAlmProfileConfEntry 10 }   
        
    zxGponOltThreshUsed  OBJECT-TYPE 
         SYNTAX           BITS 
           {
               riseAlmThresh(0),
               riseAlmClrThresh(1),
               riseWarnThresh(2),
               riseWarnClrThresh(3),
               fallWarnThresh(4),
               fallWarnClrThresh(5),
               fallAlmThresh(6),
               fallAlmClrThresh(7)
           }             
        MAX-ACCESS  read-create
        STATUS      current
        DESCRIPTION     
            "The threshold used flag for falling alarm restore."
        ::= { zxGponOltPerfAlmProfileConfEntry 11 }            

    zxGponOltAlmPrfRowStatus  OBJECT-TYPE
        SYNTAX      RowStatus
        MAX-ACCESS  read-create
        STATUS      current
        DESCRIPTION     
            "The status of this conceptual row. 
            
             The supported actions of this conceptual row only include:
            'createAndGo' and 'destroy'.
             
             To create a row in this table, a manager must
             set this object to createAndGo(4).
             
             To delete a row in this table, a manager must
             set this object to destroy(6).
             
             To query this object, always return 1."
        ::= { zxGponOltPerfAlmProfileConfEntry 50 }
        
--------------------------------------------------------------------------------
-- zxGponOltPerfAlmPrfApplyTable
--------------------------------------------------------------------------------

    zxGponOltPerfAlmPrfApplyTable   OBJECT-TYPE
        SYNTAX      SEQUENCE OF ZxGponOltPerfAlmPrfApplyEntry
        MAX-ACCESS  not-accessible
        STATUS      current
        DESCRIPTION 
             "The performance alarm threshold profile applying table of 
              interfaces."             
        ::= { zxAnGponPerfAlarmProfile 2 }

    zxGponOltPerfAlmPrfApplyEntry   OBJECT-TYPE
        SYNTAX      ZxGponOltPerfAlmPrfApplyEntry
        MAX-ACCESS  not-accessible
        STATUS      current
        DESCRIPTION 
            " An entry in zxGponOltPerfAlmPrfApplyTable.
            When a manager wants to apply an olt performance alarm 
            profile to specificed olt interface,it must comply with 
            the multi-variables usage rule that all the mib variables 
            related to same fuction must be in one snmp set operation, 
            the variables have only one type: mandatory.
            
            Mandatory variables must be in the one snmp set operation.
                   
            To apply an olt performance alarm profile to specificed olt 
            interface, zxGponOltPerfAlmProfile and 
            zxGponOltAlmPrfApplyRowStatus should be in the one snmp set 
            operation.
            To unapply an olt performance alarm profile to specificed olt
            interface, only zxGponOltAlmPrfApplyRowStatus should be set to 
            destroy(6)."
        INDEX   { zxGponMgmtPonOltId}
        ::= { zxGponOltPerfAlmPrfApplyTable 1 }

    ZxGponOltPerfAlmPrfApplyEntry ::= SEQUENCE {
        zxGponOltPerfAlmProfile                DisplayString,
        zxGponOltAlmPrfApplyRowStatus  RowStatus
        }
        
    zxGponOltPerfAlmProfile  OBJECT-TYPE 
        SYNTAX      DisplayString(SIZE (1 .. 32))
        MAX-ACCESS  read-create
        STATUS      current
        DESCRIPTION     
            "The performance alarm threshold profile."
        ::= { zxGponOltPerfAlmPrfApplyEntry 1 }
               
    zxGponOltAlmPrfApplyRowStatus  OBJECT-TYPE 
        SYNTAX      RowStatus
        MAX-ACCESS  read-create
        STATUS      current
        DESCRIPTION     
            "The status of this conceptual row. 
              
             The supported actions of this conceptual row only include:
             'createAndGo' and 'destroy'.

             To create a row in this table, a manager must
             set this object to createAndGo(4).
            
             To delete a row in this table, a manager must
             set this object to destroy(6).
             
             To query this object, always return 1."
        ::= { zxGponOltPerfAlmPrfApplyEntry 50 }  
        
--------------------------------------------------------------------------------
-- zxGponOntPerfAlmProfileConfTable
--------------------------------------------------------------------------------

    zxGponOntPerfAlmProfileConfTable   OBJECT-TYPE
        SYNTAX      SEQUENCE OF ZxGponOntPerfAlmProfileConfEntry
        MAX-ACCESS  not-accessible
        STATUS      current
        DESCRIPTION 
             "The performance alarm threshold profile table of interfaces."             
        ::= { zxAnGponPerfAlarmProfile 3 }

    zxGponOntPerfAlmProfileConfEntry   OBJECT-TYPE
        SYNTAX      ZxGponOntPerfAlmProfileConfEntry
        MAX-ACCESS  not-accessible
        STATUS      current
        DESCRIPTION 
            "An entry in zxGponOntPerfAlmProfileConfTable.
            When a manager wants to create or modify an onu performance 
            alarm threshold item,it must comply with the multi-variables 
            usage rule that all the mib variables related to same 
            fuction must be in one snmp set operation, the variables have
            only one type: mandatory.
            
            Mandatory variables must be in the one snmp set operation.
                   
            To create an onu performance alarm threshold item on
            different level, alarm threshold ,restore threshold and 
            zxGponOntAlmPrfRowStatus should be in one snmp set operation.
            The alarm threshold and restore threshold variables in the 
            one snmp set operationshould be on same level.
            Such as:
            zxGponOntRiseAlmThresh and zxGponOntRiseAlmClrThresh,
            zxGponOntRiseWarnThresh and zxGponOntRiseWarnClrThresh,
            zxGponOntFallWarnThresh and zxGponOntFallWarnClrThresh,
            zxGponOntFallAlmThresh and zxGponOntFallAlmClrThresh.
                          
            To modify an onu performance alarm threshold item on
            different level,alarm threshold and restore threshold
            should be also in the one snmp set 
            operation regardless of modifying alarm or restore threshold 
            value alone.
            The alarm threshold and restore threshold variables in the 
            one snmp set operationshould be on same level.
            Such as:
            zxGponOntRiseAlmThresh and zxGponOntRiseAlmClrThresh,
            zxGponOntRiseWarnThresh and zxGponOntRiseWarnClrThresh,
            zxGponOntFallWarnThresh and zxGponOntFallWarnClrThresh,
            zxGponOntFallAlmThresh and zxGponOntlFallAlmClrThresh.
            
            To remove an onu performance alarm threshold item, only 
            zxGponOntAlmPrfRowStatus should be set to destroy(6) while all 
            levels of this onu performance alarm threshold item will be 
            removed."
        INDEX   { zxGponOntAlmProfileName, zxGponOntPerfVariable }
        ::= { zxGponOntPerfAlmProfileConfTable 1 }

    ZxGponOntPerfAlmProfileConfEntry ::= SEQUENCE {
        zxGponOntAlmProfileName              DisplayString,  
        zxGponOntPerfVariable                OBJECT IDENTIFIER,
        zxGponOntRiseAlmThresh               Counter64,
        zxGponOntRiseAlmClrThresh            Counter64,        
        zxGponOntRiseWarnThresh              Counter64,  
        zxGponOntRiseWarnClrThresh           Counter64,        
        zxGponOntFallWarnThresh              Counter64, 
        zxGponOntFallWarnClrThresh           Counter64, 
        zxGponOntFallAlmThresh               Counter64,
        zxGponOntFallAlmClrThresh            Counter64,
        zxGponOntThreshUsed                  BITS,
        zxGponOntAlmPrfRowStatus             RowStatus
        }

    zxGponOntAlmProfileName  OBJECT-TYPE 
        SYNTAX      DisplayString(SIZE (1 .. 32))
        MAX-ACCESS  not-accessible
        STATUS      current
        DESCRIPTION     
            "The profile name."
        ::= { zxGponOntPerfAlmProfileConfEntry 1 }
        
    zxGponOntPerfVariable  OBJECT-TYPE 
        SYNTAX      OBJECT IDENTIFIER
        MAX-ACCESS  not-accessible
        STATUS      current
        DESCRIPTION     
            "The object identifier of performance variables."
        ::= { zxGponOntPerfAlmProfileConfEntry 2 }
        
    zxGponOntRiseAlmThresh  OBJECT-TYPE 
        SYNTAX      Counter64
        MAX-ACCESS  read-create
        STATUS      current
        DESCRIPTION     
            "The threshold for rising alarm."
        ::= { zxGponOntPerfAlmProfileConfEntry 3 }

    zxGponOntRiseAlmClrThresh  OBJECT-TYPE 
        SYNTAX      Counter64
        MAX-ACCESS  read-create
        STATUS      current
        DESCRIPTION     
            "The threshold for rising alarm restore."
        ::= { zxGponOntPerfAlmProfileConfEntry 4 }

    zxGponOntRiseWarnThresh  OBJECT-TYPE 
        SYNTAX      Counter64
        MAX-ACCESS  read-create
        STATUS      current
        DESCRIPTION     
            "The threshold for rising warning."
        ::= { zxGponOntPerfAlmProfileConfEntry 5 }

    zxGponOntRiseWarnClrThresh  OBJECT-TYPE 
        SYNTAX      Counter64
        MAX-ACCESS  read-create
        STATUS      current
        DESCRIPTION     
            "The threshold for rising warning restore."
        ::= { zxGponOntPerfAlmProfileConfEntry 6 }
        
    zxGponOntFallWarnThresh  OBJECT-TYPE 
        SYNTAX      Counter64
        MAX-ACCESS  read-create
        STATUS      current
        DESCRIPTION     
            "The threshold for falling warning."
        ::= { zxGponOntPerfAlmProfileConfEntry 7 }

    zxGponOntFallWarnClrThresh  OBJECT-TYPE 
        SYNTAX      Counter64
        MAX-ACCESS  read-create
        STATUS      current
        DESCRIPTION     
            "The threshold for falling warning restore."
        ::= { zxGponOntPerfAlmProfileConfEntry 8 }        
        
    zxGponOntFallAlmThresh  OBJECT-TYPE 
        SYNTAX      Counter64
        MAX-ACCESS  read-create
        STATUS      current
        DESCRIPTION     
            "The threshold for falling alarm."
        ::= { zxGponOntPerfAlmProfileConfEntry 9 }

    zxGponOntFallAlmClrThresh  OBJECT-TYPE 
        SYNTAX      Counter64
        MAX-ACCESS  read-create
        STATUS      current
        DESCRIPTION     
            "The threshold for falling alarm restore."
        ::= { zxGponOntPerfAlmProfileConfEntry 10 } 
        
    zxGponOntThreshUsed  OBJECT-TYPE 
         SYNTAX           BITS 
           {
               riseAlmThresh(0),
               riseAlmClrThresh(1),
               riseWarnThresh(2),
               riseWarnClrThresh(3),
               fallWarnThresh(4),
               fallWarnClrThresh(5),
               fallAlmThresh(6),
               fallAlmClrThresh(7)
           }             
        MAX-ACCESS  read-create
        STATUS      current
        DESCRIPTION     
            "The threshold used flag for falling alarm restore."
        ::= { zxGponOntPerfAlmProfileConfEntry 11 }                    

    zxGponOntAlmPrfRowStatus  OBJECT-TYPE
        SYNTAX      RowStatus
        MAX-ACCESS  read-create
        STATUS      current
        DESCRIPTION     
            "The status of this conceptual row. 
             
             The supported actions of this conceptual row only include:
             'createAndGo' and 'destroy'.

             To create a row in this table, a manager must
             set this object to createAndGo(4).
             
             To delete a row in this table, a manager must
             set this object to destroy(6). 
             
             To query this object, always return 1."
        ::= { zxGponOntPerfAlmProfileConfEntry 50 }
        
--------------------------------------------------------------------------------
-- zxGponOntPerfAlmPrfApplyTable
--------------------------------------------------------------------------------

    zxGponOntPerfAlmPrfApplyTable   OBJECT-TYPE
        SYNTAX      SEQUENCE OF ZxGponOntPerfAlmPrfApplyEntry
        MAX-ACCESS  not-accessible
        STATUS      current
        DESCRIPTION 
             "The performance alarm threshold profile 
             applying table of interfaces."             
        ::= { zxAnGponPerfAlarmProfile 4 }

    zxGponOntPerfAlmPrfApplyEntry   OBJECT-TYPE
        SYNTAX      ZxGponOntPerfAlmPrfApplyEntry
        MAX-ACCESS  not-accessible
        STATUS      current
        DESCRIPTION 
            "An entry in zxGponOntPerfAlmPrfApplyTable.
            When a manager wants to apply an onu performance alarm 
            profile to specificed onu interface,it must comply with 
            the multi-variables usage rule that all the mib variables 
            related to same fuction must be in one snmp set operation, 
            the variables have only one type: mandatory.
            
            Mandatory variables must be in the one snmp set operation.
                   
            To apply an onu performance alarm profile to specificed onu 
            interface, zxGponOntPerfAlmProfile and 
            zxGponOntAlmPrfApplyRowStatus should be in the one snmp set 
            operation.
            
            To unapply an onu performance alarm profile to specificed onu
            interface, only zxGponOltAlmPrfApplyRowStatus should be set to 
            destroy(6)."
        INDEX   { zxGponMgmtPonOltId, zxGponMgmtPonOnuId }
        ::= { zxGponOntPerfAlmPrfApplyTable 1 }

    ZxGponOntPerfAlmPrfApplyEntry ::= SEQUENCE {
        zxGponOntPerfAlmProfile                DisplayString,
        zxGponOntAlmPrfApplyRowStatus          RowStatus
        }
        
    zxGponOntPerfAlmProfile  OBJECT-TYPE 
        SYNTAX      DisplayString(SIZE (1 .. 32))
        MAX-ACCESS  read-create
        STATUS      current
        DESCRIPTION     
            "The performance alarm threshold profile."
        ::= { zxGponOntPerfAlmPrfApplyEntry 1 }
               
    zxGponOntAlmPrfApplyRowStatus  OBJECT-TYPE 
        SYNTAX      RowStatus
        MAX-ACCESS  read-create
        STATUS      current
        DESCRIPTION     
            "The status of this conceptual row.
             
             The supported actions of this conceptual row only include:
             'createAndGo' and 'destroy'.

             To create a row in this table, a manager must
             set this object to createAndGo(4).
            
             To delete a row in this table, a manager must
             set this object to destroy(6). 
             
             To query this object, always return 1."
        ::= { zxGponOntPerfAlmPrfApplyEntry 50 }  
        
--------------------------------------------------------------------------------
-- zxGponOltPerfAlmProfileTable
--------------------------------------------------------------------------------

    zxGponOltPerfAlmProfileTable   OBJECT-TYPE
        SYNTAX      SEQUENCE OF ZxGponOltPerfAlmProfileEntry
        MAX-ACCESS  not-accessible
        STATUS      current
        DESCRIPTION 
             "The performance alarm threshold profile 
             list table of interfaces."             
        ::= { zxAnGponPerfAlarmProfile 5 }

    zxGponOltPerfAlmProfileEntry   OBJECT-TYPE
        SYNTAX      ZxGponOltPerfAlmProfileEntry
        MAX-ACCESS  not-accessible
        STATUS      current
        DESCRIPTION 
            "The performance alarm threshold profile 
            applying entry of interfaces."
        INDEX   { zxGponOltPerfAlmProfileName }
        ::= { zxGponOltPerfAlmProfileTable 1 }

    ZxGponOltPerfAlmProfileEntry ::= SEQUENCE {
        zxGponOltPerfAlmProfileName           DisplayString,
        zxGponOltPerfAlmProfileRowStatus      RowStatus
        }
        
    zxGponOltPerfAlmProfileName  OBJECT-TYPE 
        SYNTAX      DisplayString(SIZE (1 .. 32))
        MAX-ACCESS  not-accessible
        STATUS      current
        DESCRIPTION     
            "The performance alarm threshold profile name."
        ::= { zxGponOltPerfAlmProfileEntry 1 }
               
    zxGponOltPerfAlmProfileRowStatus  OBJECT-TYPE 
        SYNTAX      RowStatus
        MAX-ACCESS  read-create
        STATUS      current
        DESCRIPTION     
            "The status of this conceptual row.
             
             The supported actions of this conceptual row only include:
             'createAndGo' and 'destroy'.

             To create a row in this table, a manager must
             set this object to createAndGo(4).
            
             To delete a row in this table, a manager must
             set this object to destroy(6). 
             
             To query this object, always return 1."
        ::= { zxGponOltPerfAlmProfileEntry 50 }          

--------------------------------------------------------------------------------
-- zxGponOntPerfAlmProfileTable
--------------------------------------------------------------------------------

    zxGponOntPerfAlmProfileTable   OBJECT-TYPE
        SYNTAX      SEQUENCE OF ZxGponOntPerfAlmProfileEntry
        MAX-ACCESS  not-accessible
        STATUS      current
        DESCRIPTION 
             "The performance alarm threshold profile 
             list table of interfaces."             
        ::= { zxAnGponPerfAlarmProfile 6 }

    zxGponOntPerfAlmProfileEntry   OBJECT-TYPE
        SYNTAX      ZxGponOntPerfAlmProfileEntry
        MAX-ACCESS  not-accessible
        STATUS      current
        DESCRIPTION 
            "The performance alarm threshold profile 
            applying entry of interfaces."
        INDEX   { zxGponOntPerfAlmProfileName }
        ::= { zxGponOntPerfAlmProfileTable 1 }

    ZxGponOntPerfAlmProfileEntry ::= SEQUENCE {
        zxGponOntPerfAlmProfileName           DisplayString,
        zxGponOntPerfAlmProfileRowStatus      RowStatus
        }
        
    zxGponOntPerfAlmProfileName  OBJECT-TYPE 
        SYNTAX      DisplayString(SIZE (1 .. 32))
        MAX-ACCESS  not-accessible
        STATUS      current
        DESCRIPTION     
            "The performance alarm threshold profile name."
        ::= { zxGponOntPerfAlmProfileEntry 1 }
               
    zxGponOntPerfAlmProfileRowStatus  OBJECT-TYPE 
        SYNTAX      RowStatus
        MAX-ACCESS  read-create
        STATUS      current
        DESCRIPTION     
            "The status of this conceptual row.
             
             The supported actions of this conceptual row only include:
             'createAndGo' and 'destroy'.

             To create a row in this table, a manager must
             set this object to createAndGo(4).
            
             To delete a row in this table, a manager must
             set this object to destroy(6). 
             
             To query this object, always return 1."
        ::= { zxGponOntPerfAlmProfileEntry 50 } 
---
--- DA(48 bits) SA(48 bits) TYPE/LEN(16 bits) RSVD(1bit) PRI(3 bits) VLAN(12 bits) ... ...
--- multicast and VLAN from 10 - 100, the rule as flow:
--- 1st bit = 7,   1st len = 1,  min val = 1,  max val = 1
--- 2nd bit = 116, 2nd len = 12, min val = 10, max val = 100
---
 --zxGponStandardOnu.mi2
    zxGponStandardOnu OBJECT IDENTIFIER ::= { zxGponRootMib 27 }
    
    zxGponPortIdEncryptTable OBJECT-TYPE
        SYNTAX      SEQUENCE OF ZxGponPortIdEncryptEntry
        MAX-ACCESS  not-accessible
        STATUS      current
        DESCRIPTION
            "" 
        REFERENCE
            "G.984.3"
        ::= { zxGponStandardOnu 4 }

    zxGponPortIdEncryptEntry OBJECT-TYPE
        SYNTAX      ZxGponPortIdEncryptEntry
        MAX-ACCESS  not-accessible
        STATUS      current
        DESCRIPTION
            ""
        INDEX   { zxGponMgmtPonOltId, zxGponMgmtPonOnuId, zxGponGemPortIdx }
        ::= { zxGponPortIdEncryptTable 1 }

    ZxGponPortIdEncryptEntry ::=
        SEQUENCE {
            zxGponPortIdEncryptMode INTEGER
        }

     zxGponPortIdEncryptMode OBJECT-TYPE
        SYNTAX      INTEGER{
                    downstreamAes(1),
                    disableAes(2),
                    bidirectionAes(3)
                    }
        MAX-ACCESS  read-write
        STATUS      current
        DESCRIPTION
            ""
        ::= { zxGponPortIdEncryptEntry 1}
  
--zxGponPrivateOnu.mi2
    zxGponPrivateOnu OBJECT IDENTIFIER ::= { zxGponRootMib 28 }

    zxGponOntDevMgmtTable OBJECT-TYPE
        SYNTAX      SEQUENCE OF ZxGponOntDevMgmtEntry
        MAX-ACCESS  not-accessible
        STATUS      current
        DESCRIPTION
            "" 
        REFERENCE
            "G.984.3"
        ::= { zxGponPrivateOnu 1 }

    zxGponOntDevMgmtEntry OBJECT-TYPE
        SYNTAX      ZxGponOntDevMgmtEntry
        MAX-ACCESS  not-accessible
        STATUS      current
        DESCRIPTION
            ""
        INDEX   { zxGponMgmtPonOltId, zxGponMgmtPonOnuId }
        ::= { zxGponOntDevMgmtTable 1 }

    ZxGponOntDevMgmtEntry ::=
        SEQUENCE {
            zxGponOntDevMgmtTypeName            OCTET STRING,
            zxGponOntDevMgmtName                OCTET STRING,
            zxGponOntDevMgmtDescription         OCTET STRING,
            zxGponOntDevMgmtRegisterId          OCTET STRING,
            zxGponOntDevMgmtProvisionSn         OntSerialNumber,
            zxGponOntDevMgmtPwMode              INTEGER,
            zxGponOntDevMgmtPassword            OCTET STRING,
            zxGponOntTargetState                INTEGER,
            zxGponOntDevMgmtEntryStatus         RowStatus,
            zxGponOntVportMode                  INTEGER,
            zxGponOntIsAutoUpdate               TruthValue,
            zxGponOntRegMode                    INTEGER,
            zxGponOntRegId                      OCTET STRING,            
            zxGponOntDbaOperateMode             INTEGER, 
            zxGponOntUpdateSnAction             INTEGER,              
            zxGponOntOmciBwProfilePtr           Integer32,
            zxGponOntEnableWithSn               TruthValue,
            zxGponOntCustomAuthPassControl      INTEGER,
            zxGponOntUpstreamFecEnable          TruthValue,
            zxGponOntIsSnBound                  TruthValue,
            zxGponOnuToDEnable                  INTEGER
        }

   zxGponOntDevMgmtTypeName OBJECT-TYPE
        SYNTAX      OCTET STRING(SIZE(0..64))
        MAX-ACCESS  read-write
        STATUS      current
        DESCRIPTION
            ""
        ::= { zxGponOntDevMgmtEntry 1}

   zxGponOntDevMgmtName OBJECT-TYPE
        SYNTAX      OCTET STRING(SIZE(0..128))
        MAX-ACCESS  read-write
        STATUS      current
        DESCRIPTION
            ""
        ::= { zxGponOntDevMgmtEntry 2}

   zxGponOntDevMgmtDescription OBJECT-TYPE
        SYNTAX      OCTET STRING(SIZE(127))
        MAX-ACCESS  read-write
        STATUS      current
        DESCRIPTION
            "The definition size of description does not include the termination."
        ::= { zxGponOntDevMgmtEntry 3}

   zxGponOntDevMgmtRegisterId OBJECT-TYPE
        SYNTAX      OCTET STRING(SIZE(4))
        MAX-ACCESS  read-write
        STATUS      current
        DESCRIPTION
            "Reserved. use in the future."
        ::= { zxGponOntDevMgmtEntry 4}

     zxGponOntDevMgmtProvisionSn OBJECT-TYPE
        SYNTAX      OntSerialNumber(SIZE (8))
        MAX-ACCESS  read-write
        STATUS      current
        DESCRIPTION
            "SN configed by Olt for the purpose of register"
        ::= { zxGponOntDevMgmtEntry 5}

   zxGponOntDevMgmtPwMode OBJECT-TYPE
        SYNTAX      INTEGER{
                    nonePw(1),
                    force(2)
                    }
        MAX-ACCESS  read-write
        STATUS      current
        DESCRIPTION
            ""
        ::= { zxGponOntDevMgmtEntry 6}

   zxGponOntDevMgmtPassword OBJECT-TYPE
        SYNTAX      OCTET STRING(SIZE(12))
        MAX-ACCESS  read-write
        STATUS      current
        DESCRIPTION
            "Password configed by Olt for the purpose of registration.
             This attribute is valid when zxGponOntRegMode is following value:
                     regModePw(2)--10 Bytes,
                     regModeSnPlusPw(3)--10 Bytes,
                     regModeTefPw(7)--7 Bytes(hex),
                     regModeSnPlusTefPw(8)--7 Bytes(hex),
                     regModeLoidPlusPw(10)--12 Bytes
            "
        ::= { zxGponOntDevMgmtEntry 7}
        
    zxGponOntTargetState OBJECT-TYPE
        SYNTAX      INTEGER{
                    deactive(1),
                    omciready(2)
                    }
        MAX-ACCESS  read-write
        STATUS      current
        DESCRIPTION
            ""
        ::= { zxGponOntDevMgmtEntry 8}

   zxGponOntDevMgmtEntryStatus OBJECT-TYPE
        SYNTAX      RowStatus
        MAX-ACCESS  read-create
        STATUS      current
        DESCRIPTION
            ""
        ::= { zxGponOntDevMgmtEntry 9}
        
   zxGponOntVportMode OBJECT-TYPE
        SYNTAX      INTEGER{
                    gemport(1),
                    onu(2),
                    manul(3)
                    }
        MAX-ACCESS  read-write
        STATUS      current
        DESCRIPTION
            ""
        ::= { zxGponOntDevMgmtEntry 10}

    zxGponOntIsAutoUpdate OBJECT-TYPE
        SYNTAX      TruthValue
        MAX-ACCESS  read-write
        STATUS      current
        DESCRIPTION
            ""
        ::= { zxGponOntDevMgmtEntry 11}
        
    zxGponOntRegMode OBJECT-TYPE
        SYNTAX      INTEGER{
                     regModeSn(1),
                     regModePw(2),
                     regModeSnPlusPw(3),
                     regModeRegisterId(4),
                     regModeRegisterIdPlus8021x(5),
                     regModeRegisterIdPlusMutual(6),
                     regModeTefPw(7),
                     regModeSnPlusTefPw(8),
                     regModeLoid(9),
                     regModeLoidPlusPw(10)
                    }
        MAX-ACCESS  read-write
        STATUS      current
        DESCRIPTION
            "This attribute indicates the onu registration mode.
             regModeSn: GPON/XGPON -- G.984 G.987 -- 8bytes
             regModePw: GPON -- G.984 -- 10Bytes
             regModeSnPlusPw: GPON -- G.984 -- 8+10Bytes
             regModeRegisterId: GPON/XGPON -- G.984 G.987 -- 36Bytes(XPON)
             regModeRegisterIdPlus8021x: XGPON -- G.987 -- 36Bytes
             regModeRegisterIdPlusMutual: XGPON -- G.987 -- 36Bytes
             regModeTefPw: GPON--Telefonica Password format--7Bytes(hex,fixed)
             regModeSnPlusTefPw: GPON--Telefonica SN+Password format
                                       --8+7Bytes(hex,fixed)             
             regModeLoid: GPON/XGPON -- CTC format -- 24Bytes
             regModeLoidPlusPw: GPON/XGPON -- CTC format -- 24+12Bytes
             The attribute is also used to define the registration mode
             in zxGponOnuRegistrationInfo."
        ::= { zxGponOntDevMgmtEntry 12}
        
   zxGponOntRegId OBJECT-TYPE
        SYNTAX      OCTET STRING(SIZE(64))
        MAX-ACCESS  read-write
        STATUS      current
        DESCRIPTION
            "ID configed by Olt for the purpose of register.
             This attribute is valid when zxGponOntRegMode is following value:
                regModeRegisterId(4) --36 Bytes,
                regModeRegisterIdPlus8021x(5)--36 Bytes,
                regModeRegisterIdPlusMutual(6)--36 Bytes,
                regModeLoid(9)--24 Bytes,
                regModeLoidPlusPw(10)--24 Bytes
                "                
        ::= { zxGponOntDevMgmtEntry 13}
                  
    zxGponOntDbaOperateMode OBJECT-TYPE
        SYNTAX      INTEGER{
                     sr(1),
                     nsr(2),
                     hybrid(3) 
                    }
        MAX-ACCESS  read-write
        STATUS      current
        DESCRIPTION
          "In DBA operations, there are three modes: SR(Status Reporting)-DBA, 
           NSR(Non Status Reporting)-DBA and hybrid-DBA in every T-CONT."
        ::= { zxGponOntDevMgmtEntry 14}   
     
          
   zxGponOntUpdateSnAction OBJECT-TYPE
        SYNTAX      INTEGER{
                     updateSn(1)                     
                    }
        MAX-ACCESS  read-write
        STATUS      current
        DESCRIPTION
            "if onu registration-mode is 'regModePwAutoBindSn' , when requires to update onu's  serial number 
           then will execute this action for updating. "
        ::= { zxGponOntDevMgmtEntry 15}        
        
           
    zxGponOntOmciBwProfilePtr OBJECT-TYPE
        SYNTAX      Integer32
        MAX-ACCESS  read-create
        STATUS      current
        DESCRIPTION
            "This object indicates the onu omci channel bandwidth profile,
             value '0' indicates using the system default bandwidth."
        ::= { zxGponOntDevMgmtEntry 16}   
        
    zxGponOntEnableWithSn OBJECT-TYPE
        SYNTAX      TruthValue
        MAX-ACCESS  read-create
        STATUS      current
        DESCRIPTION
            "Disable Option: Moves The ONU To The Emergency Stop State. 
             The ONU Cannot Respond To Upstream Bandwidth Allocations.
             Enable Option: Moves The ONU To The Standby State. 
             The ONU Restarts The Activation Process"
        DEFVAL { true }
        ::= { zxGponOntDevMgmtEntry 17} 
  
    zxGponOntCustomAuthPassControl OBJECT-TYPE
        SYNTAX      INTEGER
        MAX-ACCESS  read-write
        STATUS      current
        DESCRIPTION
            "This variable indicates the ONU authentication successful 
            forwarding actions.The zxGponOntCustomAuthPassControl is a bitmap
            represented as a sum, therefore, it can represent multiple 
            forwarding action.The various bit positions are:
                     1     CNC mode  1:enable,0:disable
                     2     to define      
                     4     to define      
                   ... 
            note: if all bit is 0,OLT will not report zxGponOntAuthPass 
            notification to NMS."
        ::= { zxGponOntDevMgmtEntry 18}    

    zxGponOntUpstreamFecEnable OBJECT-TYPE
        SYNTAX      TruthValue
        MAX-ACCESS  read-write
        STATUS      current
        DESCRIPTION
            "This attribute enables the ONU upstream FEC function ."
        REFERENCE   "G.984.3.13"            
        ::= { zxGponOntDevMgmtEntry 22}        
        
    zxGponOntIsSnBound OBJECT-TYPE
        SYNTAX      TruthValue
        MAX-ACCESS  read-write
        STATUS      current
        DESCRIPTION
            "This attribute indicates whether the ONU need to be bound SN.
             When zxGponOntRegMode is the following values, then this 
             attribute is valid.
                     regModeRegisterId(4)
                     regModeRegisterIdPlus8021x(5)
                     regModeRegisterIdPlusMutual(6)
                     regModeTefPw(7)                     
                     regModeLoid(9)
                     regModeLoidPlusPw(10) 
            "
        DEFVAL { true }
        ::= { zxGponOntDevMgmtEntry 23}        
        
    zxGponOnuToDEnable OBJECT-TYPE
        SYNTAX      INTEGER{
                    enabled(1),
                    disabled(2)
                    }
        MAX-ACCESS  read-write
        STATUS      current
        DESCRIPTION
            "This attribute indicates the ONU ToD message status."
        REFERENCE
            "G.988 section 9.12.2"
        DEFVAL { disabled }
        ::= { zxGponOntDevMgmtEntry 24}            
     
   --              
    zxGponOntStateTable OBJECT-TYPE
        SYNTAX      SEQUENCE OF ZxGponOntStateEntry
        MAX-ACCESS  not-accessible
        STATUS      current
        DESCRIPTION
            "" 
        REFERENCE
            "G.984.3"
        ::= { zxGponPrivateOnu 2 }

    zxGponOntStateEntry OBJECT-TYPE
        SYNTAX      ZxGponOntStateEntry
        MAX-ACCESS  not-accessible
        STATUS      current
        DESCRIPTION
            ""
        INDEX   { zxGponMgmtPonOltId, zxGponMgmtPonOnuId }
        ::= { zxGponOntStateTable 1 }

    ZxGponOntStateEntry ::=
        SEQUENCE {
            zxGponOntAdminState          INTEGER,
            zxGponOntOmccState           TruthValue,
            zxGponOntO1O7State           INTEGER,
            zxGponOntPhaseState          INTEGER,
            zxGponOnuLastOnlineTime      DisplayString,
            zxGponOnuLastOfflineTime     DisplayString,
            zxGponOnuLastOfflineReason    INTEGER
        }

   zxGponOntAdminState OBJECT-TYPE
        SYNTAX      INTEGER{
                    enable(1),
                    disable(2)
                    }
        MAX-ACCESS  read-write
        STATUS      current
        DESCRIPTION
            ""
        ::= { zxGponOntStateEntry 1}

   zxGponOntOmccState OBJECT-TYPE
        SYNTAX      TruthValue
        MAX-ACCESS  read-only
        STATUS      current
        DESCRIPTION
            ""
        ::= { zxGponOntStateEntry 2}

   zxGponOntO1O7State OBJECT-TYPE
        SYNTAX      INTEGER{
                    unknown(0),
                    o1-initial(1),
                    o2-standby(2),
                    o3-powersetup(3),
                    o4-serialnumber(4),
                    o5-ranging(5),
                    o6-operation(6),
                    o7-popup(7)
                    }
        MAX-ACCESS  read-only
        STATUS      current
        DESCRIPTION
            "
            Unknown(DyingGasp),
            Initial-state(O1),
            Standby-state(O2),
            Power-Setup-state(O3),
            Serial-Number-state(O4),
            Ranging-state(O5),
            Operation-state(O6),
            POPUP-state(O7)
            "
        ::= { zxGponOntStateEntry 3}

   zxGponOntPhaseState OBJECT-TYPE
        SYNTAX      INTEGER{
                    logging(0),
                    los(1),
                    syncMib(2),
                    working(3),
                    dyinggasp(4),
                    authFailed(5),
                    offline(6)
                    }
        MAX-ACCESS  read-only
        STATUS      current
        DESCRIPTION
            ""
        ::= { zxGponOntStateEntry 4}
        
   zxGponOnuLastOnlineTime OBJECT-TYPE
        SYNTAX      DisplayString  ( SIZE ( 1 .. 19  ) )
        MAX-ACCESS  read-only
        STATUS      current
        DESCRIPTION
            "ONU last online time.The format is yyyy-mm-dd HH:MM:SS.
            For example,2010-12-30 13:06:30."
        ::= { zxGponOntStateEntry 5}
        
   zxGponOnuLastOfflineTime OBJECT-TYPE
        SYNTAX      DisplayString  ( SIZE ( 1 .. 19  ) )
        MAX-ACCESS  read-only
        STATUS      current
        DESCRIPTION
            "ONU last offline time.The format is yyyy-mm-dd HH:MM:SS.
            For example,2010-12-30 13:06:30."
        ::= { zxGponOntStateEntry 6}
    
    zxGponOnuLastOfflineReason OBJECT-TYPE
        SYNTAX      INTEGER{
                    unknown(1),
                    los(2),
                    losi(3),
                    lofi(4),
                    sfi(5),
                    loai(6),
                    loami(7),
                    authFail(8),
                    dyingGasp(9),
                    deactiveSucc(10),
                    deactiveFail(11),
                    reboot(12),
                    shutdown(13)
                    }
        MAX-ACCESS  read-only
        STATUS      current
        DESCRIPTION
            "ONU last offine reason.
             1 : unknown reason
             2 : OLT LOS 
             3 : ONU LOS 
             4 : ONU LOF 
             5 : ONU SF 
             6 : ONU LOA 
             7 : ONU LOAM 
             8 : ONU authorization failed
             9 : ONU loss of power
             10 : ONU deactivation succeeded
             11 : ONU deactivation failed
             12 : ONU reboot
             13 : ONU shutdown"
        ::= { zxGponOntStateEntry 7}
        
    zxGponOntDevInfoTable OBJECT-TYPE
        SYNTAX      SEQUENCE OF ZxGponOntDevInfoEntry
        MAX-ACCESS  not-accessible
        STATUS      current
        DESCRIPTION
            "" 
        REFERENCE
            "G.984.3"
        ::= { zxGponPrivateOnu 3 }

    zxGponOntDevInfoEntry OBJECT-TYPE
        SYNTAX      ZxGponOntDevInfoEntry
        MAX-ACCESS  not-accessible
        STATUS      current
        DESCRIPTION
            ""
        INDEX   { zxGponMgmtPonOltId, zxGponMgmtPonOnuId }
        ::= { zxGponOntDevInfoTable 1 }

    ZxGponOntDevInfoEntry ::=
        SEQUENCE {
            zxGponOntDevInfoSupportTcontNum  INTEGER,
            zxGponOntDevInfoCurUsedTcontNum  INTEGER,
            zxGponOntDevInfoSupportPortIdNum INTEGER,
            zxGponOntDevInfoCurUsedPortIdNum INTEGER,
            zxGponOntDevInfoPqNum            INTEGER,
            zxGponOntDevInfoTsNum            INTEGER,
            zxGponOntDevInfoServiceType      INTEGER,
            zxGponOntDevInfoRealOnuId        INTEGER
        }

   zxGponOntDevInfoSupportTcontNum OBJECT-TYPE
        SYNTAX      INTEGER
        MAX-ACCESS  read-only
        STATUS      current
        DESCRIPTION
            ""
        ::= { zxGponOntDevInfoEntry 1}

   zxGponOntDevInfoCurUsedTcontNum OBJECT-TYPE
        SYNTAX      INTEGER
        MAX-ACCESS  read-only
        STATUS      current
        DESCRIPTION
            ""
        ::= { zxGponOntDevInfoEntry 2}

   zxGponOntDevInfoSupportPortIdNum OBJECT-TYPE
        SYNTAX      INTEGER
        MAX-ACCESS  read-only
        STATUS      current
        DESCRIPTION
            "Reserved. used in the future."
        ::= { zxGponOntDevInfoEntry 3}

   zxGponOntDevInfoCurUsedPortIdNum OBJECT-TYPE
        SYNTAX      INTEGER
        MAX-ACCESS  read-only
        STATUS      current
        DESCRIPTION
            ""
        ::= { zxGponOntDevInfoEntry 4}

   zxGponOntDevInfoPqNum OBJECT-TYPE
        SYNTAX      INTEGER
        MAX-ACCESS  read-only
        STATUS      current
        DESCRIPTION
            ""
        ::= { zxGponOntDevInfoEntry 5}
        
   zxGponOntDevInfoTsNum OBJECT-TYPE
        SYNTAX      INTEGER
        MAX-ACCESS  read-only
        STATUS      current
        DESCRIPTION
            ""
        ::= { zxGponOntDevInfoEntry 6}

   zxGponOntDevInfoServiceType OBJECT-TYPE
        SYNTAX      INTEGER
        MAX-ACCESS  read-only
        STATUS      current
        DESCRIPTION
            "Reserved. used in the future."
        ::= { zxGponOntDevInfoEntry 7}
        
   zxGponOntDevInfoRealOnuId OBJECT-TYPE
        SYNTAX      INTEGER
        MAX-ACCESS  read-only
        STATUS      current
        DESCRIPTION
            ""
        ::= { zxGponOntDevInfoEntry 8}
          
   zxGponOntPmStatisRealtimeInfoTable OBJECT-TYPE
        SYNTAX      SEQUENCE OF ZxGponOntPmStatisRealtimeInfoEntry
        MAX-ACCESS  not-accessible
        STATUS      current
        DESCRIPTION
            "" 
        REFERENCE
            "G.984.3"
        ::= { zxGponPrivateOnu 6 }

    zxGponOntPmStatisRealtimeInfoEntry OBJECT-TYPE
        SYNTAX      ZxGponOntPmStatisRealtimeInfoEntry
        MAX-ACCESS  not-accessible
        STATUS      current
        DESCRIPTION
            ""
        INDEX   { zxGponMgmtPonOltId, zxGponMgmtPonOnuId }
        ::= { zxGponOntPmStatisRealtimeInfoTable 1 }

    ZxGponOntPmStatisRealtimeInfoEntry ::=
        SEQUENCE {
            zxGponOntPmStatisInfoCorrectNonIdleGemFramesUpstream     Unsigned32,
            zxGponOntPmStatisInfoCorrectIdleGemFramesUpstream        Unsigned32,
            zxGponOntPmStatisInfoErroredGemFramesUpstream            Unsigned32,
            zxGponOntPmStatisInfoGemPayloadBytesUpstream             Unsigned32,
            zxGponOntPmStatisInfoCorrectEthernetFramesUpstream       Unsigned32,
            zxGponOntPmStatisInfoErroredEthernetFramesUpstream       Unsigned32,
            zxGponOntPmStatisInfoTotalOmciFramesUpstream             Unsigned32,
            zxGponOntPmStatisInfoERRi                                Unsigned32,
            zxGponOntPmStatisInfoREIi                                Unsigned32,
            zxGponOntPmStatisInfoUnreceivedBurstsUpstream            Unsigned32,
            zxGponOntPmStatisInfoBipErrorUpstream                    Unsigned32,
            zxGponOntPmStatisInfoCorrectedBitsUpstream               Unsigned32,
            zxGponOntPmStatisInfoNotCorrectedWordsUpstream           Unsigned32,
            zxGponOntPmStatisInfoLostBurst                           Unsigned32,
            zxGponOntTxCorrectNonIdleGemFrms                         Unsigned32,
            zxGponOntTxCorrectIdleGemFrms                            Unsigned32,
            zxGponOntTxOmciFrms                                      Unsigned32,
            zxGponOntTxPloamFrms                                     Unsigned32,
            zxGponOntRxPloamFrms                                     Unsigned32,
            zxGponOntLofiAlarms                                      Unsigned32,
            zxGponOntPmFecCorrectedBytes                             Unsigned32,
            zxGponOntPmFecCorrectedWords                             Unsigned32,
            zxGponOntPmFecUncorrectedWords                           Unsigned32,
            zxGponOntPmFecTotalRxWords                               Unsigned32,
            zxGponOntPmBipErrBits                                    Unsigned32,
            zxGponOntPmCrcErrPkts                                    Unsigned32
        }

   zxGponOntPmStatisInfoCorrectNonIdleGemFramesUpstream OBJECT-TYPE
        SYNTAX      Unsigned32
        MAX-ACCESS  read-only
        STATUS      current
        DESCRIPTION
            ""
        ::= { zxGponOntPmStatisRealtimeInfoEntry 1}

   zxGponOntPmStatisInfoCorrectIdleGemFramesUpstream OBJECT-TYPE
        SYNTAX      Unsigned32
        MAX-ACCESS  read-only
        STATUS      current
        DESCRIPTION
            ""
        ::= { zxGponOntPmStatisRealtimeInfoEntry 2}

   zxGponOntPmStatisInfoErroredGemFramesUpstream OBJECT-TYPE
        SYNTAX      Unsigned32
        MAX-ACCESS  read-only
        STATUS      current
        DESCRIPTION
            ""
        ::= { zxGponOntPmStatisRealtimeInfoEntry 3}

   zxGponOntPmStatisInfoGemPayloadBytesUpstream OBJECT-TYPE
        SYNTAX      Unsigned32
        MAX-ACCESS  read-only
        STATUS      current
        DESCRIPTION
            ""
        ::= { zxGponOntPmStatisRealtimeInfoEntry 4}

   zxGponOntPmStatisInfoCorrectEthernetFramesUpstream OBJECT-TYPE
        SYNTAX      Unsigned32
        MAX-ACCESS  read-only
        STATUS      current
        DESCRIPTION
            ""
        ::= { zxGponOntPmStatisRealtimeInfoEntry 5}

   zxGponOntPmStatisInfoErroredEthernetFramesUpstream OBJECT-TYPE
        SYNTAX      Unsigned32
        MAX-ACCESS  read-only
        STATUS      current
        DESCRIPTION
            ""
        ::= { zxGponOntPmStatisRealtimeInfoEntry 6}

   zxGponOntPmStatisInfoTotalOmciFramesUpstream OBJECT-TYPE
        SYNTAX      Unsigned32
        MAX-ACCESS  read-only
        STATUS      current
        DESCRIPTION
            ""
        ::= { zxGponOntPmStatisRealtimeInfoEntry 7}

   zxGponOntPmStatisInfoERRi OBJECT-TYPE
        SYNTAX      Unsigned32
        MAX-ACCESS  read-only
        STATUS      current
        DESCRIPTION
            ""
        ::= { zxGponOntPmStatisRealtimeInfoEntry 8}

   zxGponOntPmStatisInfoREIi OBJECT-TYPE
        SYNTAX      Unsigned32
        MAX-ACCESS  read-only
        STATUS      current
        DESCRIPTION
            ""
        ::= { zxGponOntPmStatisRealtimeInfoEntry 9}

   zxGponOntPmStatisInfoUnreceivedBurstsUpstream OBJECT-TYPE
        SYNTAX      Unsigned32
        MAX-ACCESS  read-only
        STATUS      current
        DESCRIPTION
            ""
        ::= { zxGponOntPmStatisRealtimeInfoEntry 10}

   zxGponOntPmStatisInfoBipErrorUpstream OBJECT-TYPE
        SYNTAX      Unsigned32
        MAX-ACCESS  read-only
        STATUS      current
        DESCRIPTION
            ""
        ::= { zxGponOntPmStatisRealtimeInfoEntry 11}

   zxGponOntPmStatisInfoCorrectedBitsUpstream OBJECT-TYPE
        SYNTAX      Unsigned32
        MAX-ACCESS  read-only
        STATUS      current
        DESCRIPTION
            ""
        ::= { zxGponOntPmStatisRealtimeInfoEntry 12}

   zxGponOntPmStatisInfoNotCorrectedWordsUpstream OBJECT-TYPE
        SYNTAX      Unsigned32
        MAX-ACCESS  read-only
        STATUS      current
        DESCRIPTION
            ""
        ::= { zxGponOntPmStatisRealtimeInfoEntry 13}

   zxGponOntPmStatisInfoLostBurst OBJECT-TYPE
        SYNTAX      Unsigned32
        MAX-ACCESS  read-only
        STATUS      current
        DESCRIPTION
            ""
        ::= { zxGponOntPmStatisRealtimeInfoEntry 14}
        
   zxGponOntTxCorrectNonIdleGemFrms OBJECT-TYPE
        SYNTAX      Unsigned32
        MAX-ACCESS  read-only
        STATUS      current
        DESCRIPTION
            "OLT sent to ONU correct non-idle GEM frames."
        ::= { zxGponOntPmStatisRealtimeInfoEntry 15}
        
   zxGponOntTxCorrectIdleGemFrms OBJECT-TYPE
        SYNTAX      Unsigned32
        MAX-ACCESS  read-only
        STATUS      current
        DESCRIPTION
            "OLT sent to ONU correct idle GEM frames."
        ::= { zxGponOntPmStatisRealtimeInfoEntry 16}
        
   zxGponOntTxOmciFrms OBJECT-TYPE
        SYNTAX      Unsigned32
        MAX-ACCESS  read-only
        STATUS      current
        DESCRIPTION
            "OLT sent to ONU OMCI frames."
        ::= { zxGponOntPmStatisRealtimeInfoEntry 17}
        
   zxGponOntTxPloamFrms OBJECT-TYPE
        SYNTAX      Unsigned32
        MAX-ACCESS  read-only
        STATUS      current
        DESCRIPTION
            "OLT sent to ONU Ploam frames."
        ::= { zxGponOntPmStatisRealtimeInfoEntry 18}
        
   zxGponOntRxPloamFrms OBJECT-TYPE
        SYNTAX      Unsigned32
        MAX-ACCESS  read-only
        STATUS      current
        DESCRIPTION
            "OLT received from ONU Ploam frames."
        ::= { zxGponOntPmStatisRealtimeInfoEntry 19}
        
   zxGponOntLofiAlarms OBJECT-TYPE
        SYNTAX      Unsigned32
        MAX-ACCESS  read-only
        STATUS      current
        DESCRIPTION
            "The real time statistics of lofi alarm times."
        ::= { zxGponOntPmStatisRealtimeInfoEntry 20}
        
   zxGponOntPmFecCorrectedBytes OBJECT-TYPE
        SYNTAX      Unsigned32
        MAX-ACCESS  read-only
        STATUS      current
        DESCRIPTION
            "Errored bytes which have been corrected by FEC on ONU side."
        ::= { zxGponOntPmStatisRealtimeInfoEntry 21}
    
   zxGponOntPmFecCorrectedWords OBJECT-TYPE
        SYNTAX      Unsigned32
        MAX-ACCESS  read-only
        STATUS      current
        DESCRIPTION
            "Errored codewords which have been corrected by FEC on ONU side."
        ::= { zxGponOntPmStatisRealtimeInfoEntry 22}
        
   zxGponOntPmFecUncorrectedWords OBJECT-TYPE
        SYNTAX      Unsigned32
        MAX-ACCESS  read-only
        STATUS      current
        DESCRIPTION
          "Errored codewords which haven't been corrected by FEC on ONU side."
        ::= { zxGponOntPmStatisRealtimeInfoEntry 23}

   zxGponOntPmFecTotalRxWords OBJECT-TYPE
        SYNTAX      Unsigned32
        MAX-ACCESS  read-only
        STATUS      current
        DESCRIPTION
            "Received codewords by FEC on ONU side."
        ::= { zxGponOntPmStatisRealtimeInfoEntry 24}
        
   zxGponOntPmBipErrBits OBJECT-TYPE
        SYNTAX      Unsigned32
        MAX-ACCESS  read-only
        STATUS      current
        DESCRIPTION
            "Errored bits by BIP on ONU side."
        ::= { zxGponOntPmStatisRealtimeInfoEntry 25}
        
   zxGponOntPmCrcErrPkts OBJECT-TYPE
        SYNTAX      Unsigned32
        MAX-ACCESS  read-only
        STATUS      current
        DESCRIPTION
            "Errored packets by CRC on ONU side."
        ::= { zxGponOntPmStatisRealtimeInfoEntry 26}
                                     
   zxGponOntPmStatisHistoryInfoTable OBJECT-TYPE
        SYNTAX      SEQUENCE OF ZxGponOntPmStatisHistoryInfoEntry
        MAX-ACCESS  not-accessible
        STATUS      current
        DESCRIPTION
            "" 
        REFERENCE
            "G.984.3"
        ::= { zxGponPrivateOnu 7 }

    zxGponOntPmStatisHistoryInfoEntry OBJECT-TYPE
        SYNTAX      ZxGponOntPmStatisHistoryInfoEntry
        MAX-ACCESS  not-accessible
        STATUS      current
        DESCRIPTION
            ""
        INDEX   { zxGponMgmtPonOltId, zxGponMgmtPonOnuId }
        ::= { zxGponOntPmStatisHistoryInfoTable 1 }

    ZxGponOntPmStatisHistoryInfoEntry ::=
        SEQUENCE {
            zxGponOntPmStatisHistoryInfoCorrectNonIdleGemFramesUpstream      Unsigned32,
            zxGponOntPmStatisHistoryInfoCorrectIdleGemFramesUpstream         Unsigned32,
            zxGponOntPmStatisHistoryInfoErroredGemFramesUpstream             Unsigned32,
            zxGponOntPmStatisHistoryInfoGemPayloadBytesUpstream              Unsigned32,
            zxGponOntPmStatisHistoryInfoCorrectEthernetFramesUpstream        Unsigned32,
            zxGponOntPmStatisHistoryInfoErroredEthernetFramesUpstream        Unsigned32,
            zxGponOntPmStatisHistoryInfoTotalOmciFramesUpstream              Unsigned32,
            zxGponOntPmStatisHistoryInfoERRi                                 Unsigned32,
            zxGponOntPmStatisHistoryInfoREIi                                 Unsigned32,
            zxGponOntPmStatisHistoryInfoUnreceivedBurstsUpstream             Unsigned32,
            zxGponOntPmStatisHistoryInfoBipErrorUpstream                     Unsigned32,
            zxGponOntPmStatisHistoryInfoCorrectedBitsUpstream                Unsigned32,
            zxGponOntPmStatisHistoryInfoNotCorrectedWordsUpstream            Unsigned32,
            zxGponOntPmStatisHistoryInfoLostBurst                            Unsigned32,
            zxGponOntTxHisCrctNonIdleGemFrms                   Unsigned32,
            zxGponOntTxHisCrctIdleGemFrms                      Unsigned32,
            zxGponOntTxHisOmciFrms                             Unsigned32,
            zxGponOntTxHisPloamFrms                            Unsigned32,
            zxGponOntRxHisPloamFrms                            Unsigned32,
            zxGponOntHisLofiAlarms                             Unsigned32
        }

   zxGponOntPmStatisHistoryInfoCorrectNonIdleGemFramesUpstream OBJECT-TYPE
        SYNTAX      Unsigned32
        MAX-ACCESS  read-only
        STATUS      current
        DESCRIPTION
            ""
        ::= { zxGponOntPmStatisHistoryInfoEntry 1}

   zxGponOntPmStatisHistoryInfoCorrectIdleGemFramesUpstream OBJECT-TYPE
        SYNTAX      Unsigned32
        MAX-ACCESS  read-only
        STATUS      current
        DESCRIPTION
            ""
        ::= { zxGponOntPmStatisHistoryInfoEntry 2}

   zxGponOntPmStatisHistoryInfoErroredGemFramesUpstream OBJECT-TYPE
        SYNTAX      Unsigned32
        MAX-ACCESS  read-only
        STATUS      current
        DESCRIPTION
            ""
        ::= { zxGponOntPmStatisHistoryInfoEntry 3}

   zxGponOntPmStatisHistoryInfoGemPayloadBytesUpstream OBJECT-TYPE
        SYNTAX      Unsigned32
        MAX-ACCESS  read-only
        STATUS      current
        DESCRIPTION
            ""
        ::= { zxGponOntPmStatisHistoryInfoEntry 4}

   zxGponOntPmStatisHistoryInfoCorrectEthernetFramesUpstream OBJECT-TYPE
        SYNTAX      Unsigned32
        MAX-ACCESS  read-only
        STATUS      current
        DESCRIPTION
            ""
        ::= { zxGponOntPmStatisHistoryInfoEntry 5}

   zxGponOntPmStatisHistoryInfoErroredEthernetFramesUpstream OBJECT-TYPE
        SYNTAX      Unsigned32
        MAX-ACCESS  read-only
        STATUS      current
        DESCRIPTION
            ""
        ::= { zxGponOntPmStatisHistoryInfoEntry 6}

   zxGponOntPmStatisHistoryInfoTotalOmciFramesUpstream OBJECT-TYPE
        SYNTAX      Unsigned32
        MAX-ACCESS  read-only
        STATUS      current
        DESCRIPTION
            ""
        ::= { zxGponOntPmStatisHistoryInfoEntry 7}

   zxGponOntPmStatisHistoryInfoERRi OBJECT-TYPE
        SYNTAX      Unsigned32
        MAX-ACCESS  read-only
        STATUS      current
        DESCRIPTION
            ""
        ::= { zxGponOntPmStatisHistoryInfoEntry 8}

   zxGponOntPmStatisHistoryInfoREIi OBJECT-TYPE
        SYNTAX      Unsigned32
        MAX-ACCESS  read-only
        STATUS      current
        DESCRIPTION
            ""
        ::= { zxGponOntPmStatisHistoryInfoEntry 9}

   zxGponOntPmStatisHistoryInfoUnreceivedBurstsUpstream OBJECT-TYPE
        SYNTAX      Unsigned32
        MAX-ACCESS  read-only
        STATUS      current
        DESCRIPTION
            ""
        ::= { zxGponOntPmStatisHistoryInfoEntry 10}

   zxGponOntPmStatisHistoryInfoBipErrorUpstream OBJECT-TYPE
        SYNTAX      Unsigned32
        MAX-ACCESS  read-only
        STATUS      current
        DESCRIPTION
            ""
        ::= { zxGponOntPmStatisHistoryInfoEntry 11}

   zxGponOntPmStatisHistoryInfoCorrectedBitsUpstream OBJECT-TYPE
        SYNTAX      Unsigned32
        MAX-ACCESS  read-only
        STATUS      current
        DESCRIPTION
            ""
        ::= { zxGponOntPmStatisHistoryInfoEntry 12}

   zxGponOntPmStatisHistoryInfoNotCorrectedWordsUpstream OBJECT-TYPE
        SYNTAX      Unsigned32
        MAX-ACCESS  read-only
        STATUS      current
        DESCRIPTION
            ""
        ::= { zxGponOntPmStatisHistoryInfoEntry 13}
        
   zxGponOntPmStatisHistoryInfoLostBurst OBJECT-TYPE
        SYNTAX      Unsigned32
        MAX-ACCESS  read-only
        STATUS      current
        DESCRIPTION
            ""
        ::= { zxGponOntPmStatisHistoryInfoEntry 14}
        
   zxGponOntTxHisCrctNonIdleGemFrms OBJECT-TYPE
        SYNTAX      Unsigned32
        MAX-ACCESS  read-only
        STATUS      current
        DESCRIPTION
            "OLT sent to ONU historical correct non-idle GEM frames." 
        ::= { zxGponOntPmStatisHistoryInfoEntry 15}
        
   zxGponOntTxHisCrctIdleGemFrms OBJECT-TYPE
        SYNTAX      Unsigned32
        MAX-ACCESS  read-only
        STATUS      current
        DESCRIPTION
            "OLT sent to ONU historical correct idle GEM frames."
        ::= { zxGponOntPmStatisHistoryInfoEntry 16}
        
   zxGponOntTxHisOmciFrms OBJECT-TYPE
        SYNTAX      Unsigned32
        MAX-ACCESS  read-only
        STATUS      current
        DESCRIPTION
            "OLT sent to ONU historical OMCI frames."
        ::= { zxGponOntPmStatisHistoryInfoEntry 17}
        
   zxGponOntTxHisPloamFrms OBJECT-TYPE
        SYNTAX      Unsigned32
        MAX-ACCESS  read-only
        STATUS      current
        DESCRIPTION
            "OLT sent to ONU historical Ploam frames."
        ::= { zxGponOntPmStatisHistoryInfoEntry 18}
        
   zxGponOntRxHisPloamFrms OBJECT-TYPE
        SYNTAX      Unsigned32
        MAX-ACCESS  read-only
        STATUS      current
        DESCRIPTION
            "OLT received from ONU historical Ploam frames."
        ::= { zxGponOntPmStatisHistoryInfoEntry 19}
        
   zxGponOntHisLofiAlarms OBJECT-TYPE
        SYNTAX      Unsigned32
        MAX-ACCESS  read-only
        STATUS      current
        DESCRIPTION
            "The historical statistics of LOFi alarm times."
        ::= { zxGponOntPmStatisHistoryInfoEntry 20}
   
   zxGponOntBpInfoTable OBJECT-TYPE
        SYNTAX      SEQUENCE OF ZxGponOntBpInfoEntry
        MAX-ACCESS  not-accessible
        STATUS      current
        DESCRIPTION
            "" 
        REFERENCE
            ""
        ::= { zxGponPrivateOnu 10 }

    zxGponOntBpInfoEntry OBJECT-TYPE
        SYNTAX      ZxGponOntBpInfoEntry
        MAX-ACCESS  not-accessible
        STATUS      current
        DESCRIPTION
            ""
        INDEX   {zxGponMgmtPonOltId, zxGponMgmtPonOnuId,zxGponMgmtPonOnuBpIndex}
        ::= { zxGponOntBpInfoTable 1 }

    ZxGponOntBpInfoEntry ::=
        SEQUENCE {
            zxGponMgmtPonOnuBpIndex          INTEGER,
            zxGponOntBpName                  OCTET STRING,
            zxGponMgmtPonOnuBpMapType        INTEGER,
            zxGponOntBpInfotEntryStatus      RowStatus
        }
   
   zxGponMgmtPonOnuBpIndex OBJECT-TYPE
        SYNTAX      INTEGER(1..256)
        MAX-ACCESS  read-only
        STATUS      current
        DESCRIPTION
            "An arbitrary(unique) integer for identifiying an entry
             in the table, from 1 to 256."
        ::= { zxGponOntBpInfoEntry 1}
        
    zxGponOntBpName OBJECT-TYPE
        SYNTAX      OCTET STRING(SIZE(0..128))
        MAX-ACCESS  read-write
        STATUS      current
        DESCRIPTION
            ""
        ::= { zxGponOntBpInfoEntry 2}
        
   zxGponMgmtPonOnuBpMapType OBJECT-TYPE
        SYNTAX      INTEGER{
                                cos(1),
                    vlan(2),
                    cosPlusVlan(3),
                    oneToOne(4)
                    }
        MAX-ACCESS  read-write
        STATUS      current
        DESCRIPTION
            "1:cos 2:vlan 3:cos+vlan 4: 1:1"
        ::= { zxGponOntBpInfoEntry 3}
   
   zxGponOntBpInfotEntryStatus OBJECT-TYPE
        SYNTAX      RowStatus
        MAX-ACCESS  read-create
        STATUS      current
        DESCRIPTION
            ""
        ::= { zxGponOntBpInfoEntry 4}

zxGponOntBpMapInfoTable OBJECT-TYPE
        SYNTAX      SEQUENCE OF ZxGponOntBpMapInfoEntry
        MAX-ACCESS  not-accessible
        STATUS      current
        DESCRIPTION
            "" 
        REFERENCE
            ""
        ::= { zxGponPrivateOnu 11 }

    zxGponOntBpMapInfoEntry OBJECT-TYPE
        SYNTAX      ZxGponOntBpMapInfoEntry
        MAX-ACCESS  not-accessible
        STATUS      current
        DESCRIPTION
            ""
        INDEX   {zxGponMgmtPonOltId, zxGponMgmtPonOnuId,zxGponMgmtPonOnuBpIndex,zxGponBpMapGemPortIdx}
        ::= { zxGponOntBpMapInfoTable 1 }

    ZxGponOntBpMapInfoEntry ::=
        SEQUENCE {
                zxGponBpMapGemPortIdx                    INTEGER,    
            zxGponOntBpMapInfoCos          INTEGER,
            zxGponOntBpMapInfoVlanId       VlanId,
            zxGponOntBpMapInfotEntryStatus         RowStatus
        }
   
   zxGponBpMapGemPortIdx OBJECT-TYPE
        SYNTAX      INTEGER(1..256)
        MAX-ACCESS  not-accessible
        STATUS      current
        DESCRIPTION
            "It is equal to the 'zxGponGemPortIdx' of 'zxGponGemPortTable'."
        ::= { zxGponOntBpMapInfoEntry 1}
   zxGponOntBpMapInfoCos OBJECT-TYPE
        SYNTAX      INTEGER(0..7)
        MAX-ACCESS  read-write
        STATUS      current
        DESCRIPTION
            "a cos value(0..7) referenced by a gemport mapped to a Bp."
        ::= { zxGponOntBpMapInfoEntry 2}
   zxGponOntBpMapInfoVlanId OBJECT-TYPE
        SYNTAX      VlanId
        MAX-ACCESS  read-write
        STATUS      current
        DESCRIPTION
             "a vlanid(1..4094) value referenced by a gemport mapped to a Bp."
        ::= { zxGponOntBpMapInfoEntry 3}
   zxGponOntBpMapInfotEntryStatus OBJECT-TYPE
        SYNTAX      RowStatus
        MAX-ACCESS  read-create
        STATUS      current
        DESCRIPTION
            ""
        ::= { zxGponOntBpMapInfoEntry 4}
        
   zxGponVportStatInfoTable OBJECT-TYPE
        SYNTAX      SEQUENCE OF ZxGponVportStatInfoEntry
        MAX-ACCESS  not-accessible
        STATUS      current
        DESCRIPTION
            "" 
        REFERENCE
            "G.984.3"
        ::= { zxGponPrivateOnu 12 }
            

    zxGponVportStatInfoEntry OBJECT-TYPE
        SYNTAX      ZxGponVportStatInfoEntry
        MAX-ACCESS  not-accessible
        STATUS      current
        DESCRIPTION
            ""
        INDEX   { zxGponMgmtPonOltId, zxGponMgmtPonOnuId, zxGponVportId,zxGponVportStatMode, zxGponVportStatInstance }
        ::= { zxGponVportStatInfoTable 1 }

    ZxGponVportStatInfoEntry ::=
        SEQUENCE {
            zxGponVportId                                          Unsigned32,
            zxGponVportStatMode                                    INTEGER,
            zxGponVportStatInstance                                Unsigned32,
            zxGponVportStatInfoPassedPktsUpstream                  Counter64,
            zxGponVportStatInfoDropPktsUpstream                    Counter64,
            zxGponVportStatInfoPassedPktsDownstream                Counter64,
            zxGponVportStatInfoDropPktsDownstream                  Counter64,
            zxGponVportStatInfoPassedBcPktsDownstream              Counter64,
            zxGponVportStatInfoDropBcPktsDownstream                Counter64
        }

   zxGponVportId OBJECT-TYPE
        SYNTAX      Unsigned32
        MAX-ACCESS  read-only
        STATUS      current
        DESCRIPTION
            "an vport in an onu, from 1 to M."
        ::= { zxGponVportStatInfoEntry 1}
        
   zxGponVportStatMode OBJECT-TYPE
        SYNTAX      INTEGER{
                    gemport(0),
                    vlan(1),
                    none(2)
                    }
        MAX-ACCESS  read-only
        STATUS      current
        DESCRIPTION
            ""
        ::= { zxGponVportStatInfoEntry 2}
        
   zxGponVportStatInstance OBJECT-TYPE
        SYNTAX      Unsigned32
        MAX-ACCESS  read-only
        STATUS      current
        DESCRIPTION
            "According to statistic mode, it menas a gemport or a vlan id."
        ::= { zxGponVportStatInfoEntry 3}
        
   zxGponVportStatInfoPassedPktsUpstream OBJECT-TYPE
        SYNTAX      Counter64
        MAX-ACCESS  read-only
        STATUS      current
        DESCRIPTION
            ""
        ::= { zxGponVportStatInfoEntry 4}
        
   zxGponVportStatInfoDropPktsUpstream OBJECT-TYPE
        SYNTAX      Counter64
        MAX-ACCESS  read-only
        STATUS      current
        DESCRIPTION
            ""
        ::= { zxGponVportStatInfoEntry 5}
        
   zxGponVportStatInfoPassedPktsDownstream OBJECT-TYPE
        SYNTAX      Counter64
        MAX-ACCESS  read-only
        STATUS      current
        DESCRIPTION
            ""
        ::= { zxGponVportStatInfoEntry 6}
        
   zxGponVportStatInfoDropPktsDownstream OBJECT-TYPE
        SYNTAX      Counter64
        MAX-ACCESS  read-only
        STATUS      current
        DESCRIPTION
            ""
        ::= { zxGponVportStatInfoEntry 7}
        
   zxGponVportStatInfoPassedBcPktsDownstream OBJECT-TYPE
        SYNTAX      Counter64
        MAX-ACCESS  read-only
        STATUS      current
        DESCRIPTION
            ""
        ::= { zxGponVportStatInfoEntry 8}
        
   zxGponVportStatInfoDropBcPktsDownstream OBJECT-TYPE
        SYNTAX      Counter64
        MAX-ACCESS  read-only
        STATUS      current
        DESCRIPTION
            ""
        ::= { zxGponVportStatInfoEntry 9}

--zxGponServiceMgmt.mi2
    zxGponServiceMgmt OBJECT IDENTIFIER ::= { zxGponRootMib 30 }

    zxOnuTrafficMgmtUnitTable OBJECT-TYPE
        SYNTAX      SEQUENCE OF ZxOnuTrafficMgmtUnitEntry
        MAX-ACCESS  not-accessible
        STATUS      current
        DESCRIPTION
            "This table represents ONU's traffic management unit information including T-CONT and
            user bandwidth management unit."
        ::= { zxGponServiceMgmt 1 }

    zxOnuTrafficMgmtUnitEntry OBJECT-TYPE
        SYNTAX      ZxOnuTrafficMgmtUnitEntry
        MAX-ACCESS  not-accessible
        STATUS      current
        DESCRIPTION
            "It is entry in the zxOnuTrafficMgmtUnitTable."
        INDEX   { zxGponMgmtPonOltId, zxGponMgmtPonOnuId, zxOnuTrafficMgmtUnitTcontIdx }
        ::= { zxOnuTrafficMgmtUnitTable 1 }

    ZxOnuTrafficMgmtUnitEntry ::=
        SEQUENCE {
            zxOnuTrafficMgmtUnitTcontIdx          INTEGER,
            zxOnuTrafficMgmtUnitName              ZxGponRecordName,
            zxOnuTrafficMgmtUnitTcontUpBWIdxPtr   INTEGER,
            zxOnuTrafficMgmtUnitAllocId           INTEGER,
            zxOnuTrafficMgmtUnitUsedPortIdNum     INTEGER,
            zxOnuTrafficMgmtUnitUsedFlowNum       INTEGER,
            zxOnuTrafficMgmtUnitUsedCos           INTEGER,
            zxOnuTrafficMgmtUnitEntryStatus       RowStatus,
            zxOnuTrafficMgmtUnitDbaGapMode        INTEGER
            
        }

    zxOnuTrafficMgmtUnitTcontIdx OBJECT-TYPE
        SYNTAX      INTEGER
        MAX-ACCESS  not-accessible
        STATUS      current
        DESCRIPTION
            "An arbitrary(unique) integer for identifiying an entry
             in the table, from 1 to N."
        ::= { zxOnuTrafficMgmtUnitEntry 1}

    zxOnuTrafficMgmtUnitName       OBJECT-TYPE
      SYNTAX      ZxGponRecordName(SIZE (0..64))
      MAX-ACCESS  read-write
      STATUS      current 
      DESCRIPTION 
         "The white space can't be included in the name."
      REFERENCE   "N/A"
      ::= { zxOnuTrafficMgmtUnitEntry 2 }

    zxOnuTrafficMgmtUnitTcontUpBWIdxPtr       OBJECT-TYPE
      SYNTAX      INTEGER
      MAX-ACCESS  read-write
      STATUS      current 
      DESCRIPTION 
        "This attribute is the index of templet used by T-CONT BW configuration."
      REFERENCE   "N/A"
      ::= { zxOnuTrafficMgmtUnitEntry 3 }

    zxOnuTrafficMgmtUnitAllocId       OBJECT-TYPE
      SYNTAX      INTEGER
      MAX-ACCESS  read-write
      STATUS      current 
      DESCRIPTION 
        "This attribute is the allocid of tcont,value range is [256..4095]."
      REFERENCE   "N/A"
      ::= { zxOnuTrafficMgmtUnitEntry 4 }
      
    zxOnuTrafficMgmtUnitUsedPortIdNum     OBJECT-TYPE
      SYNTAX      INTEGER
      MAX-ACCESS  read-only
      STATUS      current 
      DESCRIPTION 
        "The number of portId using this BW management unit."
      REFERENCE   "N/A"
      ::= { zxOnuTrafficMgmtUnitEntry 5 }
      
    zxOnuTrafficMgmtUnitUsedFlowNum     OBJECT-TYPE
      SYNTAX      INTEGER
      MAX-ACCESS  read-only
      STATUS      current 
      DESCRIPTION 
        "The number of flow using this BW management unit."
      REFERENCE   "N/A"
      ::= { zxOnuTrafficMgmtUnitEntry 6 }

    zxOnuTrafficMgmtUnitUsedCos     OBJECT-TYPE
      SYNTAX      INTEGER
      MAX-ACCESS  read-only
      STATUS      current 
      DESCRIPTION 
        "The integer in binary mode indicates the used COS(0-3)."
      REFERENCE   "N/A"
      ::= { zxOnuTrafficMgmtUnitEntry 7 }
      
    zxOnuTrafficMgmtUnitEntryStatus       OBJECT-TYPE
      SYNTAX      RowStatus
      MAX-ACCESS  read-create
      STATUS      current 
      DESCRIPTION 
        "This entry can be create modified and delete."
      REFERENCE   "N/A"
      ::= { zxOnuTrafficMgmtUnitEntry 8 }
            
    zxOnuTrafficMgmtUnitDbaGapMode OBJECT-TYPE
        SYNTAX     INTEGER{
                   mode1(1),
                   mode2(2),
                   mode3(3),
                   mode4(4)
                   }
        MAX-ACCESS  read-create
        STATUS      current
        DESCRIPTION
            "This attribute specifies the DBA gap mode. 
             For GPON ONU,the explanations of these modes as follows:
               mode1 is one frame, 
               mode2 is two frames, 
               mode3 is four frames, 
               mode4 is eight frames.
             For example,'two frames' indicates that T-CONT will perform DBA 
             in a gap of two data frames.              
             "
        ::= { zxOnuTrafficMgmtUnitEntry 9 }
      

    zxGponGemPortTable OBJECT-TYPE
        SYNTAX      SEQUENCE OF ZxGponGemPortEntry
        MAX-ACCESS  not-accessible
        STATUS      current
        DESCRIPTION
            "This table represents ONU side  configuration."
        ::= { zxGponServiceMgmt 2 }

    zxGponGemPortEntry OBJECT-TYPE
        SYNTAX      ZxGponGemPortEntry
        MAX-ACCESS  not-accessible
        STATUS      current
        DESCRIPTION
            "It is entry in the table zxGponGemPortTable."
        INDEX   { zxGponMgmtPonOltId, zxGponMgmtPonOnuId, zxGponGemPortIdx }
        ::= { zxGponGemPortTable 1 }

    ZxGponGemPortEntry ::=
        SEQUENCE {
            zxGponGemPortIdx               INTEGER,
            zxGponGemPortName              ZxGponRecordName,
            zxGponGemPortType              INTEGER,
            zxGponGemPortTcontIdx          INTEGER,
            zxGponGemPortDirection         INTEGER,
            zxGponGemPortUpTrafficPtr      INTEGER,
            zxGponGemPortDownTrafficPtr    INTEGER,
            zxGponGemPortPortId            INTEGER,
            zxGponGemPortDefaultCosType    INTEGER,
            zxGponGemPortEntryStatus       RowStatus,
            zxGponGemPortEnable            TruthValue,
            zxGponGemPortDownQueueMapId    INTEGER,
            zxGponGemPortUpQueueMapId      INTEGER
        }

    zxGponGemPortIdx OBJECT-TYPE
        SYNTAX      INTEGER
        MAX-ACCESS  not-accessible
        STATUS      current
        DESCRIPTION
            "An arbitrary(unique) integer for identifiying an entry
             in the table. It is the virtual portid index"
        ::= { zxGponGemPortEntry 1}

    zxGponGemPortName       OBJECT-TYPE
      SYNTAX      ZxGponRecordName(SIZE (0..64))
      MAX-ACCESS  read-write
      STATUS      current 
      DESCRIPTION 
        "This attribute specifies the name of the GEM port.
         The white space can't be included in the name."
      REFERENCE   ""
      ::= { zxGponGemPortEntry 2 }

    zxGponGemPortType OBJECT-TYPE
        SYNTAX      INTEGER{
                    unicast(1),
                    multicast(2)
                    }
        MAX-ACCESS  read-write
        STATUS      current
        DESCRIPTION
            "This attribute specifies the type of the GEM port. Only 'unicast' is supported at present."
        ::= { zxGponGemPortEntry 3}

    zxGponGemPortTcontIdx OBJECT-TYPE
        SYNTAX      INTEGER
        MAX-ACCESS  read-write
        STATUS      current
        DESCRIPTION
            "It is equal to the 'zxOnuTrafficMgmtUnitTcontIdx' of 'zxOnuTrafficMgmtUnitTable'."
        ::= { zxGponGemPortEntry 4}

    zxGponGemPortDirection OBJECT-TYPE
        SYNTAX      INTEGER{
                    up(1),
                    down(2),
                    bidirection(3)
                    }
        MAX-ACCESS  read-write
        STATUS      current
        DESCRIPTION
            "This attribute specifies the type of the direction of GEM port. Default value is 'bidirection'."
        ::= { zxGponGemPortEntry 5}

    zxGponGemPortUpTrafficPtr OBJECT-TYPE
        SYNTAX      INTEGER
        MAX-ACCESS  read-write
        STATUS      current
        DESCRIPTION
            "The GEM PORT upstream traffic descriptor profile."
        ::= { zxGponGemPortEntry 6}

    zxGponGemPortDownTrafficPtr OBJECT-TYPE
        SYNTAX      INTEGER
        MAX-ACCESS  read-write
        STATUS      current
        DESCRIPTION
            "The GEM PORT downstream traffic descriptor profile."
        ::= { zxGponGemPortEntry 7}

    zxGponGemPortPortId OBJECT-TYPE
        SYNTAX      INTEGER
        MAX-ACCESS  read-write
        STATUS      current
        DESCRIPTION
            "portid of gemport([65..1023])."
        ::= { zxGponGemPortEntry 8}

    zxGponGemPortDefaultCosType OBJECT-TYPE
        SYNTAX      INTEGER{
                     cos0(1),
                     cos1(2),
                     cos2(3),
                     cos3(4),
                     cos4(5),                     
                     cos5(6),                     
                     cos6(7),
                     cos7(8)
                     }
        MAX-ACCESS  read-write
        STATUS      current
        DESCRIPTION
            "The default COS."
        ::= { zxGponGemPortEntry 9}
        

    zxGponGemPortEntryStatus       OBJECT-TYPE
      SYNTAX      RowStatus
      MAX-ACCESS  read-create
      STATUS      current 
      DESCRIPTION 
        "This entry can be create modified and delete."
      REFERENCE   "N/A"
      ::= { zxGponGemPortEntry 10 }
                              
    zxGponGemPortEnable OBJECT-TYPE
        SYNTAX      TruthValue
        MAX-ACCESS  read-write
        STATUS      current
        DESCRIPTION
            "Active/deactive GEM Port."
        ::= { zxGponGemPortEntry 11}      
    zxGponGemPortDownQueueMapId OBJECT-TYPE
        SYNTAX      INTEGER(0..7)
        MAX-ACCESS  read-write
        STATUS      current
        DESCRIPTION
            "The queue map id."
        ::= { zxGponGemPortEntry 12}    
        
    zxGponGemPortUpQueueMapId OBJECT-TYPE
        SYNTAX      INTEGER(0..1)
        MAX-ACCESS  read-write
        STATUS      current
        DESCRIPTION
            "The queue map id."
        ::= { zxGponGemPortEntry 13}             
   
    zxGponGemPortLimitRateTable OBJECT-TYPE
        SYNTAX      SEQUENCE OF ZxGponGemPortLimitRateEntry
        MAX-ACCESS  not-accessible
        STATUS      current
        DESCRIPTION
            "This table represents ONU gemport limit rate configuration."
        ::= { zxGponServiceMgmt 3 }

    zxGponGemPortLimitRateEntry OBJECT-TYPE
        SYNTAX      ZxGponGemPortLimitRateEntry
        MAX-ACCESS  not-accessible
        STATUS      current
        DESCRIPTION
            "It is entry in the table zxGponGemPortLimitRateTable."
        INDEX   { zxGponMgmtPonOltId, zxGponMgmtPonOnuId, zxGponGemPortIdx }
        ::= { zxGponGemPortLimitRateTable 1 }

    ZxGponGemPortLimitRateEntry ::=
        SEQUENCE {            
            zxGponGemPortLimitUpTrafficPtr      INTEGER,
            zxGponGemPortLimitDownTrafficPtr    INTEGER
        }
   
    
    zxGponGemPortLimitUpTrafficPtr OBJECT-TYPE
        SYNTAX      INTEGER
        MAX-ACCESS  read-write
        STATUS      current
        DESCRIPTION
            "The GEM PORT upstream traffic descriptor profile."
        ::= { zxGponGemPortLimitRateEntry 1}

    zxGponGemPortLimitDownTrafficPtr OBJECT-TYPE
        SYNTAX      INTEGER
        MAX-ACCESS  read-write
        STATUS      current
        DESCRIPTION
            "The GEM PORT downstream traffic descriptor profile."
        ::= { zxGponGemPortLimitRateEntry 2}
           
    zxAnGponOltPerfMgmt         OBJECT IDENTIFIER ::= { zxGponRootMib 31}
    
--------------------------------------------------------------------------------
-- zxGponOltCurrPerfTable
--------------------------------------------------------------------------------
  zxGponOltCurrPerfTable OBJECT-TYPE
        SYNTAX      SEQUENCE OF ZxGponOltCurrPerfEntry
        MAX-ACCESS  not-accessible
        STATUS      current
        DESCRIPTION
            "The current performance data table of GPON OLT." 
        ::= { zxAnGponOltPerfMgmt 1 }

    zxGponOltCurrPerfEntry OBJECT-TYPE
        SYNTAX      ZxGponOltCurrPerfEntry
        MAX-ACCESS  not-accessible
        STATUS      current
        DESCRIPTION
            "An entry in the OLT current performance data table."
        INDEX   { zxGponMgmtPonOltId }
        ::= { zxGponOltCurrPerfTable 1 }

    ZxGponOltCurrPerfEntry ::=
        SEQUENCE {
        zxGponOltCorrNonIdleGemFrmUp    Counter64,
        zxGponOltCorrIdleGemFrmUp       Counter64,
        zxGponOltErroredGemFrmUp        Counter64,
        zxGponOltGemPayloadBytesUp      Counter64,                    
        zxGponOltCorrEtherFrmUp         Counter64,                          
        zxGponOltErroredEtherFrmUp      Counter64,                       
        zxGponOltPerfErr                Counter64,       
        zxGponOltPerfRei                Counter64,       
        zxGponOltValidEtherPktDown      Counter64,                   
        zxGponOltPloamDown              Counter64,
        zxGponOltErroredPloamUp         Counter64,                    
        zxGponOltPloamUp                Counter64,                   
        zxGponOltFecCorrBytes           Counter64,              
        zxGponOltFecCorrWords           Counter64,              
        zxGponOltFecUnCorrWords         Counter64,              
        zxGponOltFecTotalRxWords        Counter64, 
        zxGponOltBipCorrBits            Counter64,
        zxGponOltCrcErrPkts             Counter64,
        zxGponOltPerfCapability         BITS,
        zxGponOltCurrReset              INTEGER              
        }

   zxGponOltCorrNonIdleGemFrmUp OBJECT-TYPE
        SYNTAX      Counter64
        MAX-ACCESS  read-only
        STATUS      current
        DESCRIPTION
            "Performance of upstream correct none idle gemport frames"
        ::= { zxGponOltCurrPerfEntry 1}

   zxGponOltCorrIdleGemFrmUp OBJECT-TYPE
        SYNTAX      Counter64
        MAX-ACCESS  read-only
        STATUS      current
        DESCRIPTION
            "Performance of upstream correct idle gemport frames"
        ::= { zxGponOltCurrPerfEntry 2}

   zxGponOltErroredGemFrmUp OBJECT-TYPE
        SYNTAX      Counter64
        MAX-ACCESS  read-only
        STATUS      current
        DESCRIPTION
            "Performance of upstream errored gemport frames"
        ::= { zxGponOltCurrPerfEntry 3}
        
   zxGponOltGemPayloadBytesUp OBJECT-TYPE
        SYNTAX      Counter64
        MAX-ACCESS  read-only
        STATUS      current
        DESCRIPTION
            "Performance of upstream gemport payload bytes"
        ::= { zxGponOltCurrPerfEntry 4}

   zxGponOltCorrEtherFrmUp OBJECT-TYPE
        SYNTAX      Counter64
        MAX-ACCESS  read-only
        STATUS      current
        DESCRIPTION
            "Performance of upstream correct ethernet frames"
        ::= { zxGponOltCurrPerfEntry 5}

   zxGponOltErroredEtherFrmUp OBJECT-TYPE
        SYNTAX      Counter64
        MAX-ACCESS  read-only
        STATUS      current
        DESCRIPTION
            "Performance of upstream errored ethernet frames"
        ::= { zxGponOltCurrPerfEntry 6}

   zxGponOltPerfErr OBJECT-TYPE
        SYNTAX      Counter64
        MAX-ACCESS  read-only
        STATUS      current
        DESCRIPTION
            "Performance of ERR alarm times"
        ::= { zxGponOltCurrPerfEntry 7}

   zxGponOltPerfRei OBJECT-TYPE
        SYNTAX      Counter64
        MAX-ACCESS  read-only
        STATUS      current
        DESCRIPTION
            "Performance of remote onu error alarm times"
        ::= { zxGponOltCurrPerfEntry 8}

   zxGponOltValidEtherPktDown OBJECT-TYPE
        SYNTAX      Counter64
        MAX-ACCESS  read-only
        STATUS      current
        DESCRIPTION
            "Performance of downstream valid ethernet packets"
        ::= { zxGponOltCurrPerfEntry 9}

   zxGponOltPloamDown OBJECT-TYPE
        SYNTAX      Counter64
        MAX-ACCESS  read-only
        STATUS      current
        DESCRIPTION
            "Performance of downstream ploam messages"
        ::= { zxGponOltCurrPerfEntry 10}

   zxGponOltErroredPloamUp OBJECT-TYPE
        SYNTAX      Counter64
        MAX-ACCESS  read-only
        STATUS      current
        DESCRIPTION
            "Performance of upstream errored ploam messages"
        ::= { zxGponOltCurrPerfEntry 11}
        
   zxGponOltPloamUp OBJECT-TYPE
        SYNTAX      Counter64
        MAX-ACCESS  read-only
        STATUS      current
        DESCRIPTION
            "Performance of upstream ploam messages"
        ::= { zxGponOltCurrPerfEntry 12}
        
   zxGponOltFecCorrBytes OBJECT-TYPE
        SYNTAX      Counter64
        MAX-ACCESS  read-only
        STATUS      current
        DESCRIPTION
            "Error bytes which have been corrected by FEC."
        ::= { zxGponOltCurrPerfEntry 13}
    
   zxGponOltFecCorrWords  OBJECT-TYPE
        SYNTAX      Counter64
        MAX-ACCESS  read-only
        STATUS      current
        DESCRIPTION
            "Error codewords which have been corrected by FEC."
        ::= { zxGponOltCurrPerfEntry 14}
        
    zxGponOltFecUnCorrWords  OBJECT-TYPE
        SYNTAX      Counter64
        MAX-ACCESS  read-only
        STATUS      current
        DESCRIPTION
            "Error codewords which haven't been corrected by FEC."
        ::= { zxGponOltCurrPerfEntry 15}

   zxGponOltFecTotalRxWords OBJECT-TYPE
        SYNTAX      Counter64
        MAX-ACCESS  read-only
        STATUS      current
        DESCRIPTION
            "Received codewords by FEC."
        ::= { zxGponOltCurrPerfEntry 16}
   
   zxGponOltBipCorrBits OBJECT-TYPE
        SYNTAX      Counter64
        MAX-ACCESS  read-only
        STATUS      current
        DESCRIPTION
            "PON Port BIP Corr Bits."
        ::= { zxGponOltCurrPerfEntry 17}      
        
   zxGponOltCrcErrPkts OBJECT-TYPE
        SYNTAX      Counter64
        MAX-ACCESS  read-only
        STATUS      current
        DESCRIPTION
            "Error packets by CRC."
        ::= { zxGponOltCurrPerfEntry 18} 
        
   zxGponOltPerfCapability  OBJECT-TYPE
        SYNTAX      BITS 
           {
               zxGponOltCorrNonIdleGemFrmUp(0),
               zxGponOltCorrIdleGemFrmUp(1),
               zxGponOltErroredGemFrmUp(2),
               zxGponOltGemPayloadBytesUp(3),
               zxGponOltCorrEtherFrmUp(4),
               zxGponOltErroredEtherFrmUp(5),
               zxGponOltPerfErr(6),
               zxGponOltPerfRei(7),
               zxGponOltValidEtherPktDown(8),
               zxGponOltPloamDown(9),
               zxGponOltErroredPloamUp(10),
               zxGponOltPloamUp(11),
               zxGponOltFecCorrBytes(12),
               zxGponOltFecCorrWords(13),
               zxGponOltFecUnCorrWords(14),
               zxGponOltFecTotalRxWords(15),
               zxGponOltBipCorrBits(16),
               zxGponOltCrcErrPkts(17)
           }             
        MAX-ACCESS  read-only
        STATUS      current
        DESCRIPTION
            "The attribute indicates that the supports of GPON OLT performance,
            each bit from left to right represents the support of performance 
            statistic from top to bottom in this MIB table, value 1 represents 
            support and value 0 is not support. 
            And the supports of C15M,C1D,H15M,H1D performance statistics 
            decided by zxGponOltPerfCapability also."
        ::= { zxGponOltCurrPerfEntry 99} 
        
   zxGponOltCurrReset OBJECT-TYPE 
        SYNTAX      INTEGER
            {
                perfReset(1)
            }
        MAX-ACCESS  read-write
        STATUS      current
        DESCRIPTION     
            "Clear all the current performance 
            variables.When get this variable, always return 1."
        ::= { zxGponOltCurrPerfEntry 100 }             
             
--------------------------------------------------------------------------------
-- zxGponOltCurrPerf15MinTable
--------------------------------------------------------------------------------

   zxGponOltCurrPerf15MinTable OBJECT-TYPE
        SYNTAX      SEQUENCE OF ZxGponOltCurrPerf15MinEntry
        MAX-ACCESS  not-accessible
        STATUS      current
        DESCRIPTION
            "The current 15 minutes performance data table of GPON OLT." 
        ::= { zxAnGponOltPerfMgmt 2 }

    zxGponOltCurrPerf15MinEntry OBJECT-TYPE
        SYNTAX      ZxGponOltCurrPerf15MinEntry
        MAX-ACCESS  not-accessible
        STATUS      current
        DESCRIPTION
            "An entry in the OLT current 15 minutes performance data table."
        INDEX   { zxGponMgmtPonOltId }
        ::= { zxGponOltCurrPerf15MinTable 1 }

    ZxGponOltCurrPerf15MinEntry ::=
        SEQUENCE {
        zxGponOltC15MTimeElapsed            Gauge32,
        zxGponOltC15MCorrNonIdleGemFrmUp    Counter64,    
        zxGponOltC15MCorrIdleGemFrmUp    Counter64,
        zxGponOltC15MErroredGemFrmUp        Counter64,
        zxGponOltC15MGemPayloadBytesUp      Counter64,                    
        zxGponOltC15MCorrEtherFrmUp      Counter64,                          
        zxGponOltC15MErroredEtherFrmUp      Counter64,                       
        zxGponOltC15MErr                    Counter64,       
        zxGponOltC15MRei                    Counter64,          
        zxGponOltC15MValidEtherPktDown      Counter64,                   
        zxGponOltC15MPloamDown              Counter64, 
        zxGponOltC15MErroredPloamUp         Counter64,                  
        zxGponOltC15MPloamUp                Counter64,                   
        zxGponOltC15MFecCorrBytes      Counter64,
        zxGponOltC15MFecCorrWords      Counter64,
        zxGponOltC15MFecUnCorrWords      Counter64,
        zxGponOltC15MFecTotalRxWords        Counter64,
        zxGponOltC15MBipCorrBits       Counter64,
        zxGponOltC15MCrcErrPkts             Counter64,
        zxGponOltC15MReset                  INTEGER
        }

    zxGponOltC15MTimeElapsed  OBJECT-TYPE 
        SYNTAX      Gauge32(0..86399)
        UNITS       "seconds"
        MAX-ACCESS  read-only
        STATUS      current
        DESCRIPTION     
            "Number of seconds that have elapsed since the beginning
             of the current 15 minutes interval."     
        ::= { zxGponOltCurrPerf15MinEntry 1 }      
                    
    zxGponOltC15MCorrNonIdleGemFrmUp OBJECT-TYPE
        SYNTAX      Counter64
        MAX-ACCESS  read-only
        STATUS      current
        DESCRIPTION
            "The current 15 minutes interval upstream correct none 
            idle gemport frames"
        ::= { zxGponOltCurrPerf15MinEntry 2}

    zxGponOltC15MCorrIdleGemFrmUp OBJECT-TYPE
        SYNTAX      Counter64
        MAX-ACCESS  read-only
        STATUS      current
        DESCRIPTION
            "The current 15 minutes interval upstream correct
             idle gemport frames"
        ::= { zxGponOltCurrPerf15MinEntry 3}

   zxGponOltC15MErroredGemFrmUp OBJECT-TYPE
        SYNTAX      Counter64
        MAX-ACCESS  read-only
        STATUS      current
        DESCRIPTION
            "The current 15 minutes interval upstream
             errored gemport frames"
        ::= { zxGponOltCurrPerf15MinEntry 4}
        
   zxGponOltC15MGemPayloadBytesUp OBJECT-TYPE
        SYNTAX      Counter64
        MAX-ACCESS  read-only
        STATUS      current
        DESCRIPTION
            "The current 15 minutes interval upstream gemport 
            payload bytes"
        ::= { zxGponOltCurrPerf15MinEntry 5}

   zxGponOltC15MCorrEtherFrmUp OBJECT-TYPE
        SYNTAX      Counter64
        MAX-ACCESS  read-only
        STATUS      current
        DESCRIPTION
            "The current 15 minutes interval upstream correct 
            ethernet frames"
        ::= { zxGponOltCurrPerf15MinEntry 6}

   zxGponOltC15MErroredEtherFrmUp OBJECT-TYPE
        SYNTAX      Counter64
        MAX-ACCESS  read-only
        STATUS      current
        DESCRIPTION
            "The current 15 minutes interval upstream errored 
            ethernet frames"
        ::= { zxGponOltCurrPerf15MinEntry 7}
   
   zxGponOltC15MErr  OBJECT-TYPE 
        SYNTAX      Counter64
        MAX-ACCESS  read-only
        STATUS      current
        DESCRIPTION     
            "The current 15 minutes interval ERR alarm times
             of this interface."
        ::= { zxGponOltCurrPerf15MinEntry 8 }
        
   zxGponOltC15MRei OBJECT-TYPE
        SYNTAX      Counter64
        MAX-ACCESS  read-only
        STATUS      current
        DESCRIPTION
            "The current 15 minutes interval remote onu error
             alarm times of this interface."
        ::= { zxGponOltCurrPerf15MinEntry 9}

   zxGponOltC15MValidEtherPktDown OBJECT-TYPE
        SYNTAX      Counter64
        MAX-ACCESS  read-only
        STATUS      current
        DESCRIPTION
            "The current 15 minutes interval  downstream 
            valid ethernet packets"
        ::= { zxGponOltCurrPerf15MinEntry 10} 

   zxGponOltC15MPloamDown OBJECT-TYPE
        SYNTAX      Counter64
        MAX-ACCESS  read-only
        STATUS      current
        DESCRIPTION
            "The current 15 minutes interval  downstream
             ploam messages"
        ::= { zxGponOltCurrPerf15MinEntry 11}

   zxGponOltC15MErroredPloamUp OBJECT-TYPE
        SYNTAX      Counter64
        MAX-ACCESS  read-only
        STATUS      current
        DESCRIPTION
            "The current 15 minutes interval upstream 
             errored ploam messages"
        ::= { zxGponOltCurrPerf15MinEntry 12}

   zxGponOltC15MPloamUp OBJECT-TYPE
        SYNTAX      Counter64
        MAX-ACCESS  read-only
        STATUS      current
        DESCRIPTION
            "The current 15 minutes interval total
             upstream ploam messages"
        ::= { zxGponOltCurrPerf15MinEntry 13}
   
   zxGponOltC15MFecCorrBytes OBJECT-TYPE
        SYNTAX      Counter64
        MAX-ACCESS  read-only
        STATUS      current
        DESCRIPTION
            "The current 15 minutes interval error bytes 
            which have been corrected by FEC of this interface."
        ::= { zxGponOltCurrPerf15MinEntry 14}

   zxGponOltC15MFecCorrWords OBJECT-TYPE
        SYNTAX      Counter64
        MAX-ACCESS  read-only
        STATUS      current
        DESCRIPTION
            "The current 15 minutes interval error codewords
             which have been corrected by FEC of this interface."
        ::= { zxGponOltCurrPerf15MinEntry 15}

   zxGponOltC15MFecUnCorrWords OBJECT-TYPE
        SYNTAX      Counter64
        MAX-ACCESS  read-only
        STATUS      current
        DESCRIPTION
            "The current 15 minutes interval error codewords
             which haven't been corrected by FEC of this interface."
        ::= { zxGponOltCurrPerf15MinEntry 16}

   zxGponOltC15MFecTotalRxWords OBJECT-TYPE
        SYNTAX      Counter64
        MAX-ACCESS  read-only
        STATUS      current
        DESCRIPTION
            "The current 15 minutes interval received codewords
             by FEC of this interface."
        ::= { zxGponOltCurrPerf15MinEntry 17}
       
   zxGponOltC15MBipCorrBits OBJECT-TYPE
        SYNTAX      Counter64
        MAX-ACCESS  read-only
        STATUS      current
        DESCRIPTION
            "The current 15 minutes interval PON port BIP
             corrected Bits.."
        ::= { zxGponOltCurrPerf15MinEntry 18}      
        
   zxGponOltC15MCrcErrPkts OBJECT-TYPE
        SYNTAX      Counter64
        MAX-ACCESS  read-only
        STATUS      current
        DESCRIPTION
            "The current 15 minutes interval error packets by CRC."
        ::= { zxGponOltCurrPerf15MinEntry 19} 
        
   zxGponOltC15MReset OBJECT-TYPE 
        SYNTAX      INTEGER
            {
                perfReset(1)
            }
        MAX-ACCESS  read-write
        STATUS      current
        DESCRIPTION     
            "Clear all the current 15-minutes performance variables.
            When get this variable, always return 1."
        ::= { zxGponOltCurrPerf15MinEntry 100 } 

--------------------------------------------------------------------------------
-- zxGponOltCurrPerf1DayTable
--------------------------------------------------------------------------------

   zxGponOltCurrPerf1DayTable OBJECT-TYPE
        SYNTAX      SEQUENCE OF ZxGponOltCurrPerf1DayEntry
        MAX-ACCESS  not-accessible
        STATUS      current
        DESCRIPTION
            "The current 1 day performance data table of GPON OLT." 
        ::= { zxAnGponOltPerfMgmt 3 }

    zxGponOltCurrPerf1DayEntry OBJECT-TYPE
        SYNTAX      ZxGponOltCurrPerf1DayEntry
        MAX-ACCESS  not-accessible
        STATUS      current
        DESCRIPTION
            "An entry in the OLT current 1 day performance data table."
        INDEX   { zxGponMgmtPonOltId }
        ::= { zxGponOltCurrPerf1DayTable 1 }

    ZxGponOltCurrPerf1DayEntry ::=
        SEQUENCE {
        zxGponOltC1DTimeElapsed            Gauge32,
        zxGponOltC1DCorrNonIdleGemFrmUp    Counter64,    
        zxGponOltC1DCorrIdleGemFrmUp    Counter64,
        zxGponOltC1DErroredGemFrmUp        Counter64,
        zxGponOltC1DGemPayloadBytesUp      Counter64,                    
        zxGponOltC1DCorrEtherFrmUp      Counter64,                          
        zxGponOltC1DErroredEtherFrmUp      Counter64,                       
        zxGponOltC1DErr                    Counter64,       
        zxGponOltC1DRei                    Counter64,           
        zxGponOltC1DValidEtherPktDown      Counter64,                    
        zxGponOltC1DPloamDown              Counter64, 
        zxGponOltC1DErroredPloamUp         Counter64,                   
        zxGponOltC1DPloamUp                Counter64,                    
        zxGponOltC1DFecCorrBytes      Counter64,
        zxGponOltC1DFecCorrWords      Counter64,
        zxGponOltC1DFecUnCorrWords      Counter64,
        zxGponOltC1DFecTotalRxWords        Counter64,
        zxGponOltC1DBipCorrBits       Counter64,
        zxGponOltC1DCrcErrPkts             Counter64,
        zxGponOltC1DReset                  INTEGER
        }

    zxGponOltC1DTimeElapsed  OBJECT-TYPE 
        SYNTAX      Gauge32(0..86399)
        UNITS       "seconds"
        MAX-ACCESS  read-only
        STATUS      current
        DESCRIPTION     
            "Number of seconds that have elapsed since the beginning
             of the current 1 day interval."     
        ::= { zxGponOltCurrPerf1DayEntry 1 }      
                    
    zxGponOltC1DCorrNonIdleGemFrmUp OBJECT-TYPE
        SYNTAX      Counter64
        MAX-ACCESS  read-only
        STATUS      current
        DESCRIPTION
            "The current 1 day interval upstream correct none 
            idle gemport frames"
        ::= { zxGponOltCurrPerf1DayEntry 2}

    zxGponOltC1DCorrIdleGemFrmUp OBJECT-TYPE
        SYNTAX      Counter64
        MAX-ACCESS  read-only
        STATUS      current
        DESCRIPTION
            "The current 1 day interval upstream correct
             idle gemport frames"
        ::= { zxGponOltCurrPerf1DayEntry 3}

   zxGponOltC1DErroredGemFrmUp OBJECT-TYPE
        SYNTAX      Counter64
        MAX-ACCESS  read-only
        STATUS      current
        DESCRIPTION
            "The current 1 day interval upstream
             errored gemport frames"
        ::= { zxGponOltCurrPerf1DayEntry 4}
        
   zxGponOltC1DGemPayloadBytesUp OBJECT-TYPE
        SYNTAX      Counter64
        MAX-ACCESS  read-only
        STATUS      current
        DESCRIPTION
            "The current 1 day interval upstream gemport 
            payload bytes"
        ::= { zxGponOltCurrPerf1DayEntry 5}

   zxGponOltC1DCorrEtherFrmUp OBJECT-TYPE
        SYNTAX      Counter64
        MAX-ACCESS  read-only
        STATUS      current
        DESCRIPTION
            "The current 1 day interval upstream correct 
            ethernet frames"
        ::= { zxGponOltCurrPerf1DayEntry 6}

   zxGponOltC1DErroredEtherFrmUp OBJECT-TYPE
        SYNTAX      Counter64
        MAX-ACCESS  read-only
        STATUS      current
        DESCRIPTION
            "The current 1 day interval upstream errored 
            ethernet frames"
        ::= { zxGponOltCurrPerf1DayEntry 7}
        
   zxGponOltC1DErr  OBJECT-TYPE 
        SYNTAX      Counter64
        MAX-ACCESS  read-only
        STATUS      current
        DESCRIPTION     
            "The current 1 day interval ERR alarm times
             of this interface."
        ::= { zxGponOltCurrPerf1DayEntry 8 }
        
   zxGponOltC1DRei OBJECT-TYPE
        SYNTAX      Counter64
        MAX-ACCESS  read-only
        STATUS      current
        DESCRIPTION
            "The current 1 day interval remote onu error
             alarm times of this interface."
        ::= { zxGponOltCurrPerf1DayEntry 9}

   zxGponOltC1DValidEtherPktDown OBJECT-TYPE
        SYNTAX      Counter64
        MAX-ACCESS  read-only
        STATUS      current
        DESCRIPTION
            "The current 1 day interval  downstream 
            valid ethernet packets"
        ::= { zxGponOltCurrPerf1DayEntry 10} 

   zxGponOltC1DPloamDown OBJECT-TYPE
        SYNTAX      Counter64
        MAX-ACCESS  read-only
        STATUS      current
        DESCRIPTION
            "The current 1 day interval  downstream
             ploam messages"
        ::= { zxGponOltCurrPerf1DayEntry 11}
   
   zxGponOltC1DErroredPloamUp OBJECT-TYPE
        SYNTAX      Counter64
        MAX-ACCESS  read-only
        STATUS      current
        DESCRIPTION
            "The current 1 day interval errored 
            upstream ploam messages"
        ::= { zxGponOltCurrPerf1DayEntry 12}

   zxGponOltC1DPloamUp OBJECT-TYPE
        SYNTAX      Counter64
        MAX-ACCESS  read-only
        STATUS      current
        DESCRIPTION
            "The current 1 day interval total
            upstream ploam messages"
        ::= { zxGponOltCurrPerf1DayEntry 13}
        
   zxGponOltC1DFecCorrBytes OBJECT-TYPE
        SYNTAX      Counter64
        MAX-ACCESS  read-only
        STATUS      current
        DESCRIPTION
            "The current 1 day interval error bytes 
            which have been corrected by FEC of this interface."
        ::= { zxGponOltCurrPerf1DayEntry 14}

   zxGponOltC1DFecCorrWords OBJECT-TYPE
        SYNTAX      Counter64
        MAX-ACCESS  read-only
        STATUS      current
        DESCRIPTION
            "The current 1 day interval error codewords
             which have been corrected by FEC of this interface."
        ::= { zxGponOltCurrPerf1DayEntry 15}

   zxGponOltC1DFecUnCorrWords OBJECT-TYPE
        SYNTAX      Counter64
        MAX-ACCESS  read-only
        STATUS      current
        DESCRIPTION
            "The current 1 day interval error codewords
             which haven't been corrected by FEC of this interface."
        ::= { zxGponOltCurrPerf1DayEntry 16}

   zxGponOltC1DFecTotalRxWords OBJECT-TYPE
        SYNTAX      Counter64
        MAX-ACCESS  read-only
        STATUS      current
        DESCRIPTION
            "The current 1 day interval received codewords
             by FEC of this interface."
        ::= { zxGponOltCurrPerf1DayEntry 17}
        
   zxGponOltC1DBipCorrBits OBJECT-TYPE
        SYNTAX      Counter64
        MAX-ACCESS  read-only
        STATUS      current
        DESCRIPTION
            "The current 1 day interval PON port BIP
             corrected Bits.."
        ::= { zxGponOltCurrPerf1DayEntry 18}      
        
   zxGponOltC1DCrcErrPkts OBJECT-TYPE
        SYNTAX      Counter64
        MAX-ACCESS  read-only
        STATUS      current
        DESCRIPTION
            "The current 1 day interval error packets by CRC."
        ::= { zxGponOltCurrPerf1DayEntry 19}      
       
   zxGponOltC1DReset OBJECT-TYPE 
        SYNTAX      INTEGER
            {
                perfReset(1)
            }
        MAX-ACCESS  read-write
        STATUS      current
        DESCRIPTION     
            "Clear all the current 1 day performance variables.
            When get this variable, always return 1."
        ::= { zxGponOltCurrPerf1DayEntry 100 } 
                
--------------------------------------------------------------------------------
-- zxGponOltPerf15MinIntervalTable
--------------------------------------------------------------------------------

   zxGponOltPerf15MinIntervalTable OBJECT-TYPE
        SYNTAX      SEQUENCE OF ZxGponOltPerf15MinIntervalEntry
        MAX-ACCESS  not-accessible
        STATUS      current
        DESCRIPTION
            "The 15 minutes interval performance data table of GPON OLT." 
        ::= { zxAnGponOltPerfMgmt 4 }

    zxGponOltPerf15MinIntervalEntry OBJECT-TYPE
        SYNTAX      ZxGponOltPerf15MinIntervalEntry
        MAX-ACCESS  not-accessible
        STATUS      current
        DESCRIPTION
            "An entry in the OLT 15 minutes interval performance data table."
        INDEX   { zxGponMgmtPonOltId, zxGponOltH15MIntervalNumber  }
        ::= { zxGponOltPerf15MinIntervalTable 1 }

    ZxGponOltPerf15MinIntervalEntry ::=
        SEQUENCE {
        zxGponOltH15MIntervalNumber         Integer32,
        zxGponOltH15MDateAndTime            DateAndTime,
        zxGponOltH15MCorrNonIdleGemFrmUp    Counter64,
        zxGponOltH15MCorrIdleGemFrmUp    Counter64,
        zxGponOltH15MErroredGemFrmUp        Counter64,
        zxGponOltH15MGemPayloadBytesUp      Counter64,                    
        zxGponOltH15MCorrEtherFrmUp      Counter64,                          
        zxGponOltH15MErroredEtherFrmUp      Counter64,                                               
        zxGponOltH15MErr                    Counter64,       
        zxGponOltH15MRei                    Counter64,            
        zxGponOltH15MValidEtherPktDown      Counter64,                                     
        zxGponOltH15MPloamDown              Counter64,
        zxGponOltH15MErroredPloamUp         Counter64,                    
        zxGponOltH15MPloamUp                Counter64,                    
        zxGponOltH15MFecCorrBytes      Counter64,
        zxGponOltH15MFecCorrWords      Counter64,
        zxGponOltH15MFecUnCorrWords         Counter64,
        zxGponOltH15MFecTotalRxWords        Counter64,
        zxGponOltH15MBipCorrBits       Counter64,
        zxGponOltH15MCrcErrPkts             Counter64,
        zxGponOltH15MValidData              TruthValue
        }

    zxGponOltH15MIntervalNumber  OBJECT-TYPE 
        SYNTAX      Integer32(1..96)
        MAX-ACCESS  not-accessible
        STATUS      current
        DESCRIPTION     
             "Performance Data Interval.
              
              Interval 1 is the the most recent previous interval; 
              Interval 96 is 24 hours ago.  
              Intervals from 2 to 96 are optional."       
        ::= { zxGponOltPerf15MinIntervalEntry 1 }      
        
    zxGponOltH15MDateAndTime     OBJECT-TYPE   
        SYNTAX      DateAndTime
        MAX-ACCESS  read-only
        STATUS      current
        DESCRIPTION     
             "15min performace data interval create time."       
        ::= { zxGponOltPerf15MinIntervalEntry 2 }            
    
    zxGponOltH15MCorrNonIdleGemFrmUp OBJECT-TYPE
        SYNTAX      Counter64
        MAX-ACCESS  read-only
        STATUS      current
        DESCRIPTION
            "The 15 minutes interval upstream correct none 
            idle gemport frames"
        ::= { zxGponOltPerf15MinIntervalEntry 3}

    zxGponOltH15MCorrIdleGemFrmUp OBJECT-TYPE
        SYNTAX      Counter64
        MAX-ACCESS  read-only
        STATUS      current
        DESCRIPTION
            "The 15 minutes interval upstream correct
             idle gemport frames"
        ::= { zxGponOltPerf15MinIntervalEntry 4}

   zxGponOltH15MErroredGemFrmUp OBJECT-TYPE
        SYNTAX      Counter64
        MAX-ACCESS  read-only
        STATUS      current
        DESCRIPTION
            "The 15 minutes interval upstream
             errored gemport frames"
        ::= { zxGponOltPerf15MinIntervalEntry 5}
   
   zxGponOltH15MGemPayloadBytesUp OBJECT-TYPE
        SYNTAX      Counter64
        MAX-ACCESS  read-only
        STATUS      current
        DESCRIPTION
            "The 15 minutes interval upstream gemport 
            payload bytes"
        ::= { zxGponOltPerf15MinIntervalEntry 6}

   zxGponOltH15MCorrEtherFrmUp OBJECT-TYPE
        SYNTAX      Counter64
        MAX-ACCESS  read-only
        STATUS      current
        DESCRIPTION
            "The 15 minutes interval upstream correct 
            ethernet frames"
        ::= { zxGponOltPerf15MinIntervalEntry 7}

   zxGponOltH15MErroredEtherFrmUp OBJECT-TYPE
        SYNTAX      Counter64
        MAX-ACCESS  read-only
        STATUS      current
        DESCRIPTION
            "The 15 minutes interval upstream errored 
            ethernet frames"
        ::= { zxGponOltPerf15MinIntervalEntry 8}
   
   zxGponOltH15MErr  OBJECT-TYPE 
        SYNTAX      Counter64
        MAX-ACCESS  read-only
        STATUS      current
        DESCRIPTION     
            "The 15 minutes interval ERR alarm times
             of this interface."
        ::= { zxGponOltPerf15MinIntervalEntry 9 }
              
   zxGponOltH15MRei OBJECT-TYPE
        SYNTAX      Counter64
        MAX-ACCESS  read-only
        STATUS      current
        DESCRIPTION
            "The 15 minutes interval remote onu error alarm 
             times of this interface."
        ::= { zxGponOltPerf15MinIntervalEntry 10}
      
   zxGponOltH15MValidEtherPktDown OBJECT-TYPE
        SYNTAX      Counter64
        MAX-ACCESS  read-only
        STATUS      current
        DESCRIPTION
            "The 15 minutes interval  downstream 
            valid ethernet packets"
        ::= { zxGponOltPerf15MinIntervalEntry 11}  

   zxGponOltH15MPloamDown OBJECT-TYPE
        SYNTAX      Counter64
        MAX-ACCESS  read-only
        STATUS      current
        DESCRIPTION
            "The 15 minutes interval  downstream
             ploam messages"
        ::= { zxGponOltPerf15MinIntervalEntry 12}
        
   zxGponOltH15MErroredPloamUp OBJECT-TYPE
        SYNTAX      Counter64
        MAX-ACCESS  read-only
        STATUS      current
        DESCRIPTION
            "The 15 minutes interval errored upstream
             ploam messages"
        ::= { zxGponOltPerf15MinIntervalEntry 13}
        
   zxGponOltH15MPloamUp OBJECT-TYPE
        SYNTAX      Counter64
        MAX-ACCESS  read-only
        STATUS      current
        DESCRIPTION
            "The 15 minutes interval total upstream
             ploam messages"
        ::= { zxGponOltPerf15MinIntervalEntry 14}

   zxGponOltH15MFecCorrBytes OBJECT-TYPE
        SYNTAX      Counter64
        MAX-ACCESS  read-only
        STATUS      current
        DESCRIPTION
            "The 15 minutes interval error bytes which have 
             been corrected by FEC of this interface."
        ::= { zxGponOltPerf15MinIntervalEntry 15}

   zxGponOltH15MFecCorrWords OBJECT-TYPE
        SYNTAX      Counter64
        MAX-ACCESS  read-only
        STATUS      current
        DESCRIPTION
            "The 15 minutes interval error codewords which 
            have been corrected by FEC of this interface."
        ::= { zxGponOltPerf15MinIntervalEntry 16}

   zxGponOltH15MFecUnCorrWords OBJECT-TYPE
        SYNTAX      Counter64
        MAX-ACCESS  read-only
        STATUS      current
        DESCRIPTION
            "The 15 minutes interval error codewords which 
            haven't been corrected by FEC of this interface."
        ::= { zxGponOltPerf15MinIntervalEntry 17}

   zxGponOltH15MFecTotalRxWords OBJECT-TYPE
        SYNTAX      Counter64
        MAX-ACCESS  read-only
        STATUS      current
        DESCRIPTION
            "The 15 minutes interval received codewords by 
            FEC of this interface."
        ::= { zxGponOltPerf15MinIntervalEntry 18}
        
   zxGponOltH15MBipCorrBits OBJECT-TYPE
        SYNTAX      Counter64
        MAX-ACCESS  read-only
        STATUS      current
        DESCRIPTION
            "The 15 minutes interval PON port BIP
             corrected Bits.."
        ::= { zxGponOltPerf15MinIntervalEntry 19}      
        
   zxGponOltH15MCrcErrPkts OBJECT-TYPE
        SYNTAX      Counter64
        MAX-ACCESS  read-only
        STATUS      current
        DESCRIPTION
            "The 15 minutes interval error packets by CRC."
        ::= { zxGponOltPerf15MinIntervalEntry 20}      
        
   zxGponOltH15MValidData OBJECT-TYPE
        SYNTAX      TruthValue
        MAX-ACCESS  read-only
        STATUS      current
        DESCRIPTION     
             "Performance data valid flag. 
              true(1) means valid.  
              false(2) means invalid and the performace data is useless."
        ::= { zxGponOltPerf15MinIntervalEntry 100}     
        
--------------------------------------------------------------------------------
-- zxGponOltPerf1DayIntervalTable
--------------------------------------------------------------------------------

    zxGponOltPerf1DayIntervalTable   OBJECT-TYPE
        SYNTAX      SEQUENCE OF ZxGponOltPerf1DayIntervalEntry
        MAX-ACCESS  not-accessible
        STATUS      current
        DESCRIPTION 
             "The 1 day interval performance data table of interfaces."             
        ::= { zxAnGponOltPerfMgmt 5 }

    zxGponOltPerf1DayIntervalEntry   OBJECT-TYPE
        SYNTAX      ZxGponOltPerf1DayIntervalEntry
        MAX-ACCESS  not-accessible
        STATUS      current
        DESCRIPTION 
            "The 1 day interval performance data entry of interfaces."
        INDEX   { zxGponMgmtPonOltId, zxGponOltH1DIntervalNumber }
        ::= { zxGponOltPerf1DayIntervalTable 1 }

    ZxGponOltPerf1DayIntervalEntry ::= 
        SEQUENCE {
        zxGponOltH1DIntervalNumber         Integer32,
        zxGponOltH1DDateAndTime            DateAndTime,
        zxGponOltH1DCorrNonIdleGemFrmUp      Counter64,
        zxGponOltH1DCorrIdleGemFrmUp      Counter64,
        zxGponOltH1DErroredGemFrmUp          Counter64,
        zxGponOltH1DGemPayloadBytesUp        Counter64,                    
        zxGponOltH1DCorrEtherFrmUp        Counter64,                          
        zxGponOltH1DErroredEtherFrmUp        Counter64,                                                
        zxGponOltH1DErr                    Counter64,       
        zxGponOltH1DRei                    Counter64,            
        zxGponOltH1DValidEtherPktDown        Counter64,                                      
        zxGponOltH1DPloamDown                Counter64,                    
        zxGponOltH1DErroredPloamUp           Counter64,
        zxGponOltH1DPloamUp                  Counter64,                    
        zxGponOltH1DFecCorrBytes      Counter64,
        zxGponOltH1DFecCorrWords      Counter64,
        zxGponOltH1DFecUnCorrWords      Counter64,
        zxGponOltH1DFecTotalRxWords        Counter64,
        zxGponOltH1DBipCorrBits       Counter64,
        zxGponOltH1DCrcErrPkts             Counter64,
        zxGponOltH1DValidData              TruthValue
        }

    zxGponOltH1DIntervalNumber  OBJECT-TYPE 
        SYNTAX      Integer32(1..7)
        MAX-ACCESS  not-accessible
        STATUS      current
        DESCRIPTION     
             "Performance Data 
               
               Interval  1 is the the most recent previous interval
               Interval 7 is 1 week ago.  
               Intervals from 2 to 7 are optional."      
        ::= { zxGponOltPerf1DayIntervalEntry 1 }      
        
    zxGponOltH1DDateAndTime     OBJECT-TYPE   
        SYNTAX      DateAndTime
        MAX-ACCESS  read-only
        STATUS      current
        DESCRIPTION     
             "1 day performace data interval create time."       
        ::= { zxGponOltPerf1DayIntervalEntry 2 }            
    
    zxGponOltH1DCorrNonIdleGemFrmUp OBJECT-TYPE
        SYNTAX      Counter64
        MAX-ACCESS  read-only
        STATUS      current
        DESCRIPTION
            "The 1 day interval upstream correct none 
            idle gemport frames"
        ::= { zxGponOltPerf1DayIntervalEntry 3}

    zxGponOltH1DCorrIdleGemFrmUp OBJECT-TYPE
        SYNTAX      Counter64
        MAX-ACCESS  read-only
        STATUS      current
        DESCRIPTION
            "The 1 day interval upstream correct
             idle gemport frames"
        ::= { zxGponOltPerf1DayIntervalEntry 4}

   zxGponOltH1DErroredGemFrmUp OBJECT-TYPE
        SYNTAX      Counter64
        MAX-ACCESS  read-only
        STATUS      current
        DESCRIPTION
            "The 1 day interval upstream
             errored gemport frames"
        ::= { zxGponOltPerf1DayIntervalEntry 5}
   
   zxGponOltH1DGemPayloadBytesUp OBJECT-TYPE
        SYNTAX      Counter64
        MAX-ACCESS  read-only
        STATUS      current
        DESCRIPTION
            "The 1 day interval upstream gemport 
            payload bytes"
        ::= { zxGponOltPerf1DayIntervalEntry 6}

   zxGponOltH1DCorrEtherFrmUp OBJECT-TYPE
        SYNTAX      Counter64
        MAX-ACCESS  read-only
        STATUS      current
        DESCRIPTION
            "The 1 day interval upstream correct 
            ethernet frames"
        ::= { zxGponOltPerf1DayIntervalEntry 7}

   zxGponOltH1DErroredEtherFrmUp OBJECT-TYPE
        SYNTAX      Counter64
        MAX-ACCESS  read-only
        STATUS      current
        DESCRIPTION
            "The 1 day interval upstream errored 
            ethernet frames"
        ::= { zxGponOltPerf1DayIntervalEntry 8}
       
    zxGponOltH1DErr  OBJECT-TYPE 
        SYNTAX      Counter64
        MAX-ACCESS  read-only
        STATUS      current
        DESCRIPTION     
            "The 1 day interval ERR alarm times
             of this interface."
        ::= { zxGponOltPerf1DayIntervalEntry 9 }
        
    zxGponOltH1DRei OBJECT-TYPE
        SYNTAX      Counter64
        MAX-ACCESS  read-only
        STATUS      current
        DESCRIPTION
            "The 1 day interval remote onu error
             alarm times of this interface."
        ::= { zxGponOltPerf1DayIntervalEntry 10}

   zxGponOltH1DValidEtherPktDown OBJECT-TYPE
        SYNTAX      Counter64
        MAX-ACCESS  read-only
        STATUS      current
        DESCRIPTION
            "The 1 day interval  downstream 
            valid ethernet packets"
        ::= { zxGponOltPerf1DayIntervalEntry 11} 

   zxGponOltH1DPloamDown OBJECT-TYPE
        SYNTAX      Counter64
        MAX-ACCESS  read-only
        STATUS      current
        DESCRIPTION
            "The 1 day interval  downstream
             ploam messages"
        ::= { zxGponOltPerf1DayIntervalEntry 12}
   
   zxGponOltH1DErroredPloamUp OBJECT-TYPE
        SYNTAX      Counter64
        MAX-ACCESS  read-only
        STATUS      current
        DESCRIPTION
            "The 1 day interval errored upstream
             ploam messages"
        ::= { zxGponOltPerf1DayIntervalEntry 13}
        
   zxGponOltH1DPloamUp OBJECT-TYPE
        SYNTAX      Counter64
        MAX-ACCESS  read-only
        STATUS      current
        DESCRIPTION
            "The 1 day interval total upstream
             ploam messages"
        ::= { zxGponOltPerf1DayIntervalEntry 14}
   
   zxGponOltH1DFecCorrBytes OBJECT-TYPE
        SYNTAX      Counter64
        MAX-ACCESS  read-only
        STATUS      current
        DESCRIPTION
            "The 1 day interval error bytes 
            which have been corrected by FEC of this interface."
        ::= { zxGponOltPerf1DayIntervalEntry 15}

   zxGponOltH1DFecCorrWords OBJECT-TYPE
        SYNTAX      Counter64
        MAX-ACCESS  read-only
        STATUS      current
        DESCRIPTION
            "The 1 day interval error codewords
             which have been corrected by FEC of this interface."
        ::= { zxGponOltPerf1DayIntervalEntry 16}

   zxGponOltH1DFecUnCorrWords OBJECT-TYPE
        SYNTAX      Counter64
        MAX-ACCESS  read-only
        STATUS      current
        DESCRIPTION
            "The 1 day interval error codewords
             which haven't been corrected by FEC of this interface."
        ::= { zxGponOltPerf1DayIntervalEntry 17}

   zxGponOltH1DFecTotalRxWords OBJECT-TYPE
        SYNTAX      Counter64
        MAX-ACCESS  read-only
        STATUS      current
        DESCRIPTION
            "The 1 day interval received codewords
             by FEC of this interface."
        ::= { zxGponOltPerf1DayIntervalEntry 18}
        
   zxGponOltH1DBipCorrBits OBJECT-TYPE
        SYNTAX      Counter64
        MAX-ACCESS  read-only
        STATUS      current
        DESCRIPTION
            "The 1 day interval PON port BIP
             corrected Bits.."
        ::= { zxGponOltPerf1DayIntervalEntry 19}      
        
   zxGponOltH1DCrcErrPkts OBJECT-TYPE
        SYNTAX      Counter64
        MAX-ACCESS  read-only
        STATUS      current
        DESCRIPTION
            "The 1 day interval error packets by CRC."
        ::= { zxGponOltPerf1DayIntervalEntry 20}  
        
   zxGponOltH1DValidData OBJECT-TYPE
        SYNTAX      TruthValue
        MAX-ACCESS  read-only
        STATUS      current
        DESCRIPTION     
             "Performance data valid flag. 
              true(1) means valid.  
              false(2) means invalid and the performace data is useless."
        ::= { zxGponOltPerf1DayIntervalEntry 100}  
        
   zxAnGponOntPerfMgmt         OBJECT IDENTIFIER ::= { zxGponRootMib 32}   
  
--------------------------------------------------------------------------------
-- zxGponOntCurrPerfTable
--------------------------------------------------------------------------------
   zxGponOntCurrPerfTable OBJECT-TYPE
        SYNTAX      SEQUENCE OF ZxGponOntCurrPerfEntry
        MAX-ACCESS  not-accessible
        STATUS      current
        DESCRIPTION
            "The GPON ONU current performance data table" 
        ::= { zxAnGponOntPerfMgmt 1 }

    zxGponOntCurrPerfEntry OBJECT-TYPE
        SYNTAX      ZxGponOntCurrPerfEntry
        MAX-ACCESS  not-accessible
        STATUS      current
        DESCRIPTION
            "The entry in the ONU current performance data table."
        INDEX   { zxGponMgmtPonOltId, zxGponMgmtPonOnuId }
        ::= { zxGponOntCurrPerfTable 1 }

    ZxGponOntCurrPerfEntry ::=
    SEQUENCE {
        zxGponOntCorrNonIdleGemFrmUp                Counter64,
        zxGponOntGemPayloadBytesUp                  Counter64,
        zxGponOntCorrEtherFrmUp                     Counter64,
        zxGponOntErroredEtherFrmUp                  Counter64,
        zxGponOntTotlOmciFrmUp                      Counter64,
        zxGponOntErri                               Counter64,
        zxGponOntReii                               Counter64,
        zxGponOntUnrxBurstsUp                       Counter64,
        zxGponOntBipErrorUp                         Counter64,
        zxGponOntCorrBitsUp                         Counter64,
        zxGponOntNotCorrWordsUp                     Counter64,
        zxGponOntCorrNonIdleGemFrmDn                Counter64, 
        zxGponOntTxOmciFrames                       Counter64,
        zxGponOntTxPloamFrames                      Counter64,
        zxGponOntRxPloamFrames                      Counter64,
        zxGponOntLofiAlms                           Counter64,
        zxGponOntFecCorrBytes                       Counter64,
        zxGponOntFecCorrWords                       Counter64,
        zxGponOntFecUnCorrWords                     Counter64,
        zxGponOntFecTotalRxWords                    Counter64,
        zxGponOntCrcErrPkts                         Counter64,
        zxGponOnuPerfCapability                     BITS,
        zxGponOntCurrReset                          INTEGER
        }

   zxGponOntCorrNonIdleGemFrmUp OBJECT-TYPE
        SYNTAX      Counter64
        MAX-ACCESS  read-only
        STATUS      current
        DESCRIPTION
            "The total number of correct non-idle GEM frames upstream."
        ::= { zxGponOntCurrPerfEntry 1}

   zxGponOntGemPayloadBytesUp OBJECT-TYPE
        SYNTAX      Counter64
        MAX-ACCESS  read-only
        STATUS      current
        DESCRIPTION
            "The total number of payload bytes of GEM frames upstream."
        ::= { zxGponOntCurrPerfEntry 2}

   zxGponOntCorrEtherFrmUp OBJECT-TYPE
        SYNTAX      Counter64
        MAX-ACCESS  read-only
        STATUS      current
        DESCRIPTION
            "The total number of correct ethernet frames upstream."
        ::= { zxGponOntCurrPerfEntry 3}

   zxGponOntErroredEtherFrmUp OBJECT-TYPE
        SYNTAX      Counter64
        MAX-ACCESS  read-only
        STATUS      current
        DESCRIPTION
            "The total number of error ethernet frames upstream."
        ::= { zxGponOntCurrPerfEntry 4}

   zxGponOntTotlOmciFrmUp OBJECT-TYPE
        SYNTAX      Counter64
        MAX-ACCESS  read-only
        STATUS      current
        DESCRIPTION
            "The total number of OMCI frames upstream."
        ::= { zxGponOntCurrPerfEntry 5}

   zxGponOntErri OBJECT-TYPE
        SYNTAX      Counter64
        MAX-ACCESS  read-only
        STATUS      current
        DESCRIPTION
            "The total number of bip errors detected on OLT side."
        ::= { zxGponOntCurrPerfEntry 6}

   zxGponOntReii OBJECT-TYPE
        SYNTAX      Counter64
        MAX-ACCESS  read-only
        STATUS      current
        DESCRIPTION
            "The total number of bip errors detected on ONU side."
        ::= { zxGponOntCurrPerfEntry 7}

   zxGponOntUnrxBurstsUp OBJECT-TYPE
        SYNTAX      Counter64
        MAX-ACCESS  read-only
        STATUS      current
        DESCRIPTION
            "The total number of lost brust."
        ::= { zxGponOntCurrPerfEntry 8}

   zxGponOntBipErrorUp OBJECT-TYPE
        SYNTAX      Counter64
        MAX-ACCESS  read-only
        STATUS      current
        DESCRIPTION
            "The total number of bip errors upstream."
        ::= { zxGponOntCurrPerfEntry 9}

   zxGponOntCorrBitsUp OBJECT-TYPE
        SYNTAX      Counter64
        MAX-ACCESS  read-only
        STATUS      current
        DESCRIPTION
            "The total number of corrected bits upstream."
        ::= { zxGponOntCurrPerfEntry 10}

   zxGponOntNotCorrWordsUp OBJECT-TYPE
        SYNTAX      Counter64
        MAX-ACCESS  read-only
        STATUS      current
        DESCRIPTION
            "The total number of not corrected words."
        ::= { zxGponOntCurrPerfEntry 11}
        
   zxGponOntCorrNonIdleGemFrmDn OBJECT-TYPE
        SYNTAX      Counter64
        MAX-ACCESS  read-only
        STATUS      current
        DESCRIPTION
            "OLT sent to ONU correct non-idle GEM frames."
        ::= { zxGponOntCurrPerfEntry 12}
        
   zxGponOntTxOmciFrames OBJECT-TYPE
        SYNTAX      Counter64
        MAX-ACCESS  read-only
        STATUS      current
        DESCRIPTION
            "OLT sent to ONU OMCI frames."
        ::= { zxGponOntCurrPerfEntry 13}
        
   zxGponOntTxPloamFrames OBJECT-TYPE
        SYNTAX      Counter64
        MAX-ACCESS  read-only
        STATUS      current
        DESCRIPTION
            "OLT sent to ONU Ploam frames."
        ::= { zxGponOntCurrPerfEntry 14}
        
   zxGponOntRxPloamFrames OBJECT-TYPE
        SYNTAX      Counter64
        MAX-ACCESS  read-only
        STATUS      current
        DESCRIPTION
            "OLT received from ONU Ploam frames."
        ::= { zxGponOntCurrPerfEntry 15}
        
   zxGponOntLofiAlms OBJECT-TYPE
        SYNTAX      Counter64
        MAX-ACCESS  read-only
        STATUS      current
        DESCRIPTION
            "The real time statistics of lofi alarm times."
        ::= { zxGponOntCurrPerfEntry 16}
        
   zxGponOntFecCorrBytes OBJECT-TYPE
        SYNTAX      Counter64
        MAX-ACCESS  read-only
        STATUS      current
        DESCRIPTION
            "Error bytes which have been corrected by FEC."
        ::= { zxGponOntCurrPerfEntry 17}
    
   zxGponOntFecCorrWords OBJECT-TYPE
        SYNTAX      Counter64
        MAX-ACCESS  read-only
        STATUS      current
        DESCRIPTION
            "Error codewords which have been corrected by FEC."
        ::= { zxGponOntCurrPerfEntry 18}
        
   zxGponOntFecUnCorrWords OBJECT-TYPE
        SYNTAX      Counter64
        MAX-ACCESS  read-only
        STATUS      current
        DESCRIPTION
            "Error codewords which haven't been corrected by FEC."
        ::= { zxGponOntCurrPerfEntry 19}

   zxGponOntFecTotalRxWords OBJECT-TYPE
        SYNTAX      Counter64
        MAX-ACCESS  read-only
        STATUS      current
        DESCRIPTION
            "Received codewords by FEC."
        ::= { zxGponOntCurrPerfEntry 20}
        
   zxGponOntCrcErrPkts OBJECT-TYPE
        SYNTAX      Counter64
        MAX-ACCESS  read-only
        STATUS      current
        DESCRIPTION
            "Error packets by CRC."
        ::= { zxGponOntCurrPerfEntry 21}   
        
   zxGponOnuPerfCapability OBJECT-TYPE 
        SYNTAX      BITS 
           {
               zxGponOntCorrNonIdleGemFrmUp(0),
               zxGponOntGemPayloadBytesUp(1),
               zxGponOntCorrEtherFrmUp(2),
               zxGponOntErroredEtherFrmUp(3),
               zxGponOntTotlOmciFrmUp(4),
               zxGponOntErri(5),
               zxGponOntReii(6),
               zxGponOntUnrxBurstsUp(7),
               zxGponOntBipErrorUp(8),
               zxGponOntCorrBitsUp(9),
               zxGponOntNotCorrWordsUp(10),
               zxGponOntCorrNonIdleGemFrmDn(11),
               zxGponOntTxOmciFrames(12),
               zxGponOntTxPloamFrames(13),
               zxGponOntRxPloamFrames(14),
               zxGponOntLofiAlms(15),
               zxGponOntFecCorrBytes(16),
               zxGponOntFecCorrWords(17),
               zxGponOntFecUnCorrWords(18),
               zxGponOntFecTotalRxWords(19),
               zxGponOntCrcErrPkts(20)
           }             
        MAX-ACCESS  read-only
        STATUS      current
        DESCRIPTION     
            "The attribute indicates that the supports of GPON ONU performance,
            each bit from left to right represents the support of performance 
            statistic from top to bottom in this MIB table, value 1 represents 
            support and value 0 is not support.
            And the supports of C15M,C1D,H15M,H1D performance statistics 
            decided by zxGponOnuPerfCapability also." 
        ::= { zxGponOntCurrPerfEntry 99 } 
        
    zxGponOntCurrReset OBJECT-TYPE 
        SYNTAX      INTEGER
            {
                perfReset(1)
            }
        MAX-ACCESS  read-write
        STATUS      current
        DESCRIPTION     
            "Clear all the current performance variables.
            When get this variable, always return 1."
        ::= { zxGponOntCurrPerfEntry 100 } 
    
--------------------------------------------------------------------------------
-- zxGponOntCurrPerf15MinTable
--------------------------------------------------------------------------------

   zxGponOntCurrPerf15MinTable OBJECT-TYPE
        SYNTAX      SEQUENCE OF ZxGponOntCurrPerf15MinEntry
        MAX-ACCESS  not-accessible
        STATUS      current
        DESCRIPTION
            "The current 15 minutes performance 
            data table of GPON ONU." 
        ::= { zxAnGponOntPerfMgmt 2 }

    zxGponOntCurrPerf15MinEntry OBJECT-TYPE
        SYNTAX      ZxGponOntCurrPerf15MinEntry
        MAX-ACCESS  not-accessible
        STATUS      current
        DESCRIPTION
            "An entry in the ONU current 15 minutes 
            performance data table."
        INDEX   { zxGponMgmtPonOltId, zxGponMgmtPonOnuId  }
        ::= { zxGponOntCurrPerf15MinTable 1 }

    ZxGponOntCurrPerf15MinEntry ::=
        SEQUENCE {
        zxGponOntC15MTimeElapsed                             Gauge32,
        zxGponOntC15MCorrNonIdleGemFrmUp                        Counter64,
        zxGponOntC15MGemPayloadBytesUp                       Counter64,
        zxGponOntC15MCorrEtherFrmUp                          Counter64,
        zxGponOntC15MErroredEtherFrmUp                       Counter64,
        zxGponOntC15MTotlOmciFrmUp                           Counter64,
        zxGponOntC15MErri                                    Counter64,
        zxGponOntC15MReii                                    Counter64,
        zxGponOntC15MUnrxBurstsUp                            Counter64,
        zxGponOntC15MBipErrorUp                              Counter64,
        zxGponOntC15MCorrBitsUp                              Counter64,
        zxGponOntC15MNotCorrWordsUp                          Counter64,
        zxGponOntC15MCorrNonIdleGemFrmDn                        Counter64, 
        zxGponOntC15MTxOmciFrms                              Counter64,
        zxGponOntC15MTxPloamFrms                             Counter64,
        zxGponOntC15MRxPloamFrms                             Counter64,
        zxGponOntC15MLofiAlarms                              Counter64,
        zxGponOntC15MFecCorrBytes                       Counter64,
        zxGponOntC15MFecCorrWords                       Counter64,
        zxGponOntC15MFecUnCorrWords                          Counter64,
        zxGponOntC15MFecTotalRxWords                         Counter64,
        zxGponOntC15MCrcErrPkts                              Counter64,
        zxGponOntC15MReset                                   INTEGER
        }

    zxGponOntC15MTimeElapsed  OBJECT-TYPE 
        SYNTAX      Gauge32(0..86399)
        UNITS       "seconds"
        MAX-ACCESS  read-only
        STATUS      current
        DESCRIPTION     
            "Number of seconds that have elapsed since the 
            beginning of the current 15 minutes interval."     
        ::= { zxGponOntCurrPerf15MinEntry 1 }      
                    
   zxGponOntC15MCorrNonIdleGemFrmUp OBJECT-TYPE
        SYNTAX      Counter64
        MAX-ACCESS  read-only
        STATUS      current
        DESCRIPTION
            "The current 15 minutes interval correct non-idle
             GEM frames upstream."
        ::= { zxGponOntCurrPerf15MinEntry 2}

   zxGponOntC15MGemPayloadBytesUp OBJECT-TYPE
        SYNTAX      Counter64
        MAX-ACCESS  read-only
        STATUS      current
        DESCRIPTION
            "The current 15 minutes interval payload bytes of
             GEM frames upstream."
        ::= { zxGponOntCurrPerf15MinEntry 3}

   zxGponOntC15MCorrEtherFrmUp OBJECT-TYPE
        SYNTAX      Counter64
        MAX-ACCESS  read-only
        STATUS      current
        DESCRIPTION
            "The current 15 minutes interval correct ethernet
             frames upstream."
        ::= { zxGponOntCurrPerf15MinEntry 4}

   zxGponOntC15MErroredEtherFrmUp OBJECT-TYPE
        SYNTAX      Counter64
        MAX-ACCESS  read-only
        STATUS      current
        DESCRIPTION
            "The current 15 minutes interval error ethernet
             frames upstream."
        ::= { zxGponOntCurrPerf15MinEntry 5}

   zxGponOntC15MTotlOmciFrmUp OBJECT-TYPE
        SYNTAX      Counter64
        MAX-ACCESS  read-only
        STATUS      current
        DESCRIPTION
            "The current 15 minutes interval OMCI frames
             upstream."
        ::= { zxGponOntCurrPerf15MinEntry 6}

   zxGponOntC15MErri OBJECT-TYPE
        SYNTAX      Counter64
        MAX-ACCESS  read-only
        STATUS      current
        DESCRIPTION
            "The current 15 minutes interval bip errors
             detected on OLT side."
        ::= { zxGponOntCurrPerf15MinEntry 7}

   zxGponOntC15MReii OBJECT-TYPE
        SYNTAX      Counter64
        MAX-ACCESS  read-only
        STATUS      current
        DESCRIPTION
            "The current 15 minutes interval bip errors
             detected on ONU side."
        ::= { zxGponOntCurrPerf15MinEntry 8}

   zxGponOntC15MUnrxBurstsUp OBJECT-TYPE
        SYNTAX      Counter64
        MAX-ACCESS  read-only
        STATUS      current
        DESCRIPTION
            "The current 15 minutes interval lost brust."
        ::= { zxGponOntCurrPerf15MinEntry 9}

   zxGponOntC15MBipErrorUp OBJECT-TYPE
        SYNTAX      Counter64
        MAX-ACCESS  read-only
        STATUS      current
        DESCRIPTION
            "The current 15 minutes interval bip errors
             upstream."
        ::= { zxGponOntCurrPerf15MinEntry 10}

   zxGponOntC15MCorrBitsUp OBJECT-TYPE
        SYNTAX      Counter64
        MAX-ACCESS  read-only
        STATUS      current
        DESCRIPTION
            "The current 15 minutes interval corrected
             bits upstream."
        ::= { zxGponOntCurrPerf15MinEntry 11}

   zxGponOntC15MNotCorrWordsUp OBJECT-TYPE
        SYNTAX      Counter64
        MAX-ACCESS  read-only
        STATUS      current
        DESCRIPTION
            "The current 15 minutes interval not
             corrected words."
        ::= { zxGponOntCurrPerf15MinEntry 12}
        
   zxGponOntC15MCorrNonIdleGemFrmDn OBJECT-TYPE
        SYNTAX      Counter64
        MAX-ACCESS  read-only
        STATUS      current
        DESCRIPTION
            "The current 15 minutes interval OLT sent to 
            ONU correct non-idle GEM frames."
        ::= { zxGponOntCurrPerf15MinEntry 13}
        
   zxGponOntC15MTxOmciFrms OBJECT-TYPE
        SYNTAX      Counter64
        MAX-ACCESS  read-only
        STATUS      current
        DESCRIPTION
            "The current 15 minutes interval
             OLT sent to ONU OMCI frames."
        ::= { zxGponOntCurrPerf15MinEntry 14}
        
   zxGponOntC15MTxPloamFrms OBJECT-TYPE
        SYNTAX      Counter64
        MAX-ACCESS  read-only
        STATUS      current
        DESCRIPTION
            "The current 15 minutes interval
             OLT sent to ONU Ploam frames."
        ::= { zxGponOntCurrPerf15MinEntry 15}
        
   zxGponOntC15MRxPloamFrms OBJECT-TYPE
        SYNTAX      Counter64
        MAX-ACCESS  read-only
        STATUS      current
        DESCRIPTION
            "The current 15 minutes interval
             OLT received from ONU Ploam frames."
        ::= { zxGponOntCurrPerf15MinEntry 16}
        
   zxGponOntC15MLofiAlarms OBJECT-TYPE
        SYNTAX      Counter64
        MAX-ACCESS  read-only
        STATUS      current
        DESCRIPTION
            "The current 15 minutes interval
             lofi alarm times."
        ::= { zxGponOntCurrPerf15MinEntry 17}
        
   zxGponOntC15MFecCorrBytes OBJECT-TYPE
        SYNTAX      Counter64
        MAX-ACCESS  read-only
        STATUS      current
        DESCRIPTION
            "The current 15 minutes interval error
             bytes which have been corrected by FEC."
        ::= { zxGponOntCurrPerf15MinEntry 18}
    
   zxGponOntC15MFecCorrWords OBJECT-TYPE
        SYNTAX      Counter64
        MAX-ACCESS  read-only
        STATUS      current
        DESCRIPTION
            "The current 15 minutes interval error 
            codewords which have been corrected by FEC."
        ::= { zxGponOntCurrPerf15MinEntry 19}
        
   zxGponOntC15MFecUnCorrWords OBJECT-TYPE
        SYNTAX      Counter64
        MAX-ACCESS  read-only
        STATUS      current
        DESCRIPTION
            "The current 15 minutes interval error codewords
             which haven't been corrected by FEC."
        ::= { zxGponOntCurrPerf15MinEntry 20}

   zxGponOntC15MFecTotalRxWords OBJECT-TYPE
        SYNTAX      Counter64
        MAX-ACCESS  read-only
        STATUS      current
        DESCRIPTION
            "The current 15 minutes interval received
             codewords by FEC."
        ::= { zxGponOntCurrPerf15MinEntry 21}
        
   zxGponOntC15MCrcErrPkts OBJECT-TYPE
        SYNTAX      Counter64
        MAX-ACCESS  read-only
        STATUS      current
        DESCRIPTION
            "The current 15 minutes interval error
             packets by CRC."
        ::= { zxGponOntCurrPerf15MinEntry 22} 
       
   zxGponOntC15MReset OBJECT-TYPE 
        SYNTAX      INTEGER
            {
                perfReset(1)
            }
        MAX-ACCESS  read-write
        STATUS      current
        DESCRIPTION     
            "Clear all the current 15-minutes performance variables.
            When get this variable, always return 1."
        ::= { zxGponOntCurrPerf15MinEntry 100 } 
        
--------------------------------------------------------------------------------
-- zxGponOntCurrPerf1DayTable
--------------------------------------------------------------------------------

   zxGponOntCurrPerf1DayTable OBJECT-TYPE
        SYNTAX      SEQUENCE OF ZxGponOntCurrPerf1DayEntry
        MAX-ACCESS  not-accessible
        STATUS      current
        DESCRIPTION
            "The current 1 day performance 
            data table of GPON ONU." 
        ::= { zxAnGponOntPerfMgmt 3 }

    zxGponOntCurrPerf1DayEntry OBJECT-TYPE
        SYNTAX      ZxGponOntCurrPerf1DayEntry
        MAX-ACCESS  not-accessible
        STATUS      current
        DESCRIPTION
            "An entry in the ONU current 1 day 
            performance data table."
        INDEX   { zxGponMgmtPonOltId, zxGponMgmtPonOnuId  }
        ::= { zxGponOntCurrPerf1DayTable 1 }

    ZxGponOntCurrPerf1DayEntry ::=
        SEQUENCE {
        zxGponOntC1DTimeElapsed                             Gauge32,
        zxGponOntC1DCorrNonIdleGemFrmUp                        Counter64,
        zxGponOntC1DGemPayloadBytesUp                       Counter64,
        zxGponOntC1DCorrEtherFrmUp                          Counter64,
        zxGponOntC1DErroredEtherFrmUp                       Counter64,
        zxGponOntC1DTotlOmciFrmUp                           Counter64,
        zxGponOntC1DErri                                    Counter64,
        zxGponOntC1DReii                                    Counter64,
        zxGponOntC1DUnrxBurstsUp                            Counter64,
        zxGponOntC1DBipErrorUp                              Counter64,
        zxGponOntC1DCorrBitsUp                              Counter64,
        zxGponOntC1DNotCorrWordsUp                          Counter64,
        zxGponOntC1DCorrNonIdleGemFrmDn                        Counter64, 
        zxGponOntC1DTxOmciFrms                              Counter64,
        zxGponOntC1DTxPloamFrms                             Counter64,
        zxGponOntC1DRxPloamFrms                             Counter64,
        zxGponOntC1DLofiAlarms                              Counter64,
        zxGponOntC1DFecCorrBytes                       Counter64,
        zxGponOntC1DFecCorrWords                       Counter64,
        zxGponOntC1DFecUnCorrWords                         Counter64,
        zxGponOntC1DFecTotalRxWords                         Counter64,
        zxGponOntC1DCrcErrPkts                              Counter64,
        zxGponOntC1DReset                                   INTEGER
        }

    zxGponOntC1DTimeElapsed  OBJECT-TYPE 
        SYNTAX      Gauge32(0..86399)
        UNITS       "seconds"
        MAX-ACCESS  read-only
        STATUS      current
        DESCRIPTION     
            "Number of seconds that have elapsed since the 
            beginning of the current 1 day interval."     
        ::= { zxGponOntCurrPerf1DayEntry 1 }      
                    
   zxGponOntC1DCorrNonIdleGemFrmUp OBJECT-TYPE
        SYNTAX      Counter64
        MAX-ACCESS  read-only
        STATUS      current
        DESCRIPTION
            "The current 1 day interval correct non-idle
             GEM frames upstream."
        ::= { zxGponOntCurrPerf1DayEntry 2}

   zxGponOntC1DGemPayloadBytesUp OBJECT-TYPE
        SYNTAX      Counter64
        MAX-ACCESS  read-only
        STATUS      current
        DESCRIPTION
            "The current 1 day interval payload bytes of
             GEM frames upstream."
        ::= { zxGponOntCurrPerf1DayEntry 3}

   zxGponOntC1DCorrEtherFrmUp OBJECT-TYPE
        SYNTAX      Counter64
        MAX-ACCESS  read-only
        STATUS      current
        DESCRIPTION
            "The current 1 day interval correct ethernet
             frames upstream."
        ::= { zxGponOntCurrPerf1DayEntry 4}

   zxGponOntC1DErroredEtherFrmUp OBJECT-TYPE
        SYNTAX      Counter64
        MAX-ACCESS  read-only
        STATUS      current
        DESCRIPTION
            "The current 1 day interval error ethernet
             frames upstream."
        ::= { zxGponOntCurrPerf1DayEntry 5}

   zxGponOntC1DTotlOmciFrmUp OBJECT-TYPE
        SYNTAX      Counter64
        MAX-ACCESS  read-only
        STATUS      current
        DESCRIPTION
            "The current 1 day interval OMCI frames
             upstream."
        ::= { zxGponOntCurrPerf1DayEntry 6}

   zxGponOntC1DErri OBJECT-TYPE
        SYNTAX      Counter64
        MAX-ACCESS  read-only
        STATUS      current
        DESCRIPTION
            "The current 1 day interval bip errors
             detected on OLT side."
        ::= { zxGponOntCurrPerf1DayEntry 7}

   zxGponOntC1DReii OBJECT-TYPE
        SYNTAX      Counter64
        MAX-ACCESS  read-only
        STATUS      current
        DESCRIPTION
            "The current 1 day interval bip errors
             detected on ONU side."
        ::= { zxGponOntCurrPerf1DayEntry 8}

   zxGponOntC1DUnrxBurstsUp OBJECT-TYPE
        SYNTAX      Counter64
        MAX-ACCESS  read-only
        STATUS      current
        DESCRIPTION
            "The current 1 day interval lost brust."
        ::= { zxGponOntCurrPerf1DayEntry 9}

   zxGponOntC1DBipErrorUp OBJECT-TYPE
        SYNTAX      Counter64
        MAX-ACCESS  read-only
        STATUS      current
        DESCRIPTION
            "The current 1 day interval bip errors
             upstream."
        ::= { zxGponOntCurrPerf1DayEntry 10}

   zxGponOntC1DCorrBitsUp OBJECT-TYPE
        SYNTAX      Counter64
        MAX-ACCESS  read-only
        STATUS      current
        DESCRIPTION
            "The current 1 day interval corrected
             bits upstream."
        ::= { zxGponOntCurrPerf1DayEntry 11}

   zxGponOntC1DNotCorrWordsUp OBJECT-TYPE
        SYNTAX      Counter64
        MAX-ACCESS  read-only
        STATUS      current
        DESCRIPTION
            "The current 1 day interval not
             corrected words."
        ::= { zxGponOntCurrPerf1DayEntry 12}
        
   zxGponOntC1DCorrNonIdleGemFrmDn OBJECT-TYPE
        SYNTAX      Counter64
        MAX-ACCESS  read-only
        STATUS      current
        DESCRIPTION
            "The current 1 day interval OLT sent to 
            ONU correct non-idle GEM frames."
        ::= { zxGponOntCurrPerf1DayEntry 13}
        
   zxGponOntC1DTxOmciFrms OBJECT-TYPE
        SYNTAX      Counter64
        MAX-ACCESS  read-only
        STATUS      current
        DESCRIPTION
            "The current 1 day interval
             OLT sent to ONU OMCI frames."
        ::= { zxGponOntCurrPerf1DayEntry 14}
        
   zxGponOntC1DTxPloamFrms OBJECT-TYPE
        SYNTAX      Counter64
        MAX-ACCESS  read-only
        STATUS      current
        DESCRIPTION
            "The current 1 day interval
             OLT sent to ONU Ploam frames."
        ::= { zxGponOntCurrPerf1DayEntry 15}
        
   zxGponOntC1DRxPloamFrms OBJECT-TYPE
        SYNTAX      Counter64
        MAX-ACCESS  read-only
        STATUS      current
        DESCRIPTION
            "The current 1 day interval
             OLT received from ONU Ploam frames."
        ::= { zxGponOntCurrPerf1DayEntry 16}
        
   zxGponOntC1DLofiAlarms OBJECT-TYPE
        SYNTAX      Counter64
        MAX-ACCESS  read-only
        STATUS      current
        DESCRIPTION
            "The current 1 day interval
             lofi alarm times."
        ::= { zxGponOntCurrPerf1DayEntry 17}
        
   zxGponOntC1DFecCorrBytes OBJECT-TYPE
        SYNTAX      Counter64
        MAX-ACCESS  read-only
        STATUS      current
        DESCRIPTION
            "The current 1 day interval error
             bytes which have been corrected by FEC."
        ::= { zxGponOntCurrPerf1DayEntry 18}
    
   zxGponOntC1DFecCorrWords OBJECT-TYPE
        SYNTAX      Counter64
        MAX-ACCESS  read-only
        STATUS      current
        DESCRIPTION
            "The current 1 day interval error 
            codewords which have been corrected by FEC."
        ::= { zxGponOntCurrPerf1DayEntry 19}
        
   zxGponOntC1DFecUnCorrWords OBJECT-TYPE
        SYNTAX      Counter64
        MAX-ACCESS  read-only
        STATUS      current
        DESCRIPTION
            "The current 1 day interval error codewords
             which haven't been corrected by FEC."
        ::= { zxGponOntCurrPerf1DayEntry 20}

   zxGponOntC1DFecTotalRxWords OBJECT-TYPE
        SYNTAX      Counter64
        MAX-ACCESS  read-only
        STATUS      current
        DESCRIPTION
            "The current 1 day interval received
             codewords by FEC."
        ::= { zxGponOntCurrPerf1DayEntry 21}
        
   zxGponOntC1DCrcErrPkts OBJECT-TYPE
        SYNTAX      Counter64
        MAX-ACCESS  read-only
        STATUS      current
        DESCRIPTION
            "The current 1 day interval error
             packets by CRC."
        ::= { zxGponOntCurrPerf1DayEntry 22} 
       
   zxGponOntC1DReset OBJECT-TYPE 
        SYNTAX      INTEGER
            {
                perfReset(1)
            }
        MAX-ACCESS  read-write
        STATUS      current
        DESCRIPTION     
            "Clear all the current 1 day performance variables.
            When get this variable, always return 1."
        ::= { zxGponOntCurrPerf1DayEntry 100 }  
        
--------------------------------------------------------------------------------
-- zxGponOntPerf15MinIntervalTable
--------------------------------------------------------------------------------

   zxGponOntPerf15MinIntervalTable OBJECT-TYPE
        SYNTAX      SEQUENCE OF ZxGponOntPerf15MinIntervalEntry
        MAX-ACCESS  not-accessible
        STATUS      current
        DESCRIPTION
            "The 15 minutes interval performance data table of GPON ONT." 
        ::= { zxAnGponOntPerfMgmt 4 }

    zxGponOntPerf15MinIntervalEntry OBJECT-TYPE
        SYNTAX      ZxGponOntPerf15MinIntervalEntry
        MAX-ACCESS  not-accessible
        STATUS      current
        DESCRIPTION
            "The entry in the ONU 15 minutes interval 
            performance data table."
        INDEX   { zxGponMgmtPonOltId, zxGponMgmtPonOnuId, zxGponOntH15MIntervalNumber  }
        ::= { zxGponOntPerf15MinIntervalTable 1 }

    ZxGponOntPerf15MinIntervalEntry ::=
        SEQUENCE {
        zxGponOntH15MIntervalNumber                          Integer32,
        zxGponOntH15MDateAndTime                             DateAndTime,
        zxGponOntH15MCorrNonIdleGemFrmUp                        Counter64,
        zxGponOntH15MGemPayloadBytesUp                       Counter64,
        zxGponOntH15MCorrEtherFrmUp                          Counter64,
        zxGponOntH15MErroredEtherFrmUp                       Counter64,
        zxGponOntH15MTotlOmciFrmUp                           Counter64,
        zxGponOntH15MErri                                    Counter64,
        zxGponOntH15MReii                                    Counter64,
        zxGponOntH15MUnrxBurstsUp                            Counter64,
        zxGponOntH15MBipErrorUp                              Counter64,
        zxGponOntH15MCorrBitsUp                              Counter64,
        zxGponOntH15MNotCorrWordsUp                          Counter64,
        zxGponOntH15MCorrNonIdleGemFrmDn                        Counter64, 
        zxGponOntH15MTxOmciFrms                              Counter64,
        zxGponOntH15MTxPloamFrms                             Counter64,
        zxGponOntH15MRxPloamFrms                             Counter64,
        zxGponOntH15MLofiAlarms                              Counter64,
        zxGponOntH15MFecCorrBytes                       Counter64,
        zxGponOntH15MFecCorrWords                       Counter64,
        zxGponOntH15MFecUnCorrWords                         Counter64,
        zxGponOntH15MFecTotalRxWords                         Counter64,
        zxGponOntH15MCrcErrPkts                              Counter64,
        zxGponOntH15MValidData                               TruthValue
        }

    zxGponOntH15MIntervalNumber  OBJECT-TYPE 
        SYNTAX      Integer32(1..96)
        MAX-ACCESS  not-accessible
        STATUS      current
        DESCRIPTION     
             "Performance Data.
              
              Interval 1 is the the most recent previous interval.
              Interval 96 is 24 hours ago.  
              Intervals from 2 to 96 are optional."       
        ::= { zxGponOntPerf15MinIntervalEntry 1 }      
        
    zxGponOntH15MDateAndTime     OBJECT-TYPE   
        SYNTAX      DateAndTime
        MAX-ACCESS  read-only
        STATUS      current
        DESCRIPTION     
             "15min performance data interval create time."       
        ::= { zxGponOntPerf15MinIntervalEntry 2 }            
        
   zxGponOntH15MCorrNonIdleGemFrmUp OBJECT-TYPE
        SYNTAX      Counter64
        MAX-ACCESS  read-only
        STATUS      current
        DESCRIPTION
            "The 15 minutes interval correct non-idle
             GEM frames upstream."
        ::= { zxGponOntPerf15MinIntervalEntry 3}

   zxGponOntH15MGemPayloadBytesUp OBJECT-TYPE
        SYNTAX      Counter64
        MAX-ACCESS  read-only
        STATUS      current
        DESCRIPTION
            "The 15 minutes interval payload bytes of
             GEM frames upstream."
        ::= { zxGponOntPerf15MinIntervalEntry 4}

   zxGponOntH15MCorrEtherFrmUp OBJECT-TYPE
        SYNTAX      Counter64
        MAX-ACCESS  read-only
        STATUS      current
        DESCRIPTION
            "The 15 minutes interval correct ethernet
             frames upstream."
        ::= { zxGponOntPerf15MinIntervalEntry 5}

   zxGponOntH15MErroredEtherFrmUp OBJECT-TYPE
        SYNTAX      Counter64
        MAX-ACCESS  read-only
        STATUS      current
        DESCRIPTION
            "The 15 minutes interval error ethernet
             frames upstream."
        ::= { zxGponOntPerf15MinIntervalEntry 6}

   zxGponOntH15MTotlOmciFrmUp OBJECT-TYPE
        SYNTAX      Counter64
        MAX-ACCESS  read-only
        STATUS      current
        DESCRIPTION
            "The 15 minutes interval OMCI frames
             upstream."
        ::= { zxGponOntPerf15MinIntervalEntry 7}

   zxGponOntH15MErri OBJECT-TYPE
        SYNTAX      Counter64
        MAX-ACCESS  read-only
        STATUS      current
        DESCRIPTION
            "The 15 minutes interval bip errors
             detected on OLT side."
        ::= { zxGponOntPerf15MinIntervalEntry 8}

   zxGponOntH15MReii OBJECT-TYPE
        SYNTAX      Counter64
        MAX-ACCESS  read-only
        STATUS      current
        DESCRIPTION
            "The 15 minutes interval bip errors
             detected on ONU side."
        ::= { zxGponOntPerf15MinIntervalEntry 9}

   zxGponOntH15MUnrxBurstsUp OBJECT-TYPE
        SYNTAX      Counter64
        MAX-ACCESS  read-only
        STATUS      current
        DESCRIPTION
            "The 15 minutes interval lost brust."
        ::= { zxGponOntPerf15MinIntervalEntry 10}

   zxGponOntH15MBipErrorUp OBJECT-TYPE
        SYNTAX      Counter64
        MAX-ACCESS  read-only
        STATUS      current
        DESCRIPTION
            "The 15 minutes interval bip errors
             upstream."
        ::= { zxGponOntPerf15MinIntervalEntry 11}

   zxGponOntH15MCorrBitsUp OBJECT-TYPE
        SYNTAX      Counter64
        MAX-ACCESS  read-only
        STATUS      current
        DESCRIPTION
            "The 15 minutes interval corrected
             bits upstream."
        ::= { zxGponOntPerf15MinIntervalEntry 12}

   zxGponOntH15MNotCorrWordsUp OBJECT-TYPE
        SYNTAX      Counter64
        MAX-ACCESS  read-only
        STATUS      current
        DESCRIPTION
            "The 15 minutes interval not
             corrected words."
        ::= { zxGponOntPerf15MinIntervalEntry 13}
        
   zxGponOntH15MCorrNonIdleGemFrmDn OBJECT-TYPE
        SYNTAX      Counter64
        MAX-ACCESS  read-only
        STATUS      current
        DESCRIPTION
            "The 15 minutes interval OLT sent to 
            ONU correct non-idle GEM frames."
        ::= { zxGponOntPerf15MinIntervalEntry 14}
        
   zxGponOntH15MTxOmciFrms OBJECT-TYPE
        SYNTAX      Counter64
        MAX-ACCESS  read-only
        STATUS      current
        DESCRIPTION
            "The 15 minutes interval
             OLT sent to ONU OMCI frames."
        ::= { zxGponOntPerf15MinIntervalEntry 15}
        
   zxGponOntH15MTxPloamFrms OBJECT-TYPE
        SYNTAX      Counter64
        MAX-ACCESS  read-only
        STATUS      current
        DESCRIPTION
            "The 15 minutes interval
             OLT sent to ONU Ploam frames."
        ::= { zxGponOntPerf15MinIntervalEntry 16}
        
   zxGponOntH15MRxPloamFrms OBJECT-TYPE
        SYNTAX      Counter64
        MAX-ACCESS  read-only
        STATUS      current
        DESCRIPTION
            "The 15 minutes interval
             OLT received from ONU Ploam frames."
        ::= { zxGponOntPerf15MinIntervalEntry 17}
        
   zxGponOntH15MLofiAlarms OBJECT-TYPE
        SYNTAX      Counter64
        MAX-ACCESS  read-only
        STATUS      current
        DESCRIPTION
            "The 15 minutes interval
             lofi alarm times."
        ::= { zxGponOntPerf15MinIntervalEntry 18}
        
   zxGponOntH15MFecCorrBytes OBJECT-TYPE
        SYNTAX      Counter64
        MAX-ACCESS  read-only
        STATUS      current
        DESCRIPTION
            "The 15 minutes interval error
             bytes which have been corrected by FEC."
        ::= { zxGponOntPerf15MinIntervalEntry 19}
    
   zxGponOntH15MFecCorrWords OBJECT-TYPE
        SYNTAX      Counter64
        MAX-ACCESS  read-only
        STATUS      current
        DESCRIPTION
            "The 15 minutes interval error 
            codewords which have been corrected by FEC."
        ::= { zxGponOntPerf15MinIntervalEntry 20}
        
   zxGponOntH15MFecUnCorrWords OBJECT-TYPE
        SYNTAX      Counter64
        MAX-ACCESS  read-only
        STATUS      current
        DESCRIPTION
            "The 15 minutes interval error codewords
             which haven't been corrected by FEC."
        ::= { zxGponOntPerf15MinIntervalEntry 21}

   zxGponOntH15MFecTotalRxWords OBJECT-TYPE
        SYNTAX      Counter64
        MAX-ACCESS  read-only
        STATUS      current
        DESCRIPTION
            "The 15 minutes interval received
             codewords by FEC."
        ::= { zxGponOntPerf15MinIntervalEntry 22}
        
   zxGponOntH15MCrcErrPkts OBJECT-TYPE
        SYNTAX      Counter64
        MAX-ACCESS  read-only
        STATUS      current
        DESCRIPTION
            "The 15 minutes interval error
             packets by CRC."
        ::= { zxGponOntPerf15MinIntervalEntry 23}    
        
   zxGponOntH15MValidData OBJECT-TYPE
        SYNTAX      TruthValue
        MAX-ACCESS  read-only
        STATUS      current
        DESCRIPTION     
             "Performance data valid flag. 
              true(1) means valid.  
              false(2) means invalid and the performace data is useless."
        ::= { zxGponOntPerf15MinIntervalEntry 100}  
        
--------------------------------------------------------------------------------
-- zxGponOntPerf1DayIntervalTable
--------------------------------------------------------------------------------

   zxGponOntPerf1DayIntervalTable OBJECT-TYPE
        SYNTAX      SEQUENCE OF ZxGponOntPerf1DayIntervalEntry
        MAX-ACCESS  not-accessible
        STATUS      current
        DESCRIPTION
            "The 1 day interval performance data table of GPON ONT." 
        ::= { zxAnGponOntPerfMgmt 5 }

    zxGponOntPerf1DayIntervalEntry OBJECT-TYPE
        SYNTAX      ZxGponOntPerf1DayIntervalEntry
        MAX-ACCESS  not-accessible
        STATUS      current
        DESCRIPTION
            "The entry in the ONU 1 day interval 
            performance data table."
        INDEX   { zxGponMgmtPonOltId, zxGponMgmtPonOnuId, zxGponOntH1DIntervalNumber  }
        ::= { zxGponOntPerf1DayIntervalTable 1 }

    ZxGponOntPerf1DayIntervalEntry ::=
        SEQUENCE {
        zxGponOntH1DIntervalNumber                          Integer32,
        zxGponOntH1DDateAndTime                             DateAndTime,
        zxGponOntH1DCorrNonIdleGemFrmUp                        Counter64,
        zxGponOntH1DGemPayloadBytesUp                       Counter64,
        zxGponOntH1DCorrEtherFrmUp                          Counter64,
        zxGponOntH1DErroredEtherFrmUp                       Counter64,
        zxGponOntH1DTotlOmciFrmUp                           Counter64,
        zxGponOntH1DErri                                    Counter64,
        zxGponOntH1DReii                                    Counter64,
        zxGponOntH1DUnrxBurstsUp                            Counter64,
        zxGponOntH1DBipErrorUp                              Counter64,
        zxGponOntH1DCorrBitsUp                              Counter64,
        zxGponOntH1DNotCorrWordsUp                          Counter64,
        zxGponOntH1DCorrNonIdleGemFrmDn                        Counter64, 
        zxGponOntH1DTxOmciFrms                              Counter64,
        zxGponOntH1DTxPloamFrms                             Counter64,
        zxGponOntH1DRxPloamFrms                             Counter64,
        zxGponOntH1DLofiAlarms                              Counter64,
        zxGponOntH1DFecCorrBytes                       Counter64,
        zxGponOntH1DFecCorrWords                       Counter64,
        zxGponOntH1DFecUnCorrWords                          Counter64,
        zxGponOntH1DFecTotalRxWords                         Counter64,
        zxGponOntH1DCrcErrPkts                              Counter64,
        zxGponOntH1DValidData                               TruthValue
        }

    zxGponOntH1DIntervalNumber  OBJECT-TYPE 
        SYNTAX      Integer32(1..7)
        MAX-ACCESS  not-accessible
        STATUS      current
        DESCRIPTION     
             "Performance Data.
              
              Interval 1 is the the most recent previous interval.
              Interval 7 is 1 week ago.  
              Intervals from 2 to 7 are optional."     
        ::= { zxGponOntPerf1DayIntervalEntry 1 }      
        
    zxGponOntH1DDateAndTime     OBJECT-TYPE   
        SYNTAX      DateAndTime
        MAX-ACCESS  read-only
        STATUS      current
        DESCRIPTION     
             "The 1 day performace data interval create time."       
        ::= { zxGponOntPerf1DayIntervalEntry 2 }            
        
   zxGponOntH1DCorrNonIdleGemFrmUp OBJECT-TYPE
        SYNTAX      Counter64
        MAX-ACCESS  read-only
        STATUS      current
        DESCRIPTION
            "The 1 day interval correct non-idle
             GEM frames upstream."
        ::= { zxGponOntPerf1DayIntervalEntry 3}

   zxGponOntH1DGemPayloadBytesUp OBJECT-TYPE
        SYNTAX      Counter64
        MAX-ACCESS  read-only
        STATUS      current
        DESCRIPTION
            "The 1 day interval payload bytes of
             GEM frames upstream."
        ::= { zxGponOntPerf1DayIntervalEntry 4}

   zxGponOntH1DCorrEtherFrmUp OBJECT-TYPE
        SYNTAX      Counter64
        MAX-ACCESS  read-only
        STATUS      current
        DESCRIPTION
            "The 1 day interval correct ethernet
             frames upstream."
        ::= { zxGponOntPerf1DayIntervalEntry 5}

   zxGponOntH1DErroredEtherFrmUp OBJECT-TYPE
        SYNTAX      Counter64
        MAX-ACCESS  read-only
        STATUS      current
        DESCRIPTION
            "The 1 day interval error ethernet
             frames upstream."
        ::= { zxGponOntPerf1DayIntervalEntry 6}

   zxGponOntH1DTotlOmciFrmUp OBJECT-TYPE
        SYNTAX      Counter64
        MAX-ACCESS  read-only
        STATUS      current
        DESCRIPTION
            "The 1 day interval OMCI frames
             upstream."
        ::= { zxGponOntPerf1DayIntervalEntry 7}

   zxGponOntH1DErri OBJECT-TYPE
        SYNTAX      Counter64
        MAX-ACCESS  read-only
        STATUS      current
        DESCRIPTION
            "The 1 day interval bip errors
             detected on OLT side."
        ::= { zxGponOntPerf1DayIntervalEntry 8}

   zxGponOntH1DReii OBJECT-TYPE
        SYNTAX      Counter64
        MAX-ACCESS  read-only
        STATUS      current
        DESCRIPTION
            "The 1 day interval bip errors
             detected on ONU side."
        ::= { zxGponOntPerf1DayIntervalEntry 9}

   zxGponOntH1DUnrxBurstsUp OBJECT-TYPE
        SYNTAX      Counter64
        MAX-ACCESS  read-only
        STATUS      current
        DESCRIPTION
            "The 1 day interval lost brust."
        ::= { zxGponOntPerf1DayIntervalEntry 10}

   zxGponOntH1DBipErrorUp OBJECT-TYPE
        SYNTAX      Counter64
        MAX-ACCESS  read-only
        STATUS      current
        DESCRIPTION
            "The 1 day interval bip errors
             upstream."
        ::= { zxGponOntPerf1DayIntervalEntry 11}

   zxGponOntH1DCorrBitsUp OBJECT-TYPE
        SYNTAX      Counter64
        MAX-ACCESS  read-only
        STATUS      current
        DESCRIPTION
            "The 1 day interval corrected
             bits upstream."
        ::= { zxGponOntPerf1DayIntervalEntry 12}

   zxGponOntH1DNotCorrWordsUp OBJECT-TYPE
        SYNTAX      Counter64
        MAX-ACCESS  read-only
        STATUS      current
        DESCRIPTION
            "The 1 day interval not
             corrected words."
        ::= { zxGponOntPerf1DayIntervalEntry 13}
        
   zxGponOntH1DCorrNonIdleGemFrmDn OBJECT-TYPE
        SYNTAX      Counter64
        MAX-ACCESS  read-only
        STATUS      current
        DESCRIPTION
            "The 1 day interval OLT sent to 
            ONU correct non-idle GEM frames."
        ::= { zxGponOntPerf1DayIntervalEntry 14}
        
   zxGponOntH1DTxOmciFrms OBJECT-TYPE
        SYNTAX      Counter64
        MAX-ACCESS  read-only
        STATUS      current
        DESCRIPTION
            "The 1 day interval
             OLT sent to ONU OMCI frames."
        ::= { zxGponOntPerf1DayIntervalEntry 15}
        
   zxGponOntH1DTxPloamFrms OBJECT-TYPE
        SYNTAX      Counter64
        MAX-ACCESS  read-only
        STATUS      current
        DESCRIPTION
            "The 1 day interval
             OLT sent to ONU Ploam frames."
        ::= { zxGponOntPerf1DayIntervalEntry 16}
        
   zxGponOntH1DRxPloamFrms OBJECT-TYPE
        SYNTAX      Counter64
        MAX-ACCESS  read-only
        STATUS      current
        DESCRIPTION
            "The 1 day interval
             OLT received from ONU Ploam frames."
        ::= { zxGponOntPerf1DayIntervalEntry 17}
        
   zxGponOntH1DLofiAlarms OBJECT-TYPE
        SYNTAX      Counter64
        MAX-ACCESS  read-only
        STATUS      current
        DESCRIPTION
            "The 1 day interval
             lofi alarm times."
        ::= { zxGponOntPerf1DayIntervalEntry 18}
        
   zxGponOntH1DFecCorrBytes OBJECT-TYPE
        SYNTAX      Counter64
        MAX-ACCESS  read-only
        STATUS      current
        DESCRIPTION
            "The 1 day interval error
             bytes which have been corrected by FEC."
        ::= { zxGponOntPerf1DayIntervalEntry 19}
    
   zxGponOntH1DFecCorrWords OBJECT-TYPE
        SYNTAX      Counter64
        MAX-ACCESS  read-only
        STATUS      current
        DESCRIPTION
            "The 1 day interval error 
            codewords which have been corrected by FEC."
        ::= { zxGponOntPerf1DayIntervalEntry 20}
        
   zxGponOntH1DFecUnCorrWords OBJECT-TYPE
        SYNTAX      Counter64
        MAX-ACCESS  read-only
        STATUS      current
        DESCRIPTION
            "The 1 day interval error codewords
             which haven't been corrected by FEC."
        ::= { zxGponOntPerf1DayIntervalEntry 21}

   zxGponOntH1DFecTotalRxWords OBJECT-TYPE
        SYNTAX      Counter64
        MAX-ACCESS  read-only
        STATUS      current
        DESCRIPTION
            "The 1 day interval received
             codewords by FEC."
        ::= { zxGponOntPerf1DayIntervalEntry 22}
        
   zxGponOntH1DCrcErrPkts OBJECT-TYPE
        SYNTAX      Counter64
        MAX-ACCESS  read-only
        STATUS      current
        DESCRIPTION
            "The 1 day interval error
             packets by CRC."
        ::= { zxGponOntPerf1DayIntervalEntry 23}    
        
   zxGponOntH1DValidData OBJECT-TYPE
        SYNTAX      TruthValue
        MAX-ACCESS  read-only
        STATUS      current
        DESCRIPTION     
             "Performance data valid flag. 
              true(1) means valid.  
              false(2) means invalid and the performace data is useless."
        ::= { zxGponOntPerf1DayIntervalEntry 100} 

zxAnGponGemportPerfMgmt         OBJECT IDENTIFIER ::= { zxGponRootMib 33}   

--------------------------------------------------------------------------------
-- zxGponGemPortCurrPerfTable
--------------------------------------------------------------------------------
   zxGponGemPortCurrPerfTable OBJECT-TYPE
        SYNTAX      SEQUENCE OF ZxGponGemPortCurrPerfEntry
        MAX-ACCESS  not-accessible
        STATUS      current
        DESCRIPTION
            "The GPON GEM port current performance data table" 
        ::= { zxAnGponGemportPerfMgmt 2 }

    zxGponGemPortCurrPerfEntry OBJECT-TYPE
        SYNTAX      ZxGponGemPortCurrPerfEntry
        MAX-ACCESS  not-accessible
        STATUS      current
        DESCRIPTION
            "The entry in the GEM port current performance data table."
        INDEX   { zxGponMgmtPonOltId, zxGponMgmtPonOnuId, zxGponGemPortIdx }
        ::= { zxGponGemPortCurrPerfTable 1 }

    ZxGponGemPortCurrPerfEntry ::=
    SEQUENCE {
        zxGponGemPortRxOctets                     Counter64,
        zxGponGemPortRxUcastPkts                  Counter64,
        zxGponGemPortRxBroadcastPkts              Counter64,
        zxGponGemPortRxMulticastPkts              Counter64,
        zxGponGemPortRxDiscards                   Counter64,
        zxGponGemPortTxOctets                     Counter64,
        zxGponGemPortTxUcastPkts                  Counter64,
        zxGponGemPortTxBroadcastPkts              Counter64,
        zxGponGemPortTxMulticastPkts              Counter64,
        zxGponGemPortTxDiscards                   Counter64,
        zxGponGemPortRxOctetRate                  Gauge32,
        zxGponGemPortRxOctetPeakRate              Gauge32,
        zxGponGemPortTxOctetRate                  Gauge32,
        zxGponGemPortTxOctetPeakRate              Gauge32,
        zxGponGemPortPerfCapability               BITS,
        zxGponGemPortCurrReset                    INTEGER,
        zxGponGemPortCurrRowStatus                RowStatus
        }

   zxGponGemPortRxOctets OBJECT-TYPE
        SYNTAX      Counter64
        MAX-ACCESS  read-only
        STATUS      current
        DESCRIPTION
            "The total number of octets received on the interface,
            including framing characters."
        ::= { zxGponGemPortCurrPerfEntry 1}

   zxGponGemPortRxUcastPkts OBJECT-TYPE
        SYNTAX      Counter64
        MAX-ACCESS  read-only
        STATUS      current
        DESCRIPTION
            "The number of packets, delivered by this sub-layer to a
            higher (sub-)layer, which were not addressed to a multicast
            or broadcast address at this sub-layer.  This object is a
            64-bit version of ifInUcastPkts"
        ::= { zxGponGemPortCurrPerfEntry 2}

   zxGponGemPortRxBroadcastPkts OBJECT-TYPE
        SYNTAX      Counter64
        MAX-ACCESS  read-only
        STATUS      current
        DESCRIPTION
            "The number of packets, delivered by this sub-layer to a
            higher (sub-)layer, which were addressed to a broadcast
            address at this sub-layer."
        ::= { zxGponGemPortCurrPerfEntry 3}

   zxGponGemPortRxMulticastPkts OBJECT-TYPE
        SYNTAX      Counter64
        MAX-ACCESS  read-only
        STATUS      current
        DESCRIPTION
            "The number of packets, delivered by this sub-layer to a
            higher (sub-)layer, which were addressed to a multicast
            address at this sub-layer.  For a MAC layer protocol, this
            includes both Group and Functional addresses."
        ::= { zxGponGemPortCurrPerfEntry 4}

   zxGponGemPortRxDiscards OBJECT-TYPE
        SYNTAX      Counter64
        MAX-ACCESS  read-only
        STATUS      current
        DESCRIPTION
            "The number of inbound packets which were chosen to be
            discarded even though no errors had been detected to prevent
            their being deliverable to a higher-layer protocol.  One
            possible reason for discarding such a packet could be to
            free up buffer space."
        ::= { zxGponGemPortCurrPerfEntry 5}

   zxGponGemPortTxOctets OBJECT-TYPE
        SYNTAX      Counter64
        MAX-ACCESS  read-only
        STATUS      current
        DESCRIPTION
            "The total number of octets transmitted out of the
            interface, including framing characters. "
        ::= { zxGponGemPortCurrPerfEntry 6}

   zxGponGemPortTxUcastPkts OBJECT-TYPE
        SYNTAX      Counter64
        MAX-ACCESS  read-only
        STATUS      current
        DESCRIPTION
            "The total number of packets that higher-level protocols
            requested be transmitted, and which were not addressed to a
            multicast or broadcast address at this sub-layer, including
            those that were discarded or not sent."
        ::= { zxGponGemPortCurrPerfEntry 7}

   zxGponGemPortTxBroadcastPkts OBJECT-TYPE
        SYNTAX      Counter64
        MAX-ACCESS  read-only
        STATUS      current
        DESCRIPTION
            "The total number of packets that higher-level protocols
            requested be transmitted, and which were addressed to a
            broadcast address at this sub-layer, including those that
            were discarded or not sent."
        ::= { zxGponGemPortCurrPerfEntry 8}

   zxGponGemPortTxMulticastPkts OBJECT-TYPE
        SYNTAX      Counter64
        MAX-ACCESS  read-only
        STATUS      current
        DESCRIPTION
            "The total number of packets that higher-level protocols
            requested be transmitted, and which were addressed to a
            multicast address at this sub-layer, including those that
            were discarded or not sent.  For a MAC layer protocol, this
            includes both Group and Functional addresses. "
        ::= { zxGponGemPortCurrPerfEntry 9}

   zxGponGemPortTxDiscards OBJECT-TYPE
        SYNTAX      Counter64
        MAX-ACCESS  read-only
        STATUS      current
        DESCRIPTION
            "The number of outbound packets which were chosen to be
            discarded even though no errors had been detected to prevent
            their being transmitted.  One possible reason for discarding
            such a packet could be to free up buffer space."
        ::= { zxGponGemPortCurrPerfEntry 10}  
        
   zxGponGemPortRxOctetRate OBJECT-TYPE
        SYNTAX       Gauge32
        UNITS        "Bps"  
        MAX-ACCESS   read-only
        STATUS       current
        DESCRIPTION
            "Received bytes per second."
        ::= {zxGponGemPortCurrPerfEntry 11 }
        
   zxGponGemPortRxOctetPeakRate OBJECT-TYPE
        SYNTAX       Gauge32
        UNITS        "Bps"  
        MAX-ACCESS   read-only
        STATUS       current
        DESCRIPTION
            "Peak rate of received octets."
         ::= {zxGponGemPortCurrPerfEntry 12 }
         
   zxGponGemPortTxOctetRate OBJECT-TYPE
        SYNTAX       Gauge32
        UNITS        "Bps"  
        MAX-ACCESS   read-only
        STATUS       current
        DESCRIPTION
            "Transmitted rate of octets."
         ::= {zxGponGemPortCurrPerfEntry 13 }
         
   zxGponGemPortTxOctetPeakRate OBJECT-TYPE
        SYNTAX       Gauge32
        UNITS        "Bps"  
        MAX-ACCESS   read-only
        STATUS       current
        DESCRIPTION
            "Peak rate of transmitted octets."
         ::= {zxGponGemPortCurrPerfEntry 14 }
         
   zxGponGemPortPerfCapability OBJECT-TYPE 
         SYNTAX      BITS 
           {
               zxGponGemPortRxOctets(0),
               zxGponGemPortRxUcastPkts(1),
               zxGponGemPortRxBroadcastPkts(2),
               zxGponGemPortRxMulticastPkts(3),
               zxGponGemPortRxDiscards(4),
               zxGponGemPortTxOctets(5),
               zxGponGemPortTxUcastPkts(6),
               zxGponGemPortTxBroadcastPkts(7),
               zxGponGemPortTxMulticastPkts(8),
               zxGponGemPortTxDiscards(9),
               zxGponGemPortRxOctetRate(10),
               zxGponGemPortRxOctetPeakRate(11),
               zxGponGemPortTxOctetRate(12),
               zxGponGemPortTxOctetPeakRate(13)
           }             
        MAX-ACCESS  read-only
        STATUS      current
        DESCRIPTION     
            "The attribute indicates that the supports of GPON GEM port
             performance, each bit from left to right represents the support 
             of performance statistic from top to bottom in this MIB table, 
             value 1 represents support and value 0 is not support.
             And the supports of C15M,C1D,H15M,H1D performance statistics 
             decided by zxGponGemPortPerfCapability also." 
        ::= { zxGponGemPortCurrPerfEntry 99 } 
        
   zxGponGemPortCurrReset OBJECT-TYPE 
        SYNTAX      INTEGER
            {
                perfReset(1)
            }
        MAX-ACCESS  read-write
        STATUS      current
        DESCRIPTION     
            "Clear all the current performance variables.
            When get this variable, always return 1."
        ::= { zxGponGemPortCurrPerfEntry 100 }  
        
   zxGponGemPortCurrRowStatus  OBJECT-TYPE 
        SYNTAX      RowStatus
        MAX-ACCESS  read-create
        STATUS      current
        DESCRIPTION     
            "The status of this conceptual row. 
              
             The supported actions of this conceptual row only include:
             'createAndGo' and 'destroy'.

             To create a row in this table, a manager must
             set this object to createAndGo(4).
            
             To delete a row in this table, a manager must
             set this object to destroy(6).
             
             To query this object, always return 1."
        ::= { zxGponGemPortCurrPerfEntry 101 }         
 
zxAnGponVportPerfMgmt         OBJECT IDENTIFIER ::= { zxGponRootMib 34}   

--------------------------------------------------------------------------------
-- zxGponVportCurrPerfTable
--------------------------------------------------------------------------------
   zxGponVportCurrPerfTable OBJECT-TYPE
        SYNTAX      SEQUENCE OF ZxGponVportCurrPerfEntry
        MAX-ACCESS  not-accessible
        STATUS      current
        DESCRIPTION
            "Enable/disable the interface GPON vport Statisic." 
        ::= { zxAnGponVportPerfMgmt 2 }

    zxGponVportCurrPerfEntry OBJECT-TYPE
        SYNTAX      ZxGponVportCurrPerfEntry
        MAX-ACCESS  not-accessible
        STATUS      current
        DESCRIPTION
            "It is entry in the table zxGponVportCurrPerfTable."
        INDEX   { zxGponMgmtPonOltId, zxGponMgmtPonOnuId, 
                  zxGponMgmtPonOnuBpIndex }
        ::= { zxGponVportCurrPerfTable 1 }

    ZxGponVportCurrPerfEntry ::=
    SEQUENCE {
        zxGponVportCurrRowStatus                RowStatus
        } 
                
   zxGponVportCurrRowStatus  OBJECT-TYPE 
        SYNTAX      RowStatus
        MAX-ACCESS  read-create
        STATUS      current
        DESCRIPTION     
            "The status of this conceptual row. 
              
             The supported actions of this conceptual row only include:
             'createAndGo' and 'destroy'.

             To create a row in this table, a manager must
             set this object to createAndGo(4).
            
             To delete a row in this table, a manager must
             set this object to destroy(6).
             
             To query this object, always return 1."
        ::= { zxGponVportCurrPerfEntry 101 }  
                
  zxGponTraps          OBJECT IDENTIFIER ::= { zxGponRootMib 45}    
      
  zxGponTrapsBindVar          OBJECT IDENTIFIER ::= { zxGponTraps 1}    

    zxGponOltRxPowerAlarmiReason OBJECT-TYPE
        SYNTAX      INTEGER
                        {
                        toohigh(1),
                        toolow(2)
                        }
        MAX-ACCESS  read-only
        STATUS      current
        DESCRIPTION
                ""
        ::= { zxGponTrapsBindVar 1 }   

    zxGponOltRxPowerAbnormalInformiReason OBJECT-TYPE
        SYNTAX      INTEGER
                        {
                        toohigh(1),
                        toolow(2)
                        }
        MAX-ACCESS  read-only
        STATUS      current
        DESCRIPTION
                ""
        ::= { zxGponTrapsBindVar 2 }   

    zxGponOltTxPowerAlarmReason OBJECT-TYPE
        SYNTAX      INTEGER
                        {
                        toohigh(1),
                        toolow(2)
                        }
        MAX-ACCESS  read-only
        STATUS      current
        DESCRIPTION
                ""
        ::= { zxGponTrapsBindVar 3 }   

    zxGponOltTxPowerAbnormalInformReason OBJECT-TYPE
        SYNTAX      INTEGER
                        {
                        toohigh(1),
                        toolow(2)
                        }
        MAX-ACCESS  read-only
        STATUS      current
        DESCRIPTION
                ""
        ::= { zxGponTrapsBindVar 4 }   

    zxGponTrapEventString OBJECT-TYPE
        SYNTAX      OCTET STRING(SIZE (0..255))
        MAX-ACCESS  read-only
        STATUS      current
        DESCRIPTION
                "GPON trap event string."
        ::= { zxGponTrapsBindVar 5 }
        
        
    zxGponOnuActType OBJECT-TYPE
        SYNTAX      OCTET STRING(SIZE(0..128))
        MAX-ACCESS  read-only
        STATUS      current
        DESCRIPTION
                "GPON ONU Actual type"
        ::= { zxGponTrapsBindVar 6 }
        
    zxGponOnuIpMacAntiSpoofingMac OBJECT-TYPE
        SYNTAX      MacAddress
        MAX-ACCESS  read-only
        STATUS      current
        DESCRIPTION
            "The spoofing MAC of packets."
        ::= { zxGponTrapsBindVar 7 }  
        
    zxGponOnuIpMacAntiSpoofingIp OBJECT-TYPE
        SYNTAX      IpAddress
        MAX-ACCESS  read-only
        STATUS      current
        DESCRIPTION
            "The spoofing IP of packets."
        ::= { zxGponTrapsBindVar 8 }  
        
    zxGponOnuIpMacAntiSpoofingIndex OBJECT-TYPE
        SYNTAX      INTEGER(1..256)
        MAX-ACCESS  read-only
        STATUS      current
        DESCRIPTION
                "A unique value, greater than zero, for each interface. 
                This value indicate This value identifies the interface
                which occurred IP/MAC spoofing."
        ::= { zxGponTrapsBindVar 9 }
        
    zxGponOnuRegistrationInfo OBJECT-TYPE
        SYNTAX      OCTET STRING(SIZE (0..255))
        MAX-ACCESS  read-only
        STATUS      current
        DESCRIPTION
            "ONU registration information.
             This attribute is made up of registration mode and registration
             values. Commas are used to separate registration mode
             and registration values. A number is used to represent
             registration mode of the attribute. The number's value is 
             on the list of zxGponOntRegMode defined values. 
             Correspondingly, the registration values' formats are also
             defined in zxGponOntRegMode's description.
             
             The valid ONU registration information formats are as follows:
                 1,sn
                 2,password
                 3,sn,password
                 4,register Id
                 5,register Id,8021x
                 6,register Id,mutual
                 7,telefonica password
                 8,sn,telefonica password
                 9,loid
                 10,loid,password"
        ::= { zxGponTrapsBindVar 10 }
        
    zxGponOnuLoidAuthResult OBJECT-TYPE
        SYNTAX      INTEGER
                        {
                        authSuccess(1),
                        loidError(2),
                        loidPwError(3),
                        loidDuplicate(4)
                        }
        MAX-ACCESS  accessible-for-notify
        STATUS      current
        DESCRIPTION
                "ONU LOID authentication information."
        ::= { zxGponTrapsBindVar 11 } 
        
    zxGponOltLosReason OBJECT-TYPE
        SYNTAX      INTEGER
                        {
                        allOnuDyingGasp(1),
                        fiberBroken(2),
                        allOnuOffline(3),
                        otherReasons(4)
                        }
        MAX-ACCESS  accessible-for-notify
        STATUS      current
        DESCRIPTION
                "OLT LOS Reason                
                 allOnuDyingGasp:all online ONU under the PON port are 
                                 dying gasp.
                 fiberBroken:trunk or branch fiber is broken.
                 allOnuOffline:all ONU under the PON port are offline.
                 otherReason:other reasons."
        ::= { zxGponTrapsBindVar 12 } 

    zxGponOltLOSi        NOTIFICATION-TYPE
        OBJECTS {
            ifIndex,
            zxGponOntDevMgmtName,
            zxGponOntDevMgmtTypeName,
            zxGponOntDevMgmtDescription,
            zxGponOnuRegistrationInfo
        }
        STATUS  current
        DESCRIPTION 
            "LOSi is Loss of signal for ONUi. Generate notification."
        ::={zxGponTraps 101}             
         
    zxGponOltLosiRestore  NOTIFICATION-TYPE
        OBJECTS {
            ifIndex,
            zxGponOntDevMgmtName,
            zxGponOntDevMgmtTypeName,
            zxGponOntDevMgmtDescription,
            zxGponOnuRegistrationInfo
        }
        STATUS  current
        DESCRIPTION 
            "LOSi is Loss of signal for ONUi.When the OLT receives 
            a valid optical signal from ONUi, Alarm is restored"
        ::={zxGponTraps 102} 
          
    zxGponOltLOFi        NOTIFICATION-TYPE
        OBJECTS {
            ifIndex,
            zxGponOntDevMgmtName,
            zxGponOntDevMgmtTypeName,
            zxGponOntDevMgmtDescription,
            zxGponOnuRegistrationInfo
        }
        STATUS  current
        DESCRIPTION 
            "LOFi is Loss of Frame of ONUi. Send 3 times 
            Deactivate_ONU-ID messages. Generate Loss_of_phy_layer_I 
            notification."
        ::={zxGponTraps 103}
        
    zxGponOltLOFiRestore        NOTIFICATION-TYPE
        OBJECTS {
            ifIndex,
            zxGponOntDevMgmtName,
            zxGponOntDevMgmtTypeName,
            zxGponOntDevMgmtDescription,
            zxGponOnuRegistrationInfo
        }
        STATUS  current
        DESCRIPTION 
            "LOFi is Loss of Frame of ONUi. When frame delineation 
            for ONUi is achieved in the operating state."
        ::={zxGponTraps 104}
                
    zxGponOltDOWi        NOTIFICATION-TYPE
        OBJECTS {
            ifIndex,
            zxGponOntDevMgmtName,
            zxGponOntDevMgmtTypeName,
            zxGponOntDevMgmtDescription,
            zxGponOnuRegistrationInfo
        }
        STATUS  current
        DESCRIPTION 
            "DOWi is Drift of Window of ONUi. Send modified EqD to the ONUi."
        ::={zxGponTraps 105}
                
    zxGponOltDOWiRestore   NOTIFICATION-TYPE
        OBJECTS {
            ifIndex,
            zxGponOntDevMgmtName,
            zxGponOntDevMgmtTypeName,
            zxGponOntDevMgmtDescription,
            zxGponOnuRegistrationInfo
        }
        STATUS current
        DESCRIPTION 
        "DOWi is Drift of Window of ONUi. When the OLT 
        receives the ONUi Transmission in the correct position."
        ::={zxGponTraps 106}
             
    zxGponOltSFi        NOTIFICATION-TYPE
        OBJECTS {
            ifIndex,
            zxGponOntDevMgmtName,
            zxGponOntDevMgmtTypeName,
            zxGponOntDevMgmtDescription,
            zxGponOnuRegistrationInfo
        }
        STATUS current
        DESCRIPTION 
            "SFi is Signal Fail of ONUi. Send 3 times 
            Deactivate_ONU-ID messages. Generate Loss_of_phy_layer_I 
            notification."
        ::={zxGponTraps 107}
                
    zxGponOltSFiRestore  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "SFi is Signal Fail of ONUi.When the upstream 
            BER of ONUi becomes <10?y+1, this state is cleared."
        ::={zxGponTraps 108}
        
    zxGponOltSDi       NOTIFICATION-TYPE
        OBJECTS {
            ifIndex,
            zxGponOntDevMgmtName,
            zxGponOntDevMgmtTypeName,
            zxGponOntDevMgmtDescription,
            zxGponOnuRegistrationInfo
        }
        STATUS current
        DESCRIPTION 
            "SDi is Signal Degraded of ONUi."
        ::={zxGponTraps 109}
        
    zxGponOltSDiRestore  NOTIFICATION-TYPE
        OBJECTS {
            ifIndex,
            zxGponOntDevMgmtName,
            zxGponOntDevMgmtTypeName,
            zxGponOntDevMgmtDescription,
            zxGponOnuRegistrationInfo
        }
        STATUS current
        DESCRIPTION 
        "SDi is Signal Degraded of ONUi. When the upstream 
        BER of ONUi becomes <10?X+1, this state is cleared."
        ::={zxGponTraps 110}
        
    zxGponOltLCDAi     NOTIFICATION-TYPE
        OBJECTS {
            ifIndex,
            zxGponOntDevMgmtName,
            zxGponOntDevMgmtTypeName,
            zxGponOntDevMgmtDescription,
            zxGponOnuRegistrationInfo
        }
        STATUS current
        DESCRIPTION 
            "LCDAi is Loss of ATM channel delineation. 
            Send 3 times Deactivate_ONU-ID messages Generate
            Loss_of_phy_layer_I notification."
        ::={zxGponTraps 111}
            
    zxGponOltLCDAiRestore  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "LCDAi is Loss of ATM channel delineation. When 
            cell delineation for ONUi is achieved."
        ::={zxGponTraps 112}
        
    zxGponOltLCDGi    NOTIFICATION-TYPE
        OBJECTS {
            ifIndex,
            zxGponOntDevMgmtName,
            zxGponOntDevMgmtTypeName,
            zxGponOntDevMgmtDescription,
            zxGponOnuRegistrationInfo
        }
        STATUS current
        DESCRIPTION 
            "LCDGi is Loss of GEM channel delineation. 
            Send 3 times Deactivate_ONU-ID messages Generate
            Loss_of_phy_layer_I notification."
        ::={zxGponTraps 113}
        
    zxGponOltLCDGiRestore    NOTIFICATION-TYPE
        OBJECTS {
            ifIndex,
            zxGponOntDevMgmtName,
            zxGponOntDevMgmtTypeName,
            zxGponOntDevMgmtDescription,
            zxGponOnuRegistrationInfo
        }
        STATUS current
        DESCRIPTION 
            "LCDGi is Loss of GEM channel delineation. When 
            GEM channel delineation for ONUi is achieved."
        ::={zxGponTraps 114}
              
    zxGponOltRDIi    NOTIFICATION-TYPE
        OBJECTS {
            ifIndex,
            zxGponOntDevMgmtName,
            zxGponOntDevMgmtTypeName,
            zxGponOntDevMgmtDescription,
            zxGponOnuRegistrationInfo
        }
        STATUS current
        DESCRIPTION 
            "RDIi is Remote Defect Indication of ONUi."
        ::={zxGponTraps 115}
            
    zxGponOltRDIiRestore   NOTIFICATION-TYPE
        OBJECTS {
            ifIndex,
            zxGponOntDevMgmtName,
            zxGponOntDevMgmtTypeName,
            zxGponOntDevMgmtDescription,
            zxGponOnuRegistrationInfo
        }
        STATUS current
        DESCRIPTION 
            "RDIi is Remote Defect Indication of ONUi. When the RDI field of 
            ONUi is de-asserted."
        ::={zxGponTraps 116}
             
    zxGponOltSUFi  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "SUFi is Start-up Failure of ONUi. Send 3 times Deactivate_ONU-ID messages."
        ::={zxGponTraps 117}
                
    zxGponOltSUFiRestore   NOTIFICATION-TYPE
        OBJECTS {
            ifIndex,
            zxGponOntDevMgmtName,
            zxGponOntDevMgmtTypeName,
            zxGponOntDevMgmtDescription,
            zxGponOnuRegistrationInfo
        }
        STATUS current
        DESCRIPTION 
            "SUFi is Start-up Failure of ONUi. The ONU is ranged successfully."
        ::={zxGponTraps 118}        
        
    zxGponOltDFi  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "DFi is Deactivate Failure of ONUi."
        ::={zxGponTraps 119}
                
    zxGponOltDFiRestore  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "DFi is Deactivate Failure of ONUi. Cancelled by the operator."
        ::={zxGponTraps 120}
                
    zxGponOltLOAi  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "LOAi is Loss of Acknowledge with ONUi. Send 3 times 
            Deactivate_ONU-ID messages. Generate Loss_of_phy_layer_I 
            notification."
        ::={zxGponTraps 121}
        
    zxGponOltLOAiRestore  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "LOAi is Loss of Acknowledge with ONUi. When the OLT 
            receives an acknowledgement from the ONU."
        ::={zxGponTraps 122}        
            
    zxGponOltDGi  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "DGi is Receive Dying-Gasp of ONUi. Ignore received 
            alarms from this ONU. Generate Loss_of_phy_layer_I 
            notification."
        ::={zxGponTraps 123}
                
    zxGponOltDGiRestore  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "DGi is Receive Dying-Gasp of ONUi. When the OLT receives
             a PLOAM message during ranging process."
        ::={zxGponTraps 124}
        
    zxGponOltLOAMi  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "LOAMi is Loss of PLOAM for ONUi. Send 3 times 
            Deactivate_ONU-ID messages. Generate Loss_of_phy_layer_I 
            notification."
        ::={zxGponTraps 125}
                
    zxGponOltLOAMiRestore  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "LOAMi is Loss of PLOAM for ONUi. When the OLT receives 
            a PLOAM message corresponding to its PLOAM flag in the 
            Operating state."
        ::={zxGponTraps 126}
                
    zxGponOltMEMi  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "MEMi is Message_Error Message from ONUi."
        ::={zxGponTraps 127}
                
    zxGponOltMEMiRestore  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "MEMi is Message_Error Message from ONUi. When 
            the operator is informed."
        ::={zxGponTraps 128}
                
    zxGponOltMISi  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "Misi is Link Mismatch of ONUi."
        ::={zxGponTraps 129}
                
    zxGponOltMISiRestore  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "MISi is Link Mismatch of ONUi. The OLT detects 
            that received PSTi and the transmitted PST are the same."
        ::={zxGponTraps 130}
                
    zxGponOltPEEi  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "PEEi is Physical Equipment Error of ONUi. 
            Generate Loss_of_physical_layer_I notification."
        ::={zxGponTraps 131}
              
    zxGponOltPEEiRestore  NOTIFICATION-TYPE
        OBJECTS {
            ifIndex,
            zxGponOntDevMgmtName,
            zxGponOntDevMgmtTypeName,
            zxGponOntDevMgmtDescription,
            zxGponOnuRegistrationInfo
        }
        STATUS current
        DESCRIPTION 
            "PEEi is Physical Equipment Error of ONUi. When 
            the OLT doesn't receive a PEE message from the ONUi in 3 s."
        ::={zxGponTraps 132}
                
    zxGponOntLOS    NOTIFICATION-TYPE
        OBJECTS {
                ifIndex
                }
        STATUS current
        DESCRIPTION 
            "LOS is Loss Of Signal. Switch off laser. Generate 
            Loss_of_phy_layer notification. Move to Initial- State."
        ::={zxGponTraps 133}
                
    zxGponOntLOSRestore    NOTIFICATION-TYPE
        OBJECTS {
                ifIndex
                }
        STATUS current
        DESCRIPTION 
            "LOS is Loss Of Signal. Valid optical signal."
        ::={zxGponTraps 134}
                
    zxGponOntLOF    NOTIFICATION-TYPE
        OBJECTS {
                ifIndex
                }
        STATUS current
        DESCRIPTION 
            "LOF is Loss of Frame. Switch off laser. Generate 
            Loss_of_phy_layer notification. Move to Initial- State."
        ::={zxGponTraps 135}
                
    zxGponOntLOFRestore    NOTIFICATION-TYPE
        OBJECTS {
                ifIndex
                }
        STATUS current
        DESCRIPTION 
            "LOF is Loss of Frame. When 2 consecutive frames 
            have correct PSYNC."
        ::={zxGponTraps 136}
                
    zxGponOntTF    NOTIFICATION-TYPE
        OBJECTS {
                ifIndex
                }
        STATUS current
        DESCRIPTION 
            "TF is Transmitter Failure."
        ::={zxGponTraps 137}
                
    zxGponOntTFRestore    NOTIFICATION-TYPE
        OBJECTS {
                ifIndex
                }
        STATUS current
        DESCRIPTION 
            "TF is Transmitter Failure."
        ::={zxGponTraps 138}
                
    zxGponOntSF    NOTIFICATION-TYPE
        OBJECTS {
                ifIndex
                }
        STATUS current
        DESCRIPTION 
            "SF is Signal Failed."
        ::={zxGponTraps 139}
                
    zxGponOntSFRestore    NOTIFICATION-TYPE
        OBJECTS {
                ifIndex
                }
        STATUS current
        DESCRIPTION 
            "SF is Signal Failed. Set inactive when 
            the downstream BER is <10?(y+1)."
        ::={zxGponTraps 140}
                
    zxGponOntSD    NOTIFICATION-TYPE
        OBJECTS {
                ifIndex
                }
        STATUS current
        DESCRIPTION 
            "SD is Signal Degraded."
        ::={zxGponTraps 141}
                
    zxGponOntSDRestore    NOTIFICATION-TYPE
        OBJECTS {
                ifIndex
                }
        STATUS current
        DESCRIPTION 
            "SD is Signal Degraded. Set inactive 
            when the downstream BER is <10?(x+1)."
        ::={zxGponTraps 142}
                
    zxGponOntLCDA    NOTIFICATION-TYPE
        OBJECTS {
                ifIndex
                }
        STATUS current
        DESCRIPTION 
            "LCDA is Loss of ATM channel delineation. 
            Switch off laser. Generate Loss_of_phy_layer 
            notification."
        ::={zxGponTraps 143}
                
    zxGponOntLCDARestore    NOTIFICATION-TYPE
        OBJECTS {
                ifIndex
                }
        STATUS current
        DESCRIPTION 
            "LCDA is Loss of ATM channel delineation. 
        When cell delineation is achieved."
        ::={zxGponTraps 144}
              
    zxGponOntLCDG    NOTIFICATION-TYPE
        OBJECTS {
                ifIndex
                }
        STATUS current
        DESCRIPTION 
            "LCDG is Loss of GEM channel delineation. 
        Switch off laser. Generate Loss_of_phy_layer 
        notification."
        ::={zxGponTraps 145}
                
    zxGponOntLCDGRestore    NOTIFICATION-TYPE
        OBJECTS {
                ifIndex
                }
        STATUS current
        DESCRIPTION 
            "LCDG is Loss of GEM channel delineation. 
        When GEM delineation is achieved."
        ::={zxGponTraps 146}
                
    zxGponOntRDI    NOTIFICATION-TYPE
        OBJECTS {
                ifIndex
                }
        STATUS current
        DESCRIPTION 
            "RDI is Remote Defect Indication in ONU. Set RDI status bit in PLOu."
        ::={zxGponTraps 147}
                
    zxGponOntRDIRestore    NOTIFICATION-TYPE
        OBJECTS {
                ifIndex
                }
        STATUS current
        DESCRIPTION 
            "RDI is Remote Defect Indication in ONU. When the OLT transmission defect is resolved."
        ::={zxGponTraps 148}           
        
    zxGponOntSUF    NOTIFICATION-TYPE
        OBJECTS {
                ifIndex
                }
        STATUS current
        DESCRIPTION 
            "SUF is Start-up Failure."
        ::={zxGponTraps 149}
                
    zxGponOntSUFRestore    NOTIFICATION-TYPE
        OBJECTS {
                ifIndex
                }
        STATUS current
        DESCRIPTION 
            "SUF is Start-up Failure. When ranging is successful."
        ::={zxGponTraps 150}
                
    zxGponOntMEM    NOTIFICATION-TYPE
        OBJECTS {
                ifIndex
                }
        STATUS current
        DESCRIPTION 
            "MEM is Message Error Message."
        ::={zxGponTraps 151}
                
    zxGponOntMEMRestore    NOTIFICATION-TYPE
        OBJECTS {
                ifIndex
                }
        STATUS current
        DESCRIPTION 
            "MEM is Message Error Message."
        ::={zxGponTraps 152}
               
    zxGponOntDACT    NOTIFICATION-TYPE
        OBJECTS {
                ifIndex
                }
        STATUS current
        DESCRIPTION 
            "DACT is Deactivate ONU-ID. Switch off the 
            laser and go to Standby-State. Generate 
            Loss_of_phy_layer notification."
        ::={zxGponTraps 153}
                
    zxGponOntDACTRestore    NOTIFICATION-TYPE
        OBJECTS {
                ifIndex
                }
        STATUS current
        DESCRIPTION 
            "DACT is Deactivate ONU-ID.Reception of Upstream_overhead message."
        ::={zxGponTraps 154}
                
    zxGponOntDIS    NOTIFICATION-TYPE
        OBJECTS {
                ifIndex
                }
        STATUS current
        DESCRIPTION 
            "DIS is Disabled ONU. Switch off laser. Go to 
            Emergency-Stop State Generate Loss_of_phy_layer 
            notification."
        ::={zxGponTraps 155}
        
    zxGponOntDISRestore    NOTIFICATION-TYPE
        OBJECTS {
                ifIndex
                }
        STATUS current
        DESCRIPTION 
            "DIS is Disabled ONU. When the ONU receives a Disable_Serial_Number
            message with Enable flag=0x0F or when it receives a Disable_Serial_Number 
            message with it's own serial number and the enable flag=0x00."
        ::={zxGponTraps 156}
                
    zxGponOntMIS    NOTIFICATION-TYPE
        OBJECTS {
                ifIndex
                }
        STATUS current
        DESCRIPTION 
            "MIS is Link Mismatching."
        ::={zxGponTraps 157}
        
    zxGponOntMISRestore    NOTIFICATION-TYPE
        OBJECTS {
                ifIndex
                }
        STATUS current
        DESCRIPTION 
            "MIS is Link Mismatching. The ONU detects that the received 
            PST and transmitted PST are the same."
        ::={zxGponTraps 158}
                
    zxGponOntPee    NOTIFICATION-TYPE
        OBJECTS {
                ifIndex
                }
        STATUS current
        DESCRIPTION 
            "Pee is Physical Equipment Error. Generate Loss_of_physical_layer notification."
        ::={zxGponTraps 159}
                
    zxGponOntPeeRestore    NOTIFICATION-TYPE
        OBJECTS {
                ifIndex
                }
        STATUS current
        DESCRIPTION 
            "Pee is Physical Equipment Error. When the ONU doesn't receive a PEE message in 3 s."
        ::={zxGponTraps 160}
        
    zxGponOltLOS    NOTIFICATION-TYPE
        OBJECTS {
                ifIndex,zxGponOltLosReason
                }
        STATUS current
        DESCRIPTION 
            "LOS is Loss Of Signal. Switch off laser. Generate 
            Loss_of_phy_layer notification. Move to Initial- State."
        ::={zxGponTraps 161}
        
    zxGponOltLOSRestore    NOTIFICATION-TYPE
        OBJECTS {
                ifIndex,zxGponOltLosReason
                }
        STATUS current
        DESCRIPTION 
            "LOS is Loss Of Signal. Valid optical signal."
        ::={zxGponTraps 162}
        
    zxGponOltLOF    NOTIFICATION-TYPE
        OBJECTS {
                ifIndex
                }
        STATUS current
        DESCRIPTION 
            "LOF is Loss of Frame. Switch off laser. Generate 
            Loss_of_phy_layer notification. Move to Initial- State."
        ::={zxGponTraps 163}
        
    zxGponOltLOFRestore    NOTIFICATION-TYPE
        OBJECTS {
                ifIndex
                }
        STATUS current
        DESCRIPTION 
            "LOF is Loss of Frame. When 2 consecutive frames"
        ::={zxGponTraps 164}
                
    zxGponOntRegister  NOTIFICATION-TYPE
        OBJECTS {
                ifIndex 
                }
        STATUS current
        DESCRIPTION 
            " "
        ::={zxGponTraps 165}
                
    zxGponOntUnregister  NOTIFICATION-TYPE
        OBJECTS {
                ifIndex
                }
        STATUS current
        DESCRIPTION 
            ""
        ::={zxGponTraps 166}
            
    zxGponOntAuthPass  NOTIFICATION-TYPE
        OBJECTS {
                ifIndex,zxGponOntCustomAuthPassControl
                }
        STATUS current
        DESCRIPTION 
            ""
        ::={zxGponTraps 167}
        
    zxGponOntAuthFailed  NOTIFICATION-TYPE
        OBJECTS {
                ifIndex
                }
        STATUS current
        DESCRIPTION 
            ""
        ::={zxGponTraps 168} 

    zxPonFanOffLine    NOTIFICATION-TYPE
        OBJECTS {
                ifIndex
                }
        STATUS current
        DESCRIPTION 
            ""
        ::={zxGponTraps 171}
        
    zxPonFanOffLineRestore    NOTIFICATION-TYPE
        OBJECTS {
                ifIndex
                }
        STATUS current
        DESCRIPTION 
            ""
        ::={zxGponTraps 172}

    zxGponLinkOntDyingGasp    NOTIFICATION-TYPE
        OBJECTS {
                ifIndex
                }
        STATUS current
        DESCRIPTION 
            ""
        ::={zxGponTraps 173}
        
    zxGponLinkOntDyingGaspRestore    NOTIFICATION-TYPE
        OBJECTS {
                ifIndex
                }
        STATUS current
        DESCRIPTION 
            ""
        ::={zxGponTraps 174}

    zxGponOltRxPowerAlarmi    NOTIFICATION-TYPE
        OBJECTS {
            ifIndex,
            zxGponOltRxPowerAlarmiReason,
            zxGponOntDevMgmtName,
            zxGponOntDevMgmtTypeName,
            zxGponOntDevMgmtDescription,
            zxGponOnuRegistrationInfo
        }
        STATUS current
        DESCRIPTION 
            ""
        ::={zxGponTraps 175}
        
    zxGponOltRxPowerAlarmiRestore    NOTIFICATION-TYPE
        OBJECTS {
            ifIndex,
            zxGponOltRxPowerAlarmiReason,
            zxGponOntDevMgmtName,
            zxGponOntDevMgmtTypeName,
            zxGponOntDevMgmtDescription,
            zxGponOnuRegistrationInfo
        }
        STATUS current
        DESCRIPTION 
            ""
        ::={zxGponTraps 176}

    zxGponOltRxPowerAbnormalInformi    NOTIFICATION-TYPE
        OBJECTS {
            ifIndex,
            zxGponOltRxPowerAbnormalInformiReason,
            zxGponOntDevMgmtName,
            zxGponOntDevMgmtTypeName,
            zxGponOntDevMgmtDescription,
            zxGponOnuRegistrationInfo
        }
        STATUS current
        DESCRIPTION 
            ""
        ::={zxGponTraps 177}
        
    zxGponOltRxPowerNormalInformi    NOTIFICATION-TYPE
        OBJECTS {
            ifIndex,
            zxGponOntDevMgmtName,
            zxGponOntDevMgmtTypeName,
            zxGponOntDevMgmtDescription,
            zxGponOnuRegistrationInfo
        }
        STATUS current
        DESCRIPTION 
            ""
        ::={zxGponTraps 178}

    zxGponOltTxPowerAlarm    NOTIFICATION-TYPE
        OBJECTS {
                ifIndex,zxGponOltTxPowerAlarmReason
                }
        STATUS current
        DESCRIPTION 
            ""
        ::={zxGponTraps 179}
        
    zxGponOltTxPowerAlarmRestore    NOTIFICATION-TYPE
        OBJECTS {
                ifIndex,zxGponOltTxPowerAlarmReason
                }
        STATUS current
        DESCRIPTION 
            ""
        ::={zxGponTraps 180}
    
    zxGponOltTxPowerAbnormalInform    NOTIFICATION-TYPE
        OBJECTS {
                ifIndex,zxGponOltTxPowerAbnormalInformReason
                }
        STATUS current
        DESCRIPTION 
            ""
        ::={zxGponTraps 181}
        
    zxGponOltTxPowerNormalInform    NOTIFICATION-TYPE
        OBJECTS {
                ifIndex,zxGponOntDevMgmtName,zxGponOntDevMgmtTypeName,zxGponOntDevMgmtDescription
                }
        STATUS current
        DESCRIPTION 
            ""
        ::={zxGponTraps 182}

    zxGponOltFakedSN    NOTIFICATION-TYPE
        OBJECTS {
                ifIndex,zxGponTrapEventString,zxGponOntDevMgmtName,zxGponOntDevMgmtTypeName,zxGponOntDevMgmtDescription
                }
        STATUS current
        DESCRIPTION 
            "OLT detects a faked SN event."
        ::={zxGponTraps 183}
        
    zxGponOnuConstantOptical    NOTIFICATION-TYPE
        OBJECTS {
            ifIndex,
            zxGponOntDevMgmtName,
            zxGponOntDevMgmtTypeName,
            zxGponOntDevMgmtDescription,
            zxGponOnuRegistrationInfo
        }
        STATUS current
        DESCRIPTION 
            "It  indicate ONU constant optical."
        ::={zxGponTraps 184}
        
    zxGponOnuConstantOpticalRestore    NOTIFICATION-TYPE
        OBJECTS {
            ifIndex,
            zxGponOntDevMgmtName,
            zxGponOntDevMgmtTypeName,
            zxGponOntDevMgmtDescription,
            zxGponOnuRegistrationInfo
        }
        STATUS current
        DESCRIPTION 
            "It  indicate ONU constant optical restore."
        ::={zxGponTraps 185}
        
    zxGponOnuFiberBending    NOTIFICATION-TYPE
        OBJECTS {
            ifIndex,
            zxGponOntDevMgmtName,
            zxGponOntDevMgmtTypeName,
            zxGponOntDevMgmtDescription,
            zxGponOnuRegistrationInfo
        }
        STATUS current
        DESCRIPTION 
            "It  indicate ONU constant optical."
        ::={zxGponTraps 186}
        
    zxGponOnuFiberBendingRestore    NOTIFICATION-TYPE
        OBJECTS {
            ifIndex,
            zxGponOntDevMgmtName,
            zxGponOntDevMgmtTypeName,
            zxGponOntDevMgmtDescription,
            zxGponOnuRegistrationInfo
        }
        STATUS current
        DESCRIPTION 
            "It  indicate ONU constant optical restore."
        ::={zxGponTraps 187}        

    zxGponOnuOpticalTransceiverLos  NOTIFICATION-TYPE
        OBJECTS {
                ifIndex,zxGponOntDevMgmtName,zxGponOntDevMgmtTypeName,zxGponOntDevMgmtDescription
                }
        STATUS current
        DESCRIPTION 
            "It  indicate ONU constant optical."
        ::={zxGponTraps 188}
        
    zxGponOnuOpticalTransceiverLosRestore    NOTIFICATION-TYPE
        OBJECTS {
                ifIndex,zxGponOntDevMgmtName,zxGponOntDevMgmtTypeName,zxGponOntDevMgmtDescription
                }
        STATUS current
        DESCRIPTION 
            "It  indicate ONU constant optical restore."
        ::={zxGponTraps 189}
        
    zxGponMacSpoofing    NOTIFICATION-TYPE
        OBJECTS {
            ifIndex,
            zxGponSpoofingPort,
            zxGponSpoofingMac,
            zxGponSpoofingVlan,
            zxGponSpoofingConflictPort,
            zxGponOntDevMgmtName,
            zxGponOntDevMgmtTypeName,
            zxGponOntDevMgmtDescription,
            zxGponOnuRegistrationInfo
        }
        STATUS current
        DESCRIPTION 
            "It  indicate Gpon port mac spoolfing."
        ::={zxGponTraps 190}
        
    zxGponUnauthOnuOnline  NOTIFICATION-TYPE
        OBJECTS {
                ifIndex,zxGponOntDevMgmtTypeName,zxGponUnCfgSnOntSN,zxGponUnCfgSnOntRID,zxGponUnCfgSnOntPsw,zxGponUnCfgSnOntRtd
                }
        STATUS current
        DESCRIPTION 
            "It  indicate ONU constant optical."
        ::={zxGponTraps 191}
 
     zxGponOltTF    NOTIFICATION-TYPE
        OBJECTS {
                ifIndex
                }
        STATUS current
        DESCRIPTION 
            "TF is Transmitter Failure."
        ::={zxGponTraps 192}
                
    zxGponOltTFRestore    NOTIFICATION-TYPE
        OBJECTS {
                ifIndex
                }
        STATUS current
        DESCRIPTION 
            "TF is Transmitter Failure."
        ::={zxGponTraps 193}
    
    zxGponOltFakedPassword    NOTIFICATION-TYPE
        OBJECTS {
                ifIndex,zxGponTrapEventString
                }
        STATUS current
        DESCRIPTION 
            "OLT detects a faked password event."
        ::={zxGponTraps 194}
            
    zxGponOnuAutoAuthSuccess   NOTIFICATION-TYPE
        OBJECTS {
            ifIndex,
            zxGponOntDevMgmtName,
            zxGponOntDevMgmtTypeName,
            zxGponOntDevMgmtDescription,
            zxGponOnuActType,
            zxGponOnuRegistrationInfo
        }
        STATUS current
        DESCRIPTION 
            "It occurred when the ONU is automatically added and entering working status."
        ::={zxGponTraps 195}
        
    zxGponOltLoei   NOTIFICATION-TYPE
        OBJECTS {
                ifIndex,zxGponOntDevMgmtProvisionSn,zxGponMgmtPonOnuId
                }
        STATUS current
        DESCRIPTION 
            "It occurred when the ONU disabled, 
            then turn off and reboot ONU, the ONU not on POPUP-state(O7)."
        ::={zxGponTraps 196}
   
    zxGponOnuIpMacAntiSpoofing   NOTIFICATION-TYPE
        OBJECTS {
            ifIndex,
            zxGponOntDevMgmtName,
            zxGponOntDevMgmtTypeName,
            zxGponOntDevMgmtDescription,
            zxGponOnuIpMacAntiSpoofingIndex,
            zxGponOnuIpMacAntiSpoofingMac,
            zxGponOnuIpMacAntiSpoofingIp,
            zxGponOnuRegistrationInfo
        }
        STATUS current
        DESCRIPTION 
            "It occurred when received illegal ip or mac package.
            "
        ::={zxGponTraps 197}
        
    zxGponOnuUniLoopbackAlarm   NOTIFICATION-TYPE
        OBJECTS {
            ifIndex,
            zxGponUNIIndex,
            zxGponOntDevMgmtName,
            zxGponOntDevMgmtTypeName,
            zxGponOntDevMgmtDescription,
            zxGponOnuRegistrationInfo        
        }
        STATUS current
        DESCRIPTION 
            "It occurred when  ONU ethernet
             port loopback."
        ::={zxGponTraps 198}
        
    zxGponOnuUniLoopbackRestore   NOTIFICATION-TYPE
        OBJECTS {
            ifIndex,
            zxGponUNIIndex,
            zxGponOntDevMgmtName,
            zxGponOntDevMgmtTypeName,
            zxGponOntDevMgmtDescription,
            zxGponOnuRegistrationInfo        
        }
        STATUS current
        DESCRIPTION 
            "It occurred when ONU ethernet
             port loopback was restore."
        ::={zxGponTraps 199}
        
    zxGponOnuLoidAuthNotification    NOTIFICATION-TYPE
        OBJECTS {
                ifIndex,
                zxGponOnuLoidAuthResult
                }
        STATUS current
        DESCRIPTION 
            "It occurred when ONU authentication mode is
            LOID or LOID plus Password."
        ::={zxGponTraps 200}


END
